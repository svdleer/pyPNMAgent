--
-- SA-IHP-MIB.mib
-- MIB generated by MG-SOFT Visual MIB Builder Version 4.0 Build 349
-- Monday, November 17, 2003 at 11:01:01
--

-- Revision 1 : Release Candidate
-- Date: Wednesday, July 23, 2003 at 14:28:46
-- Comment:
-- 
-- Revision 2 : IHP Packet Loopback Test
-- Date: Monday, November 17, 2003 at 10:59:00
-- Comment:
-- Added support for the IHP Packet
-- Loopback Test. The ihpLoopbackTestTable
-- was added.
-- 
	SA-IHP-MIB DEFINITIONS ::= BEGIN
 
		IMPORTS
			ifIndex, DisplayString			
				FROM RFC1213-MIB			
			saIhpMib			
				FROM SA-DBDSGEN-MIB			
			saLlcStationSubIndex			
				FROM SA-LLC-MIB			
			saModules			
				FROM SCIATL-COMMON-MIB			
			OBJECT-GROUP, MODULE-COMPLIANCE			
				FROM SNMPv2-CONF			
			TimeTicks, IpAddress, Integer32, Unsigned32, Counter32, 
			OBJECT-TYPE, MODULE-IDENTITY, OBJECT-IDENTITY			
				FROM SNMPv2-SMI			
			DateAndTime			
				FROM SNMPv2-TC;
	
	
		-- 1.3.6.1.4.1.1429.7.1.11
		saIhpMibModule MODULE-IDENTITY 
			LAST-UPDATED "200311171056Z"		-- November 17, 2003 at 10:56 GMT
			ORGANIZATION 
				"Scientific-Atlanta"
			CONTACT-INFO 
				"DBDS Software Engineering & Architecture
				Scientific-Atlanta
				5030 Sugarloaf Parkway
				Lawrenceville, GA 30044
				"
			DESCRIPTION 
				"In-Home Protocol MIB Module.
				
				This MIB module Copyright 2003 Scientific-Atlanta
				"
			REVISION "200311171056Z"		-- November 17, 2003 at 10:56 GMT
			DESCRIPTION 
				"Added support for the IHP Packet
				Loopback Test. The ihpLoopbackTestTable
				was added."
			REVISION "200307231428Z"		-- July 23, 2003 at 14:28 GMT
			DESCRIPTION 
				" "
			::= { saModules 11 }

		
	
	
	
--
-- Node definitions
--
	
		-- 1.3.6.1.4.1.1429.9.1.4.1
		saIhpConf OBJECT-IDENTITY
			STATUS current
			DESCRIPTION 
				"Conformance"
			::= { saIhpMib 1 }

		
		-- 1.3.6.1.4.1.1429.9.1.4.1.1
		saIhpGroups OBJECT-IDENTITY
			STATUS current
			DESCRIPTION 
				"Object Groups of the SA-IHP-MIB"
			::= { saIhpConf 1 }

		
		-- 1.3.6.1.4.1.1429.9.1.4.1.1.1
		saIhpStationGroup OBJECT-GROUP
			OBJECTS { ihpStationName, ihpStationIhpMacAddress, ihpStationRfMacAddress, ihpStationPid, ihpStationType
				 }
			STATUS current
			DESCRIPTION 
				"Description."
			::= { saIhpGroups 1 }

		
		-- 1.3.6.1.4.1.1429.9.1.4.1.1.2
		saIhpCpMasterGroup OBJECT-GROUP
			OBJECTS { ihpCpRegMasterRegRqsIn, ihpCpRegMasterRegRepliesOut }
			STATUS current
			DESCRIPTION 
				"Description."
			::= { saIhpGroups 2 }

		
		-- 1.3.6.1.4.1.1429.9.1.4.1.1.3
		saIhpCpMasterRegGroup OBJECT-GROUP
			OBJECTS { ihpCpMasterRegIndex, ihpCpMasterRegRfMacAddress, ihpCpMasterRegLeaseTimeRemaining, ihpCpMasterRegLeasedItems, ihpCpMasterRegIhpMacAddress, 
				ihpCpMasterRegPid, ihpCpMasterRegIp, ihpCpMasterRegSubnetMask }
			STATUS current
			DESCRIPTION 
				"Description."
			::= { saIhpGroups 3 }

		
		-- 1.3.6.1.4.1.1429.9.1.4.1.1.4
		saIhpCpRegGroup OBJECT-GROUP
			OBJECTS { ihpCpRegStatus, ihpCpRegLeaseTimeRemaining, ihpCpRegLeasedItems, ihpCpRegIhpMacAddress, ihpCpRegPid, 
				ihpCpRegIp, ihpCpRegSubnetMask, ihpCpRegMasterRfMacAddress, ihpCpRegMasterIhpMacAddress }
			STATUS current
			DESCRIPTION 
				"Description."
			::= { saIhpGroups 4 }

		
		-- 1.3.6.1.4.1.1429.9.1.4.1.1.5
		saIhpCpSlaveGroup OBJECT-GROUP
			OBJECTS { ihpCpRegSlaveRegRqsOut, ihpCpRegSlaveRegRepliesIn }
			STATUS current
			DESCRIPTION 
				"Description."
			::= { saIhpGroups 5 }

		
		-- 1.3.6.1.4.1.1429.9.1.4.1.1.6
		saIhpMacGroup OBJECT-GROUP
			OBJECTS { ihpMacIndex, ihpMacName, ihpMacPduGoodIn, ihpMacPduErrRuntIn, ihpMacPduErrJumboIn, 
				ihpMacPduErrCrcIn, ihpMacPduErrLengthIn, ihpMacPduErrDestIn, ihpMacPduRawBytesIn, ihpMacBytesIn, 
				ihpMacBytesOut, ihpMacPduOut }
			STATUS current
			DESCRIPTION 
				"IHP MAC Layer Statistics"
			::= { saIhpGroups 6 }

		
		-- 1.3.6.1.4.1.1429.9.1.4.1.1.7
		saIhpLoopbackTestGroup OBJECT-GROUP
			OBJECTS { ihpLoopbackTestStatus, ihpLoopbackTestTime }
			STATUS current
			DESCRIPTION 
				"IHP Packet Loopback Test Status"
			::= { saIhpGroups 7 }

		
		-- 1.3.6.1.4.1.1429.9.1.4.1.2
		saIhpCompls OBJECT-IDENTITY
			STATUS current
			DESCRIPTION 
				"Compliances of the SA-IHP-MIB"
			::= { saIhpConf 2 }

		
		-- 1.3.6.1.4.1.1429.9.1.4.1.2.1
		saIhpMasterCompliance MODULE-COMPLIANCE
			STATUS current
			DESCRIPTION 
				"All stations providing IHP Master capability must
				provide this level of support."
			MODULE -- this module
				MANDATORY-GROUPS { saIhpStationGroup, saIhpCpRegGroup, saIhpCpMasterGroup, saIhpCpMasterRegGroup, saIhpMacGroup
					 }
			::= { saIhpCompls 1 }

		
		-- 1.3.6.1.4.1.1429.9.1.4.1.2.2
		saIhpSlaveCompliance MODULE-COMPLIANCE
			STATUS current
			DESCRIPTION 
				"All slave stations must provide this level of support."
			MODULE -- this module
				MANDATORY-GROUPS { saIhpStationGroup, saIhpCpSlaveGroup, saIhpCpRegGroup, saIhpMacGroup }
			::= { saIhpCompls 2 }

		
		-- 1.3.6.1.4.1.1429.9.1.4.2
		saIhpObjs OBJECT-IDENTITY
			STATUS current
			DESCRIPTION 
				"The MIB Objects defined for the SA-IHP-MIB module."
			::= { saIhpMib 2 }

		
		-- 1.3.6.1.4.1.1429.9.1.4.2.1
		ihpStation OBJECT-IDENTITY
			STATUS current
			DESCRIPTION 
				"In-Home Protocol information for this station."
			::= { saIhpObjs 1 }

		
		-- 1.3.6.1.4.1.1429.9.1.4.2.1.1
		ihpStationTable OBJECT-TYPE
			SYNTAX SEQUENCE OF IhpStationEntry
			MAX-ACCESS not-accessible
			STATUS current
			DESCRIPTION
				"This table contains the operating parameters for this station on the IHP network. "
			::= { ihpStation 1 }

		
		-- 1.3.6.1.4.1.1429.9.1.4.2.1.1.1
		ihpStationEntry OBJECT-TYPE
			SYNTAX IhpStationEntry
			MAX-ACCESS not-accessible
			STATUS current
			DESCRIPTION
				"An entry in the table. An entry will exist for every IHP interface
				on the station. The entries are indexed by ifIndex and saLlcStationSubIndex
				to provide a linkage to that related information."
			INDEX { ifIndex, saLlcStationSubIndex }
			::= { ihpStationTable 1 }

		
		IhpStationEntry ::=
			SEQUENCE { 
				ihpStationName
					DisplayString,
				ihpStationRfMacAddress
					OCTET STRING,
				ihpStationIhpMacAddress
					OCTET STRING,
				ihpStationType
					INTEGER
			 }

		-- 1.3.6.1.4.1.1429.9.1.4.2.1.1.1.1
		ihpStationName OBJECT-TYPE
			SYNTAX DisplayString
			MAX-ACCESS read-only
			STATUS current
			DESCRIPTION
				"A descriptive name for this IHP Station."
			::= { ihpStationEntry 1 }

		
		-- 1.3.6.1.4.1.1429.9.1.4.2.1.1.1.2
		ihpStationRfMacAddress OBJECT-TYPE
			SYNTAX OCTET STRING
			MAX-ACCESS read-only
			STATUS current
			DESCRIPTION
				"The RF MAC address of the station. Zero if no such 
				address exists or is not known."
			::= { ihpStationEntry 2 }

		
		-- 1.3.6.1.4.1.1429.9.1.4.2.1.1.1.3
		ihpStationIhpMacAddress OBJECT-TYPE
			SYNTAX OCTET STRING (SIZE (1))
			MAX-ACCESS read-only
			STATUS current
			DESCRIPTION
				"The IHP MAC address of the station."
			::= { ihpStationEntry 3 }

		
		-- 1.3.6.1.4.1.1429.9.1.4.2.1.1.1.4
		ihpStationType OBJECT-TYPE
			SYNTAX INTEGER
				{
				master(1),
				slave(2)
				}
			MAX-ACCESS read-only
			STATUS current
			DESCRIPTION
				"The type of station:
				master = an IHP network master
				slave  = an IHP network slave"
			::= { ihpStationEntry 4 }

		
		-- 1.3.6.1.4.1.1429.9.1.4.2.1.2
		ihpLoopbackTestTable OBJECT-TYPE
			SYNTAX SEQUENCE OF IhpLoopbackTestEntry
			MAX-ACCESS not-accessible
			STATUS current
			DESCRIPTION
				"This table provides the status of the IHP Packet
				Loopback test."
			::= { ihpStation 2 }

		
		-- 1.3.6.1.4.1.1429.9.1.4.2.1.2.1
		ihpLoopbackTestEntry OBJECT-TYPE
			SYNTAX IhpLoopbackTestEntry
			MAX-ACCESS not-accessible
			STATUS current
			DESCRIPTION
				"A row in the table."
			AUGMENTS { ihpStationEntry }
			::= { ihpLoopbackTestTable 1 }

		
		IhpLoopbackTestEntry ::=
			SEQUENCE { 
				ihpLoopbackTestStatus
					INTEGER,
				ihpLoopbackTestTime
					DateAndTime
			 }

		-- 1.3.6.1.4.1.1429.9.1.4.2.1.2.1.1
		ihpLoopbackTestStatus OBJECT-TYPE
			SYNTAX INTEGER
				{
				unknown(0),
				ok(1),
				marg(2),
				fail(3),
				inProg(4)
				}
			MAX-ACCESS read-only
			STATUS current
			DESCRIPTION
				"IHP packet loop back test status -
				
				Ok = The test was run to completion and met the passing criteria
				
				Marg = The test was run to completion and the results were in the marginal region of operation
				
				Fail = The test was run to completion and failed
				
				InProg = The test is currently in progress
				
				Unknown = The test has never been run or was aborted
				"
			::= { ihpLoopbackTestEntry 1 }

		
		-- 1.3.6.1.4.1.1429.9.1.4.2.1.2.1.2
		ihpLoopbackTestTime OBJECT-TYPE
			SYNTAX DateAndTime
			MAX-ACCESS read-only
			STATUS current
			DESCRIPTION
				"The time the ihpLoopbackTestStatus last changed."
			::= { ihpLoopbackTestEntry 2 }

		
		-- 1.3.6.1.4.1.1429.9.1.4.2.2
		ihpCp OBJECT-IDENTITY
			STATUS current
			DESCRIPTION 
				"Information pertaining to the In-Home Protocol Control Protocol"
			::= { saIhpObjs 2 }

		
		-- 1.3.6.1.4.1.1429.9.1.4.2.2.1
		ihpCpRegMasterStatsTable OBJECT-TYPE
			SYNTAX SEQUENCE OF IhpCpRegMasterStatsEntry
			MAX-ACCESS not-accessible
			STATUS current
			DESCRIPTION
				"Registration statistics"
			::= { ihpCp 1 }

		
		-- 1.3.6.1.4.1.1429.9.1.4.2.2.1.1
		ihpCpRegMasterStatsEntry OBJECT-TYPE
			SYNTAX IhpCpRegMasterStatsEntry
			MAX-ACCESS not-accessible
			STATUS current
			DESCRIPTION
				"An entry in the table."
			AUGMENTS { ihpStationEntry }
			::= { ihpCpRegMasterStatsTable 1 }

		
		IhpCpRegMasterStatsEntry ::=
			SEQUENCE { 
				ihpCpRegMasterRegRqsIn
					Counter32,
				ihpCpRegMasterRegRepliesOut
					Counter32
			 }

		-- 1.3.6.1.4.1.1429.9.1.4.2.2.1.1.1
		ihpCpRegMasterRegRqsIn OBJECT-TYPE
			SYNTAX Counter32
			MAX-ACCESS read-only
			STATUS current
			DESCRIPTION
				"The number of registration requests the master has
				received since the IHP protocol was initialized on
				this station."
			::= { ihpCpRegMasterStatsEntry 1 }

		
		-- 1.3.6.1.4.1.1429.9.1.4.2.2.1.1.2
		ihpCpRegMasterRegRepliesOut OBJECT-TYPE
			SYNTAX Counter32
			MAX-ACCESS read-only
			STATUS current
			DESCRIPTION
				"The number of registration replies the master has
				sent since the protocol was initialized on this station."
			::= { ihpCpRegMasterStatsEntry 2 }

		
		-- 1.3.6.1.4.1.1429.9.1.4.2.2.2
		ihpCpRegSlaveTable OBJECT-TYPE
			SYNTAX SEQUENCE OF IhpCpRegSlaveEntry
			MAX-ACCESS not-accessible
			STATUS current
			DESCRIPTION
				"Registration statistics"
			::= { ihpCp 2 }

		
		-- 1.3.6.1.4.1.1429.9.1.4.2.2.2.1
		ihpCpRegSlaveEntry OBJECT-TYPE
			SYNTAX IhpCpRegSlaveEntry
			MAX-ACCESS not-accessible
			STATUS current
			DESCRIPTION
				"An entry in the table."
			AUGMENTS { ihpStationEntry }
			::= { ihpCpRegSlaveTable 1 }

		
		IhpCpRegSlaveEntry ::=
			SEQUENCE { 
				ihpCpRegSlaveRegRqsOut
					Counter32,
				ihpCpRegSlaveRegRepliesIn
					Counter32
			 }

		-- 1.3.6.1.4.1.1429.9.1.4.2.2.2.1.1
		ihpCpRegSlaveRegRqsOut OBJECT-TYPE
			SYNTAX Counter32
			MAX-ACCESS read-only
			STATUS current
			DESCRIPTION
				"The number of registration requests this slave station has
				sent since the protocol was initialized on this station."
			::= { ihpCpRegSlaveEntry 1 }

		
		-- 1.3.6.1.4.1.1429.9.1.4.2.2.2.1.2
		ihpCpRegSlaveRegRepliesIn OBJECT-TYPE
			SYNTAX Counter32
			MAX-ACCESS read-only
			STATUS current
			DESCRIPTION
				"The number of registration replies this slave station has
				received since the protocol was initialized on this station."
			::= { ihpCpRegSlaveEntry 2 }

		
		-- 1.3.6.1.4.1.1429.9.1.4.2.2.3
		ihpCpRegTable OBJECT-TYPE
			SYNTAX SEQUENCE OF IhpCpRegEntry
			MAX-ACCESS not-accessible
			STATUS current
			DESCRIPTION
				"Registration information for this station."
			::= { ihpCp 3 }

		
		-- 1.3.6.1.4.1.1429.9.1.4.2.2.3.1
		ihpCpRegEntry OBJECT-TYPE
			SYNTAX IhpCpRegEntry
			MAX-ACCESS not-accessible
			STATUS current
			DESCRIPTION
				"An entry in the table."
			AUGMENTS { ihpStationEntry }
			::= { ihpCpRegTable 1 }

		
		IhpCpRegEntry ::=
			SEQUENCE { 
				ihpCpRegStatus
					INTEGER,
				ihpCpRegLeaseTimeRemaining
					TimeTicks,
				ihpCpRegLeasedItems
					BITS,
				ihpCpRegIhpMacAddress
					OCTET STRING,
				ihpCpRegPid
					Unsigned32,
				ihpCpRegIp
					IpAddress,
				ihpCpRegSubnetMask
					IpAddress,
				ihpCpRegMasterRfMacAddress
					OCTET STRING,
				ihpCpRegMasterIhpMacAddress
					OCTET STRING
			 }

		-- 1.3.6.1.4.1.1429.9.1.4.2.2.3.1.1
		ihpCpRegStatus OBJECT-TYPE
			SYNTAX INTEGER
				{
				noLease(1),
				discover(2),
				bound(3),
				boundRenew(4)
				}
			MAX-ACCESS read-only
			STATUS current
			DESCRIPTION
				"The state of the current IHP lease:
				noLease    = the station does not have a lease
				discover   = the station does not have a lease, but is attempting to obtain one
				bound      = the station has a lease
				boundRenew = the station has a lease and is in the period where renewal can take place"
			::= { ihpCpRegEntry 1 }

		
		-- 1.3.6.1.4.1.1429.9.1.4.2.2.3.1.2
		ihpCpRegLeaseTimeRemaining OBJECT-TYPE
			SYNTAX TimeTicks
			MAX-ACCESS read-only
			STATUS current
			DESCRIPTION
				"The amount of time remaining in the lease, scaled for TimeTicks. If a lease is
				not current, then this value is zero."
			::= { ihpCpRegEntry 2 }

		
		-- 1.3.6.1.4.1.1429.9.1.4.2.2.3.1.3
		ihpCpRegLeasedItems OBJECT-TYPE
			SYNTAX BITS
				{
				ihpMac(0),
				pid(1),
				ip(2)
				}
			MAX-ACCESS read-only
			STATUS current
			DESCRIPTION
				"Indicates the items that are under lease:
				ihpMac = IHP MAC Address
				pid    = PID for the MPEG Transport Stream
				ip     = IP Address
				
				No bits are set if the lease is not current."
			::= { ihpCpRegEntry 3 }

		
		-- 1.3.6.1.4.1.1429.9.1.4.2.2.3.1.4
		ihpCpRegIhpMacAddress OBJECT-TYPE
			SYNTAX OCTET STRING (SIZE (1))
			MAX-ACCESS read-only
			STATUS current
			DESCRIPTION
				"The IHP MAC address assigned to the station. Only valid if
				ihpMac is set in ihpCpRegLeasedItems."
			::= { ihpCpRegEntry 4 }

		
		-- 1.3.6.1.4.1.1429.9.1.4.2.2.3.1.5
		ihpCpRegPid OBJECT-TYPE
			SYNTAX Unsigned32
			MAX-ACCESS read-only
			STATUS current
			DESCRIPTION
				"The MPEG Transport PID assigned for use when encapsulating IHP PDUs within
				MPEG-PS sections for transmission to the station. Only valid when pid
				is set in ihpCpRegLeasedItems.
				"
			::= { ihpCpRegEntry 5 }

		
		-- 1.3.6.1.4.1.1429.9.1.4.2.2.3.1.6
		ihpCpRegIp OBJECT-TYPE
			SYNTAX IpAddress
			MAX-ACCESS read-only
			STATUS current
			DESCRIPTION
				"The IP address assigned to this station. Only valid if
				ip is set in ihpCpRegLeasedItems."
			::= { ihpCpRegEntry 6 }

		
		-- 1.3.6.1.4.1.1429.9.1.4.2.2.3.1.7
		ihpCpRegSubnetMask OBJECT-TYPE
			SYNTAX IpAddress
			MAX-ACCESS read-only
			STATUS current
			DESCRIPTION
				"The assigned subnet mask.Only valid if
				ip is set in ihpCpRegLeasedItems."
			::= { ihpCpRegEntry 7 }

		
		-- 1.3.6.1.4.1.1429.9.1.4.2.2.3.1.8
		ihpCpRegMasterRfMacAddress OBJECT-TYPE
			SYNTAX OCTET STRING
			MAX-ACCESS read-only
			STATUS current
			DESCRIPTION
				"The RF MAC address of the station that provided the lease. Zero if no such
				address exists, is not known, or if the lease is not current."
			::= { ihpCpRegEntry 8 }

		
		-- 1.3.6.1.4.1.1429.9.1.4.2.2.3.1.9
		ihpCpRegMasterIhpMacAddress OBJECT-TYPE
			SYNTAX OCTET STRING
			MAX-ACCESS read-only
			STATUS current
			DESCRIPTION
				"The IHP MAC address of the station that provided the lease. Zero if no such
				address exists, is not known, or if the lease is not current."
			::= { ihpCpRegEntry 9 }

		
		-- 1.3.6.1.4.1.1429.9.1.4.2.2.4
		ihpCpMasterRegTable OBJECT-TYPE
			SYNTAX SEQUENCE OF IhpCpMasterRegEntry
			MAX-ACCESS not-accessible
			STATUS current
			DESCRIPTION
				"Registration information for stations assigned by the master. The IHP
				master must list all stations having a current lease, including itself. "
			::= { ihpCp 4 }

		
		-- 1.3.6.1.4.1.1429.9.1.4.2.2.4.1
		ihpCpMasterRegEntry OBJECT-TYPE
			SYNTAX IhpCpMasterRegEntry
			MAX-ACCESS not-accessible
			STATUS current
			DESCRIPTION
				"An entry in the table."
			INDEX { ifIndex, saLlcStationSubIndex, ihpCpMasterRegIndex }
			::= { ihpCpMasterRegTable 1 }

		
		IhpCpMasterRegEntry ::=
			SEQUENCE { 
				ihpCpMasterRegIndex
					Integer32,
				ihpCpMasterRegRfMacAddress
					OCTET STRING,
				ihpCpMasterRegLeaseTimeRemaining
					TimeTicks,
				ihpCpMasterRegLeasedItems
					BITS,
				ihpCpMasterRegIhpMacAddress
					OCTET STRING,
				ihpCpMasterRegPid
					Unsigned32,
				ihpCpMasterRegIp
					IpAddress,
				ihpCpMasterRegSubnetMask
					IpAddress
			 }

		-- 1.3.6.1.4.1.1429.9.1.4.2.2.4.1.1
		ihpCpMasterRegIndex OBJECT-TYPE
			SYNTAX Integer32 (1..65534)
			MAX-ACCESS read-only
			STATUS current
			DESCRIPTION
				"A unique number for this entry."
			::= { ihpCpMasterRegEntry 1 }

		
		-- 1.3.6.1.4.1.1429.9.1.4.2.2.4.1.2
		ihpCpMasterRegRfMacAddress OBJECT-TYPE
			SYNTAX OCTET STRING
			MAX-ACCESS read-only
			STATUS current
			DESCRIPTION
				"The RF MAC address of the station associated with the lease."
			::= { ihpCpMasterRegEntry 2 }

		
		-- 1.3.6.1.4.1.1429.9.1.4.2.2.4.1.3
		ihpCpMasterRegLeaseTimeRemaining OBJECT-TYPE
			SYNTAX TimeTicks
			MAX-ACCESS read-only
			STATUS current
			DESCRIPTION
				"The amount of time remaining in the slave's lease, scaled for TimeTicks. If a lease is
				not current, then this value is zero."
			::= { ihpCpMasterRegEntry 3 }

		
		-- 1.3.6.1.4.1.1429.9.1.4.2.2.4.1.4
		ihpCpMasterRegLeasedItems OBJECT-TYPE
			SYNTAX BITS
				{
				ihpMac(0),
				pid(1),
				ip(2)
				}
			MAX-ACCESS read-only
			STATUS current
			DESCRIPTION
				"Indicates the items that are under lease:
				ihpMac = IHP MAC Address
				pid    = PID for the MPEG Transport Stream
				ip     = IP Address
				
				"
			::= { ihpCpMasterRegEntry 4 }

		
		-- 1.3.6.1.4.1.1429.9.1.4.2.2.4.1.5
		ihpCpMasterRegIhpMacAddress OBJECT-TYPE
			SYNTAX OCTET STRING (SIZE (1))
			MAX-ACCESS read-only
			STATUS current
			DESCRIPTION
				"The IHP MAC address assigned to the slave station. Only valid if
				ihpMac is set in ihpCpMasterRegLeasedItems."
			::= { ihpCpMasterRegEntry 5 }

		
		-- 1.3.6.1.4.1.1429.9.1.4.2.2.4.1.6
		ihpCpMasterRegPid OBJECT-TYPE
			SYNTAX Unsigned32
			MAX-ACCESS read-only
			STATUS current
			DESCRIPTION
				"The MPEG Transport PID assigned for use when encapsulating IHP PDUs within
				MPEG-PS sections for transmission to the slave station. Only valid when pid
				is set in ihpCpMasterRegLeasedItems.
				"
			::= { ihpCpMasterRegEntry 6 }

		
		-- 1.3.6.1.4.1.1429.9.1.4.2.2.4.1.7
		ihpCpMasterRegIp OBJECT-TYPE
			SYNTAX IpAddress
			MAX-ACCESS read-only
			STATUS current
			DESCRIPTION
				"The IP address assigned to the slave station. Only valid if
				ip is set in ihpCpMasterRegLeasedItems."
			::= { ihpCpMasterRegEntry 7 }

		
		-- 1.3.6.1.4.1.1429.9.1.4.2.2.4.1.8
		ihpCpMasterRegSubnetMask OBJECT-TYPE
			SYNTAX IpAddress
			MAX-ACCESS read-only
			STATUS current
			DESCRIPTION
				"The subnet mask assigned to the slave station.Only valid if
				ip is set in ihpCpMasterRegLeasedItems."
			::= { ihpCpMasterRegEntry 8 }

		
		-- 1.3.6.1.4.1.1429.9.1.4.2.3
		ihpMpegEncapsulation OBJECT-IDENTITY
			STATUS current
			DESCRIPTION 
				"Description."
			::= { saIhpObjs 3 }

		
		-- 1.3.6.1.4.1.1429.9.1.4.2.3.1
		ihpMpegEncapTable OBJECT-TYPE
			SYNTAX SEQUENCE OF IhpMpegEncapEntry
			MAX-ACCESS not-accessible
			STATUS current
			DESCRIPTION
				"Information regarding MPEG-encapsulated IHP."
			::= { ihpMpegEncapsulation 1 }

		
		-- 1.3.6.1.4.1.1429.9.1.4.2.3.1.1
		ihpMpegEncapEntry OBJECT-TYPE
			SYNTAX IhpMpegEncapEntry
			MAX-ACCESS not-accessible
			STATUS current
			DESCRIPTION
				"An entry in the table."
			AUGMENTS { ihpStationEntry }
			::= { ihpMpegEncapTable 1 }

		
		IhpMpegEncapEntry ::=
			SEQUENCE { 
				ihpStationPid
					Unsigned32
			 }

		-- 1.3.6.1.4.1.1429.9.1.4.2.3.1.1.1
		ihpStationPid OBJECT-TYPE
			SYNTAX Unsigned32
			MAX-ACCESS read-only
			STATUS current
			DESCRIPTION
				"The MPEG Transport PID used when encapsulating IHP PDUs within
				MPEG-PS sections for transmission to the station. A value of zero
				indicates that no PID has been assigned or that it is not known."
			::= { ihpMpegEncapEntry 1 }

		
		-- 1.3.6.1.4.1.1429.9.1.4.2.4
		ihpMac OBJECT-IDENTITY
			STATUS current
			DESCRIPTION 
				"IHP Media Access Control"
			::= { saIhpObjs 4 }

		
		-- 1.3.6.1.4.1.1429.9.1.4.2.4.1
		ihpMacTable OBJECT-TYPE
			SYNTAX SEQUENCE OF IhpMacEntry
			MAX-ACCESS not-accessible
			STATUS current
			DESCRIPTION
				"IHP MAC Statistics"
			::= { ihpMac 1 }

		
		-- 1.3.6.1.4.1.1429.9.1.4.2.4.1.1
		ihpMacEntry OBJECT-TYPE
			SYNTAX IhpMacEntry
			MAX-ACCESS not-accessible
			STATUS current
			DESCRIPTION
				"An entry in the table."
			INDEX { ifIndex, ihpMacIndex }
			::= { ihpMacTable 1 }

		
		IhpMacEntry ::=
			SEQUENCE { 
				ihpMacIndex
					Integer32,
				ihpMacName
					DisplayString,
				ihpMacPduGoodIn
					Counter32,
				ihpMacPduErrRuntIn
					Counter32,
				ihpMacPduErrJumboIn
					Counter32,
				ihpMacPduErrCrcIn
					Counter32,
				ihpMacPduErrLengthIn
					Counter32,
				ihpMacPduErrDestIn
					Counter32,
				ihpMacPduRawBytesIn
					Counter32,
				ihpMacBytesIn
					Counter32,
				ihpMacBytesOut
					Counter32,
				ihpMacPduOut
					Counter32
			 }

		-- 1.3.6.1.4.1.1429.9.1.4.2.4.1.1.1
		ihpMacIndex OBJECT-TYPE
			SYNTAX Integer32 (1..2147483647)
			MAX-ACCESS read-only
			STATUS current
			DESCRIPTION
				"A unique value for this MAC interface."
			::= { ihpMacEntry 1 }

		
		-- 1.3.6.1.4.1.1429.9.1.4.2.4.1.1.2
		ihpMacName OBJECT-TYPE
			SYNTAX DisplayString
			MAX-ACCESS read-only
			STATUS current
			DESCRIPTION
				"A descriptive name for this IHP MAC interface."
			::= { ihpMacEntry 2 }

		
		-- 1.3.6.1.4.1.1429.9.1.4.2.4.1.1.3
		ihpMacPduGoodIn OBJECT-TYPE
			SYNTAX Counter32
			MAX-ACCESS read-only
			STATUS current
			DESCRIPTION
				"The number of PDUs that have been successfully received by the MAC layer and passed
				to the next higher layer (usually the link layer)."
			::= { ihpMacEntry 3 }

		
		-- 1.3.6.1.4.1.1429.9.1.4.2.4.1.1.4
		ihpMacPduErrRuntIn OBJECT-TYPE
			SYNTAX Counter32
			MAX-ACCESS read-only
			STATUS current
			DESCRIPTION
				"The number of received partial PDUs that have been rejected."
			::= { ihpMacEntry 4 }

		
		-- 1.3.6.1.4.1.1429.9.1.4.2.4.1.1.5
		ihpMacPduErrJumboIn OBJECT-TYPE
			SYNTAX Counter32
			MAX-ACCESS read-only
			STATUS current
			DESCRIPTION
				"The number of received PDUs where the length field is larger 
				than the maximum packet size."
			::= { ihpMacEntry 5 }

		
		-- 1.3.6.1.4.1.1429.9.1.4.2.4.1.1.6
		ihpMacPduErrCrcIn OBJECT-TYPE
			SYNTAX Counter32
			MAX-ACCESS read-only
			STATUS current
			DESCRIPTION
				"The number of received PDUs that failed the CRC check.
				"
			::= { ihpMacEntry 6 }

		
		-- 1.3.6.1.4.1.1429.9.1.4.2.4.1.1.7
		ihpMacPduErrLengthIn OBJECT-TYPE
			SYNTAX Counter32
			MAX-ACCESS read-only
			STATUS current
			DESCRIPTION
				"The number of received PDUs where the length field is 
				less than the minimum packet size."
			::= { ihpMacEntry 7 }

		
		-- 1.3.6.1.4.1.1429.9.1.4.2.4.1.1.8
		ihpMacPduErrDestIn OBJECT-TYPE
			SYNTAX Counter32
			MAX-ACCESS read-only
			STATUS current
			DESCRIPTION
				"The number of PDUs that are rejected due to an invalid destination address."
			::= { ihpMacEntry 8 }

		
		-- 1.3.6.1.4.1.1429.9.1.4.2.4.1.1.9
		ihpMacPduRawBytesIn OBJECT-TYPE
			SYNTAX Counter32
			MAX-ACCESS read-only
			STATUS current
			DESCRIPTION
				"The total number of bytes received by this MAC layer that are part of some
				PDU, whether or not the frame passed the other validity tests."
			::= { ihpMacEntry 9 }

		
		-- 1.3.6.1.4.1.1429.9.1.4.2.4.1.1.10
		ihpMacBytesIn OBJECT-TYPE
			SYNTAX Counter32
			MAX-ACCESS read-only
			STATUS current
			DESCRIPTION
				"The total number of bytes received by this MAC layer. This value
				includes any byte received regardless of validity."
			::= { ihpMacEntry 10 }

		
		-- 1.3.6.1.4.1.1429.9.1.4.2.4.1.1.11
		ihpMacBytesOut OBJECT-TYPE
			SYNTAX Counter32
			MAX-ACCESS read-only
			STATUS current
			DESCRIPTION
				"The total number of bytes sent by this MAC layer. This value
				includes frame start and CRC bytes."
			::= { ihpMacEntry 11 }

		
		-- 1.3.6.1.4.1.1429.9.1.4.2.4.1.1.12
		ihpMacPduOut OBJECT-TYPE
			SYNTAX Counter32
			MAX-ACCESS read-only
			STATUS current
			DESCRIPTION
				"The number of PDUs that have been sent to the medium by the MAC layer."
			::= { ihpMacEntry 12 }

		
		-- 1.3.6.1.4.1.1429.9.1.4.3
		saIhpEvents OBJECT-IDENTITY
			STATUS current
			DESCRIPTION 
				"Events associated with the IHP protocol."
			::= { saIhpMib 3 }

		
		-- 1.3.6.1.4.1.1429.9.1.4.3.0
		saIhpEventsV2 OBJECT-IDENTITY
			STATUS current
			DESCRIPTION 
				"Dummy node under which all events must be defined. 
				This is required for SNMP v1/v2 compatability."
			::= { saIhpEvents 0 }

		
	
	END

--
-- SA-IHP-MIB.mib
--
