--
-- SA-HOSTRESOURCES-MIB.mib
-- MIB generated by MG-SOFT Visual MIB Builder Version 4.0 Build 349
-- Thursday, February 03, 2005 at 17:43:11
--

-- Revision 1 : Initial
-- Date: Tuesday, April 06, 2004 at 14:56:32
-- Comment:
-- This revision contains the initial work done on this module.
-- 
	SA-HOSTRESOURCES-MIB DEFINITIONS ::= BEGIN
 
		IMPORTS
			hrDeviceIndex, hrFSEntry			
				FROM HOST-RESOURCES-MIB			
			saHostResourcesMib			
				FROM SA-DBDSGEN-MIB			
			saModules			
				FROM SCIATL-COMMON-MIB			
			OBJECT-GROUP, MODULE-COMPLIANCE			
				FROM SNMPv2-CONF			
			TimeTicks, Integer32, Unsigned32, Gauge32, OBJECT-TYPE, 
			MODULE-IDENTITY, OBJECT-IDENTITY			
				FROM SNMPv2-SMI			
			DisplayString, TimeStamp, DateAndTime			
				FROM SNMPv2-TC;
	
	
-- 
-- This MIB Module Copyright 2003 Scientific-Atlanta Corporation
-- 
-- 
		-- 1.3.6.1.4.1.1429.7.1.19
		saHostResourcesMibModule MODULE-IDENTITY 
			LAST-UPDATED "200404061456Z"		-- April 06, 2004 at 14:56 GMT
			ORGANIZATION 
				"Scientific-Atlanta"
			CONTACT-INFO 
				"DBDS Software Engineering & Architecture
				Scientific-Atlanta
				5030 Sugarloaf Parkway
				Lawrencville, GA 30044
				"
			DESCRIPTION 
				"The Scientific-Atlanta SA-HOSTRESOURCES-MIB module.
				
				THIS IS A PRELIMINARY MIB DEFINITION FOR REVIEW PURPOSES ONLY."
			REVISION "200404061456Z"		-- April 06, 2004 at 14:56 GMT
			DESCRIPTION 
				"This revision contains the initial work done on this module."
			::= { saModules 19 }

		
	
	
--
-- Node definitions
--
	
		-- 1.3.6.1.4.1.1429.9.1.12.1
		saHostResourcesConf OBJECT-IDENTITY
			STATUS current
			DESCRIPTION 
				"Conformance"
			::= { saHostResourcesMib 1 }

		
		-- 1.3.6.1.4.1.1429.9.1.12.1.1
		saLlcGroups OBJECT-IDENTITY
			STATUS current
			DESCRIPTION 
				"Object groups for the SA-HOSTRESOURCES-MIB"
			::= { saHostResourcesConf 1 }

		
		-- 1.3.6.1.4.1.1429.9.1.12.1.1.1
		saHrDeviceSleepTableGroup OBJECT-GROUP
			OBJECTS { saHrDeviceSleepTimeStamp, saHrDeviceSleepDuration }
			STATUS current
			DESCRIPTION 
				"The columns in the saHrDeviceSleepTable."
			::= { saLlcGroups 1 }

		
		-- 1.3.6.1.4.1.1429.9.1.12.1.1.2
		saHrDeviceTempTableGroup OBJECT-GROUP
			OBJECTS { saHrDeviceTempIndex, saHrDeviceTempDescr, saHrDeviceTempCurrentTemp }
			STATUS current
			DESCRIPTION 
				"The columns in the saHrDeviceTempTable."
			::= { saLlcGroups 2 }

		
		-- 1.3.6.1.4.1.1429.9.1.12.1.1.3
		saHrDiskStatSumTableGroup OBJECT-GROUP
			OBJECTS { saHrDiskStatSumCumReadErrors, saHrDiskStatSumCumWriteErrors }
			STATUS current
			DESCRIPTION 
				"The columns in the saHrDiskStatSumTable."
			::= { saLlcGroups 3 }

		
		-- 1.3.6.1.4.1.1429.9.1.12.1.1.4
		saHrDiskErrTableGroup OBJECT-GROUP
			OBJECTS { saHrDiskErrIndex , saHrDiskErrTimeStamp, saHrDiskErrLocation, saHrDiskErrCmdSent, saHrDiskErrCode
				 }
			STATUS current
			DESCRIPTION 
				"The columns in the saHrDiskErrTable."
			::= { saLlcGroups 4 }

		
		-- 1.3.6.1.4.1.1429.9.1.12.1.1.5
		saHrNvmTableGroup OBJECT-GROUP
			OBJECTS { saHrNvmStorageIndex }
			STATUS current
			DESCRIPTION 
				"The columns in the saHrNVMTable."
			::= { saLlcGroups 5 }

		
		-- 1.3.6.1.4.1.1429.9.1.12.1.1.6
		saHrNvmWriteStatTableGroup OBJECT-GROUP
			OBJECTS { saHrNvmWriteStatAddress, saHrNvmWriteStatSuccesses, saHrNvmWriteStatFailures, saHrNvmWriteStatLastFailTime }
			STATUS current
			DESCRIPTION 
				"The columns in the saHrNvmWriteStatTable."
			::= { saLlcGroups 6 }

		
		-- 1.3.6.1.4.1.1429.9.1.12.1.1.7
		saHrNvmWriteTableGroup OBJECT-GROUP
			OBJECTS { saHrNvmWriteCumulativeSuccesses, saHrNvmWriteStatMaxEntries, saHrNvmWriteStatCumulativeExcessFailures }
			STATUS current
			DESCRIPTION 
				"The columns in the saHrNvmWriteTable."
			::= { saLlcGroups 7 }

		
		-- 1.3.6.1.4.1.1429.9.1.12.1.1.8
		saHrDeviceIdentityTableGroup OBJECT-GROUP
			OBJECTS { saHrDeviceIdentityModelNumber, saHrDeviceIdentitySerialNumber, saHrDeviceIdentityFirmwareVersion }
			STATUS current
			DESCRIPTION 
				"The columns in the saHrDeviceIdentityTable."
			::= { saLlcGroups 8 }

		
		-- 1.3.6.1.4.1.1429.9.1.12.1.1.9
		saHrFsHealthTableGroup OBJECT-GROUP
			OBJECTS { saHrFsHealthDeletedFiles, saHrFsHealthCrossLinkedFiles, saHrFsHealthLostClusters, saHrFsHealthBadClusters }
			STATUS current
			DESCRIPTION 
				"The columns in the saHrFsHealthTable."
			::= { saLlcGroups 9 }

		
		-- 1.3.6.1.4.1.1429.9.1.12.1.2
		saLlcCompls OBJECT-IDENTITY
			STATUS current
			DESCRIPTION 
				"Compliance descriptions for the SA-HOSTRESOURCES-MIB"
			::= { saHostResourcesConf 2 }

		
		-- 1.3.6.1.4.1.1429.9.1.12.1.2.1
		saHrComplDvr MODULE-COMPLIANCE
			STATUS current
			DESCRIPTION 
				"Devices supporting multiple disk drives for DVR purposes
				support this information. In addition to the MANDATORY-GROUPS
				clause for this module, the following tables from the
				HOST-RESOURCES-MIB are also supported:
				
				hrDeviceTable
				hrStorageTable
				hrDiskStorageTable
				hrFSTable
				hrPartitionTable
				"
			MODULE -- this module
				MANDATORY-GROUPS { saHrDeviceIdentityTableGroup }
			::= { saLlcCompls 1 }

		
		-- 1.3.6.1.4.1.1429.9.1.12.2
		saHostResourcesObjs OBJECT-IDENTITY
			STATUS current
			DESCRIPTION 
				"The objects of the SA-HOSTRESOURCES-MIB module."
			::= { saHostResourcesMib 2 }

		
		-- 1.3.6.1.4.1.1429.9.1.12.2.1
		saHrSystem OBJECT-IDENTITY
			STATUS current
			DESCRIPTION 
				"Information about the host as a whole."
			::= { saHostResourcesObjs 1 }

		
		-- 1.3.6.1.4.1.1429.9.1.12.2.2
		saHrStorage OBJECT-IDENTITY
			STATUS current
			DESCRIPTION 
				"Information about storage on the host."
			::= { saHostResourcesObjs 2 }

		
		-- 1.3.6.1.4.1.1429.9.1.12.2.3
		saHrDevice OBJECT-IDENTITY
			STATUS current
			DESCRIPTION 
				"Information about devices on the host."
			::= { saHostResourcesObjs 3 }

		
		-- 1.3.6.1.4.1.1429.9.1.12.2.3.1
		saHrDeviceSleepTable OBJECT-TYPE
			SYNTAX SEQUENCE OF SaHrDeviceSleepEntry
			MAX-ACCESS not-accessible
			STATUS current
			DESCRIPTION
				"Devices capable of going into a low power or other similar
				sleep state are represented in this table."
			::= { saHrDevice 1 }

		
		-- 1.3.6.1.4.1.1429.9.1.12.2.3.1.1
		saHrDeviceSleepEntry OBJECT-TYPE
			SYNTAX SaHrDeviceSleepEntry
			MAX-ACCESS not-accessible
			STATUS current
			DESCRIPTION
				"An entry in the table."
			INDEX { hrDeviceIndex, saHrDeviceSleepTimeStamp }
			::= { saHrDeviceSleepTable 1 }

		
		SaHrDeviceSleepEntry ::=
			SEQUENCE { 
				saHrDeviceSleepTimeStamp
					TimeTicks,
				saHrDeviceSleepDuration
					TimeTicks
			 }

		-- 1.3.6.1.4.1.1429.9.1.12.2.3.1.1.1
		saHrDeviceSleepTimeStamp OBJECT-TYPE
			SYNTAX TimeTicks
			MAX-ACCESS read-only
			STATUS current
			DESCRIPTION
				"The value of sysUpTime when the device entered sleep mode."
			::= { saHrDeviceSleepEntry 1 }

		
		-- 1.3.6.1.4.1.1429.9.1.12.2.3.1.1.2
		saHrDeviceSleepDuration OBJECT-TYPE
			SYNTAX TimeTicks
			MAX-ACCESS read-only
			STATUS current
			DESCRIPTION
				"The duration of time that the device was in sleep mode. If the
				device is still in sleep mode, then this value will reflect
				the duration at the time the inquiry was made."
			::= { saHrDeviceSleepEntry 2 }

		
		-- 1.3.6.1.4.1.1429.9.1.12.2.3.2
		saHrDeviceTempTable OBJECT-TYPE
			SYNTAX SEQUENCE OF SaHrDeviceTempEntry
			MAX-ACCESS not-accessible
			STATUS current
			DESCRIPTION
				"Temperature information for devices capable of reporting temperature is included
				in this table. This table supports multiple temperature sensors per device through
				the saHrDeviceTempIndex."
			::= { saHrDevice 2 }

		
		-- 1.3.6.1.4.1.1429.9.1.12.2.3.2.1
		saHrDeviceTempEntry OBJECT-TYPE
			SYNTAX SaHrDeviceTempEntry
			MAX-ACCESS not-accessible
			STATUS current
			DESCRIPTION
				"An entry in the table."
			INDEX { hrDeviceIndex, saHrDeviceTempIndex }
			::= { saHrDeviceTempTable 1 }

		
		SaHrDeviceTempEntry ::=
			SEQUENCE { 
				saHrDeviceTempIndex
					Unsigned32,
				saHrDeviceTempDescr
					DisplayString,
				saHrDeviceTempCurrentTemp
					Integer32
			 }

		-- 1.3.6.1.4.1.1429.9.1.12.2.3.2.1.1
		saHrDeviceTempIndex OBJECT-TYPE
			SYNTAX Unsigned32
			MAX-ACCESS read-only
			STATUS current
			DESCRIPTION
				"A unique value for each temperature sensor associated with the device."
			::= { saHrDeviceTempEntry 1 }

		
-- A human-readable description of the sensor that serves to identify
-- the sensor and differentiated it from other temperature sensors
-- associated with the device.
		-- 1.3.6.1.4.1.1429.9.1.12.2.3.2.1.2
		saHrDeviceTempDescr OBJECT-TYPE
			SYNTAX DisplayString
			MAX-ACCESS read-only
			STATUS current
			DESCRIPTION
				"A human-readable description of the temperature sensor that serves
				to differentiate it from other temperature sensors associated
				with the device."
			::= { saHrDeviceTempEntry 2 }

		
		-- 1.3.6.1.4.1.1429.9.1.12.2.3.2.1.3
		saHrDeviceTempCurrentTemp OBJECT-TYPE
			SYNTAX Integer32
			UNITS "degrees Celsius"
			MAX-ACCESS read-only
			STATUS current
			DESCRIPTION
				"The current temperature in degrees Celsius."
			::= { saHrDeviceTempEntry 3 }

		
		-- 1.3.6.1.4.1.1429.9.1.12.2.3.3
		saHrDiskStorage OBJECT-IDENTITY
			STATUS current
			DESCRIPTION 
				"Information about disk storage on the host."
			::= { saHrDevice 3 }

		
		-- 1.3.6.1.4.1.1429.9.1.12.2.3.3.1
		saHrDiskStatSumTable OBJECT-TYPE
			SYNTAX SEQUENCE OF SaHrDiskStatSumEntry
			MAX-ACCESS not-accessible
			STATUS current
			DESCRIPTION
				"Summary status information regarding disk storage."
			::= { saHrDiskStorage 1 }

		
		-- 1.3.6.1.4.1.1429.9.1.12.2.3.3.1.1
		saHrDiskStatSumEntry OBJECT-TYPE
			SYNTAX SaHrDiskStatSumEntry
			MAX-ACCESS not-accessible
			STATUS current
			DESCRIPTION
				"An entry in the table."
			INDEX { hrDeviceIndex }
			::= { saHrDiskStatSumTable 1 }

		
		SaHrDiskStatSumEntry ::=
			SEQUENCE { 
				saHrDiskStatSumCumReadErrors
					Integer32,
				saHrDiskStatSumCumWriteErrors
					Integer32
			 }

		-- 1.3.6.1.4.1.1429.9.1.12.2.3.3.1.1.1
		saHrDiskStatSumCumReadErrors OBJECT-TYPE
			SYNTAX Integer32
			MAX-ACCESS read-only
			STATUS current
			DESCRIPTION
				"The number of read errors encountered with the device since
				it was installed."
			::= { saHrDiskStatSumEntry 1 }

		
		-- 1.3.6.1.4.1.1429.9.1.12.2.3.3.1.1.2
		saHrDiskStatSumCumWriteErrors OBJECT-TYPE
			SYNTAX Integer32
			MAX-ACCESS read-only
			STATUS current
			DESCRIPTION
				"The number of write errors encountered with the device since
				it was installed."
			::= { saHrDiskStatSumEntry 2 }

		
		-- 1.3.6.1.4.1.1429.9.1.12.2.3.3.2
		saHrDiskErrTable OBJECT-TYPE
			SYNTAX SEQUENCE OF SaHrDiskErrEntry
			MAX-ACCESS not-accessible
			STATUS current
			DESCRIPTION
				"Detailed information for the last N disk errors encountered since 
				the host was initialized. N is implementation dependent."
			::= { saHrDiskStorage 2 }

		
		-- 1.3.6.1.4.1.1429.9.1.12.2.3.3.2.1
		saHrDiskErrEntry OBJECT-TYPE
			SYNTAX SaHrDiskErrEntry
			MAX-ACCESS not-accessible
			STATUS current
			DESCRIPTION
				"An entry in the table."
			INDEX { hrDeviceIndex, saHrDiskErrIndex  }
			::= { saHrDiskErrTable 1 }

		
		SaHrDiskErrEntry ::=
			SEQUENCE { 
				saHrDiskErrIndex 
					Unsigned32,
				saHrDiskErrTimeStamp
					TimeTicks,
				saHrDiskErrLocation
					OCTET STRING,
				saHrDiskErrCmdSent
					OCTET STRING,
				saHrDiskErrCode
					OCTET STRING
			 }

		-- 1.3.6.1.4.1.1429.9.1.12.2.3.3.2.1.1
		saHrDiskErrIndex  OBJECT-TYPE
			SYNTAX Unsigned32
			MAX-ACCESS read-only
			STATUS current
			DESCRIPTION
				"A unique number for the entry within a particular hrDeviceIndex value."
			::= { saHrDiskErrEntry 1 }

		
		-- 1.3.6.1.4.1.1429.9.1.12.2.3.3.2.1.2
		saHrDiskErrTimeStamp OBJECT-TYPE
			SYNTAX TimeTicks
			MAX-ACCESS read-only
			STATUS current
			DESCRIPTION
				"The value of sysUpTime when the error occured."
			::= { saHrDiskErrEntry 2 }

		
		-- 1.3.6.1.4.1.1429.9.1.12.2.3.3.2.1.3
		saHrDiskErrLocation OBJECT-TYPE
			SYNTAX OCTET STRING
			MAX-ACCESS read-only
			STATUS current
			DESCRIPTION
				"The location on the disk where the error occured. Interpretation of this
				value is dependent upon the device model, version, etc."
			::= { saHrDiskErrEntry 3 }

		
		-- 1.3.6.1.4.1.1429.9.1.12.2.3.3.2.1.4
		saHrDiskErrCmdSent OBJECT-TYPE
			SYNTAX OCTET STRING
			MAX-ACCESS read-only
			STATUS current
			DESCRIPTION
				"The command that was sent which resulted in the error. If no command was sent,
				then this value is zero. Interpretation of this
				value is dependent upon the device model, version, etc."
			::= { saHrDiskErrEntry 4 }

		
		-- 1.3.6.1.4.1.1429.9.1.12.2.3.3.2.1.5
		saHrDiskErrCode OBJECT-TYPE
			SYNTAX OCTET STRING
			MAX-ACCESS read-only
			STATUS current
			DESCRIPTION
				"The error code for the error.
				Interpretation of this value is dependent upon the device model, version, etc."
			::= { saHrDiskErrEntry 5 }

		
		-- 1.3.6.1.4.1.1429.9.1.12.2.3.3.3
		saHrDiskStatSumBadSectorsTable OBJECT-TYPE
			SYNTAX SEQUENCE OF SaHrDiskStatSumBadSectorsEntry
			MAX-ACCESS not-accessible
			STATUS current
			DESCRIPTION
				"Disk Bad Sector Count"
			::= { saHrDiskStorage 3 }

		
		-- 1.3.6.1.4.1.1429.9.1.12.2.3.3.3.1
		saHrDiskStatSumBadSectorsEntry OBJECT-TYPE
			SYNTAX SaHrDiskStatSumBadSectorsEntry
			MAX-ACCESS not-accessible
			STATUS current
			DESCRIPTION
				"A row in the table."
			INDEX { hrDeviceIndex }
			::= { saHrDiskStatSumBadSectorsTable 1 }

		
		SaHrDiskStatSumBadSectorsEntry ::=
			SEQUENCE { 
				saHrDiskStatSumBadSectors
					Integer32
			 }

		-- 1.3.6.1.4.1.1429.9.1.12.2.3.3.3.1.1
		saHrDiskStatSumBadSectors OBJECT-TYPE
			SYNTAX Integer32
			MAX-ACCESS read-only
			STATUS current
			DESCRIPTION
				"Count of the bad sectors on the disk.
				A value of (-1) means this information is unknown."
			::= { saHrDiskStatSumBadSectorsEntry 1 }

		
		-- 1.3.6.1.4.1.1429.9.1.12.2.3.3.4
		saHrDiskStatSumReallocatedSectorsTable OBJECT-TYPE
			SYNTAX SEQUENCE OF SaHrDiskStatSumReallocatedSectorsEntry
			MAX-ACCESS not-accessible
			STATUS current
			DESCRIPTION
				"Reallocated Sectors Count"
			::= { saHrDiskStorage 4 }

		
		-- 1.3.6.1.4.1.1429.9.1.12.2.3.3.4.1
		saHrDiskStatSumReallocatedSectorsEntry OBJECT-TYPE
			SYNTAX SaHrDiskStatSumReallocatedSectorsEntry
			MAX-ACCESS not-accessible
			STATUS current
			DESCRIPTION
				"A row in the table."
			INDEX { hrDeviceIndex }
			::= { saHrDiskStatSumReallocatedSectorsTable 1 }

		
		SaHrDiskStatSumReallocatedSectorsEntry ::=
			SEQUENCE { 
				saHrDiskStatSumReallocatedSectors
					Integer32
			 }

		-- 1.3.6.1.4.1.1429.9.1.12.2.3.3.4.1.1
		saHrDiskStatSumReallocatedSectors OBJECT-TYPE
			SYNTAX Integer32
			MAX-ACCESS read-only
			STATUS current
			DESCRIPTION
				"Count of the reallocated sectors on the disk.
				A value of (-1) means this information is unknown."
			::= { saHrDiskStatSumReallocatedSectorsEntry 1 }

		
		-- 1.3.6.1.4.1.1429.9.1.12.2.3.3.5
		saHrDiskStatSumFailTimeTable OBJECT-TYPE
			SYNTAX SEQUENCE OF SaHrDiskStatSumFailTimeEntry
			MAX-ACCESS not-accessible
			STATUS current
			DESCRIPTION
				"Disk Failure Time"
			::= { saHrDiskStorage 5 }

		
		-- 1.3.6.1.4.1.1429.9.1.12.2.3.3.5.1
		saHrDiskStatSumFailTimeEntry OBJECT-TYPE
			SYNTAX SaHrDiskStatSumFailTimeEntry
			MAX-ACCESS not-accessible
			STATUS current
			DESCRIPTION
				"A row in the table."
			INDEX { hrDeviceIndex }
			::= { saHrDiskStatSumFailTimeTable 1 }

		
		SaHrDiskStatSumFailTimeEntry ::=
			SEQUENCE { 
				saHrDiskStatSumFailTime
					DateAndTime
			 }

		-- 1.3.6.1.4.1.1429.9.1.12.2.3.3.5.1.1
		saHrDiskStatSumFailTime OBJECT-TYPE
			SYNTAX DateAndTime
			MAX-ACCESS read-only
			STATUS current
			DESCRIPTION
				"Time the disk was declared failed.
				A value of (0) means the disk has not been declared failed."
			::= { saHrDiskStatSumFailTimeEntry 1 }

		
		-- 1.3.6.1.4.1.1429.9.1.12.2.3.4
		saHrNvm OBJECT-IDENTITY
			STATUS current
			DESCRIPTION 
				"Information about Non-Volatile Memory on the host."
			::= { saHrDevice 4 }

		
		-- 1.3.6.1.4.1.1429.9.1.12.2.3.4.1
		saHrNvmTable OBJECT-TYPE
			SYNTAX SEQUENCE OF SaHrNvmEntry
			MAX-ACCESS not-accessible
			STATUS current
			DESCRIPTION
				"Information for non-volatile memory devices."
			::= { saHrNvm 1 }

		
		-- 1.3.6.1.4.1.1429.9.1.12.2.3.4.1.1
		saHrNvmEntry OBJECT-TYPE
			SYNTAX SaHrNvmEntry
			MAX-ACCESS not-accessible
			STATUS current
			DESCRIPTION
				"An entry in the table."
			INDEX { hrDeviceIndex }
			::= { saHrNvmTable 1 }

		
		SaHrNvmEntry ::=
			SEQUENCE { 
				saHrNvmStorageIndex
					Integer32
			 }

		-- 1.3.6.1.4.1.1429.9.1.12.2.3.4.1.1.1
		saHrNvmStorageIndex OBJECT-TYPE
			SYNTAX Integer32
			MAX-ACCESS read-only
			STATUS current
			DESCRIPTION
				"The hrStorageIndex value for the hrStorageEntry corresponding to 
				this NVM device."
			::= { saHrNvmEntry 1 }

		
		-- 1.3.6.1.4.1.1429.9.1.12.2.3.4.2
		saHrNvmWriteStatTable OBJECT-TYPE
			SYNTAX SEQUENCE OF SaHrNvmWriteStatEntry
			MAX-ACCESS not-accessible
			STATUS current
			DESCRIPTION
				"NVM Write Statistics. This table provides an implementation-defined
				number of entries to track NVM write activity at certain NVM locations.
				The agent decides what addresses to report or stop reporting."
			::= { saHrNvm 2 }

		
		-- 1.3.6.1.4.1.1429.9.1.12.2.3.4.2.1
		saHrNvmWriteStatEntry OBJECT-TYPE
			SYNTAX SaHrNvmWriteStatEntry
			MAX-ACCESS not-accessible
			STATUS current
			DESCRIPTION
				"An entry in the table."
			INDEX { hrDeviceIndex, saHrNvmWriteStatAddress }
			::= { saHrNvmWriteStatTable 1 }

		
		SaHrNvmWriteStatEntry ::=
			SEQUENCE { 
				saHrNvmWriteStatAddress
					Unsigned32,
				saHrNvmWriteStatSuccesses
					Gauge32,
				saHrNvmWriteStatFailures
					Gauge32,
				saHrNvmWriteStatLastFailTime
					TimeStamp
			 }

		-- 1.3.6.1.4.1.1429.9.1.12.2.3.4.2.1.1
		saHrNvmWriteStatAddress OBJECT-TYPE
			SYNTAX Unsigned32
			MAX-ACCESS read-only
			STATUS current
			DESCRIPTION
				"The address of the NVM location being reported."
			::= { saHrNvmWriteStatEntry 1 }

		
		-- 1.3.6.1.4.1.1429.9.1.12.2.3.4.2.1.2
		saHrNvmWriteStatSuccesses OBJECT-TYPE
			SYNTAX Gauge32
			MAX-ACCESS read-only
			STATUS current
			DESCRIPTION
				"The number of successful writes for the location since host initialization. 
				Successful and un-successful attempts are included."
			::= { saHrNvmWriteStatEntry 2 }

		
		-- 1.3.6.1.4.1.1429.9.1.12.2.3.4.2.1.3
		saHrNvmWriteStatFailures OBJECT-TYPE
			SYNTAX Gauge32
			MAX-ACCESS read-only
			STATUS current
			DESCRIPTION
				"The number of writes that have failed for this location since 
				host initialization."
			::= { saHrNvmWriteStatEntry 3 }

		
		-- 1.3.6.1.4.1.1429.9.1.12.2.3.4.2.1.4
		saHrNvmWriteStatLastFailTime OBJECT-TYPE
			SYNTAX TimeStamp
			MAX-ACCESS read-only
			STATUS current
			DESCRIPTION
				"The value of sysUpTime when the last write failed for this location."
			::= { saHrNvmWriteStatEntry 4 }

		
		-- 1.3.6.1.4.1.1429.9.1.12.2.3.4.3
		saHrNvmWriteTable OBJECT-TYPE
			SYNTAX SEQUENCE OF SaHrNvmWriteEntry
			MAX-ACCESS not-accessible
			STATUS current
			DESCRIPTION
				"NVM Write Statistics Summary. This table summarizes the
				NVM writes recorded by the agent. It provides the maximum
				number of possible entries in the saHrNvmWriteStatTable and
				also the summary of successful and unsuccessful writes to 
				an NVM device."
			::= { saHrNvm 3 }

		
		-- 1.3.6.1.4.1.1429.9.1.12.2.3.4.3.1
		saHrNvmWriteEntry OBJECT-TYPE
			SYNTAX SaHrNvmWriteEntry
			MAX-ACCESS not-accessible
			STATUS current
			DESCRIPTION
				"An entry in the table."
			INDEX { hrDeviceIndex }
			::= { saHrNvmWriteTable 1 }

		
		SaHrNvmWriteEntry ::=
			SEQUENCE { 
				saHrNvmWriteCumulativeSuccesses
					Gauge32,
				saHrNvmWriteStatMaxEntries
					Gauge32,
				saHrNvmWriteStatCumulativeExcessFailures
					Gauge32
			 }

		-- 1.3.6.1.4.1.1429.9.1.12.2.3.4.3.1.1
		saHrNvmWriteCumulativeSuccesses OBJECT-TYPE
			SYNTAX Gauge32
			MAX-ACCESS read-only
			STATUS current
			DESCRIPTION
				"The total number of NVM writes that have succeeded for this device."
			::= { saHrNvmWriteEntry 1 }

		
		-- 1.3.6.1.4.1.1429.9.1.12.2.3.4.3.1.2
		saHrNvmWriteStatMaxEntries OBJECT-TYPE
			SYNTAX Gauge32
			MAX-ACCESS read-only
			STATUS current
			DESCRIPTION
				"The maximum number of entries that this device will provide 
				in saHrNvmWriteStatTable"
			::= { saHrNvmWriteEntry 2 }

		
		-- 1.3.6.1.4.1.1429.9.1.12.2.3.4.3.1.3
		saHrNvmWriteStatCumulativeExcessFailures OBJECT-TYPE
			SYNTAX Gauge32
			MAX-ACCESS read-only
			STATUS current
			DESCRIPTION
				"The total number of NVM writes that have failed in excess 
				of what is recorded in the saHrNvmWriteStatTable for this 
				device. If this is non-zero, then more locations have failed 
				than what is reported in the table.
				"
			::= { saHrNvmWriteEntry 3 }

		
		-- 1.3.6.1.4.1.1429.9.1.12.2.3.5
		saHrDeviceIdentityTable OBJECT-TYPE
			SYNTAX SEQUENCE OF SaHrDeviceIdentityEntry
			MAX-ACCESS not-accessible
			STATUS current
			DESCRIPTION
				"This table provides identification and version information for
				coresponding devices listed in the hrDeviceTable."
			::= { saHrDevice 5 }

		
		-- 1.3.6.1.4.1.1429.9.1.12.2.3.5.1
		saHrDeviceIdentityEntry OBJECT-TYPE
			SYNTAX SaHrDeviceIdentityEntry
			MAX-ACCESS not-accessible
			STATUS current
			DESCRIPTION
				"An entry in the table."
			INDEX { hrDeviceIndex }
			::= { saHrDeviceIdentityTable 1 }

		
		SaHrDeviceIdentityEntry ::=
			SEQUENCE { 
				saHrDeviceIdentityModelNumber
					DisplayString,
				saHrDeviceIdentitySerialNumber
					DisplayString,
				saHrDeviceIdentityFirmwareVersion
					DisplayString
			 }

		-- 1.3.6.1.4.1.1429.9.1.12.2.3.5.1.1
		saHrDeviceIdentityModelNumber OBJECT-TYPE
			SYNTAX DisplayString
			MAX-ACCESS read-only
			STATUS current
			DESCRIPTION
				"The model number of the device."
			::= { saHrDeviceIdentityEntry 1 }

		
		-- 1.3.6.1.4.1.1429.9.1.12.2.3.5.1.2
		saHrDeviceIdentitySerialNumber OBJECT-TYPE
			SYNTAX DisplayString
			MAX-ACCESS read-only
			STATUS current
			DESCRIPTION
				"The serial number of the device."
			::= { saHrDeviceIdentityEntry 2 }

		
		-- 1.3.6.1.4.1.1429.9.1.12.2.3.5.1.3
		saHrDeviceIdentityFirmwareVersion OBJECT-TYPE
			SYNTAX DisplayString
			MAX-ACCESS read-only
			STATUS current
			DESCRIPTION
				"The Firmware Version Number of the device."
			::= { saHrDeviceIdentityEntry 3 }

		
		-- 1.3.6.1.4.1.1429.9.1.12.2.3.6
		saHrFsTypes OBJECT-IDENTITY
			STATUS current
			DESCRIPTION 
				"This subtree provides the identity of Scientific-Atlanta
				proprietary file systems.
				
				Values in this subtree are used to identify a Scientifi-Atlanta
				file system in the hrFSType column of the hrFSTable of the HOST-RESOURCES-MIB."
			::= { saHrDevice 6 }

		
		-- 1.3.6.1.4.1.1429.9.1.12.2.3.6.1
		saHrFsItfs OBJECT-IDENTITY
			STATUS current
			DESCRIPTION 
				"The Scientific-Atlanta ITFS.
				
				This value is used to identify the ITFS as the hrFSType
				in the hrFSTable of the HOST-RESOURCES-MIB."
			::= { saHrFsTypes 1 }

		
		-- 1.3.6.1.4.1.1429.9.1.12.2.3.6.2
		saHrFsAvfs OBJECT-IDENTITY
			STATUS current
			DESCRIPTION 
				"The Scientific-Atlanta AVFS
				
				This value is used to identify the AVFS as the hrFSType
				in the hrFSTable of the HOST-RESOURCES-MIB.."
			::= { saHrFsTypes 2 }

		
		-- 1.3.6.1.4.1.1429.9.1.12.2.3.7
		saHrFsHealthTable OBJECT-TYPE
			SYNTAX SEQUENCE OF SaHrFsHealthEntry
			MAX-ACCESS not-accessible
			STATUS current
			DESCRIPTION
				"File system health details.
				
				Coresponds to an entry in hrFSEntry in the 
				HOST-RESOURCES-MIB."
			::= { saHrDevice 7 }

		
		-- 1.3.6.1.4.1.1429.9.1.12.2.3.7.1
		saHrFsHealthEntry OBJECT-TYPE
			SYNTAX SaHrFsHealthEntry
			MAX-ACCESS not-accessible
			STATUS current
			DESCRIPTION
				"An entry in the table.
				
				Coresponds to an entry in hrFSEntry in the 
				HOST-RESOURCES-MIB."
			AUGMENTS { hrFSEntry }
			::= { saHrFsHealthTable 1 }

		
		SaHrFsHealthEntry ::=
			SEQUENCE { 
				saHrFsHealthDeletedFiles
					Unsigned32,
				saHrFsHealthCrossLinkedFiles
					Unsigned32,
				saHrFsHealthLostClusters
					Unsigned32,
				saHrFsHealthBadClusters
					Unsigned32
			 }

		-- 1.3.6.1.4.1.1429.9.1.12.2.3.7.1.1
		saHrFsHealthDeletedFiles OBJECT-TYPE
			SYNTAX Unsigned32
			MAX-ACCESS read-only
			STATUS current
			DESCRIPTION
				"Number of corrupted files found the last time this kind of
				check was executed."
			::= { saHrFsHealthEntry 1 }

		
		-- 1.3.6.1.4.1.1429.9.1.12.2.3.7.1.2
		saHrFsHealthCrossLinkedFiles OBJECT-TYPE
			SYNTAX Unsigned32
			MAX-ACCESS read-only
			STATUS current
			DESCRIPTION
				"The number of cross-linked files found the last time this kind of
				check was executed."
			::= { saHrFsHealthEntry 2 }

		
		-- 1.3.6.1.4.1.1429.9.1.12.2.3.7.1.3
		saHrFsHealthLostClusters OBJECT-TYPE
			SYNTAX Unsigned32
			MAX-ACCESS read-only
			STATUS current
			DESCRIPTION
				"Number of lost clusters found the last time this kind of check 
				was executed."
			::= { saHrFsHealthEntry 3 }

		
		-- 1.3.6.1.4.1.1429.9.1.12.2.3.7.1.4
		saHrFsHealthBadClusters OBJECT-TYPE
			SYNTAX Unsigned32
			MAX-ACCESS read-only
			STATUS current
			DESCRIPTION
				"The number of bad clusters identified by the file system."
			::= { saHrFsHealthEntry 4 }

		
		-- 1.3.6.1.4.1.1429.9.1.12.2.3.8
		saHrProcessor OBJECT-IDENTITY
			STATUS current
			DESCRIPTION 
				"Processor Device Information"
			::= { saHrDevice 8 }

		
		-- 1.3.6.1.4.1.1429.9.1.12.2.3.8.1
		saHrProcessorThreadReadyTable OBJECT-TYPE
			SYNTAX SEQUENCE OF SaHrProcessorThreadReadyEntry
			MAX-ACCESS not-accessible
			STATUS current
			DESCRIPTION
				"Information regarding the number of threads ready to run.
				
				
				If this entry is associated with a specific hrDeviceEntry and/or
				hrProcessorEntry from the HOST-RESOURCES-MIB, then saHrProcessorThreadReadyIndex
				must match the appropriate hrDeviceIndex."
			::= { saHrProcessor 1 }

		
		-- 1.3.6.1.4.1.1429.9.1.12.2.3.8.1.1
		saHrProcessorThreadReadyEntry OBJECT-TYPE
			SYNTAX SaHrProcessorThreadReadyEntry
			MAX-ACCESS not-accessible
			STATUS current
			DESCRIPTION
				"A row in the table.
				
				If this entry is associated with a specific hrDeviceEntry and/or
				hrProcessorEntry from the HOST-RESOURCES-MIB, then saHrProcessorThreadReadyIndex
				must match the appropriate hrDeviceIndex."
			INDEX { saHrProcessorThreadReadyIndex }
			::= { saHrProcessorThreadReadyTable 1 }

		
		SaHrProcessorThreadReadyEntry ::=
			SEQUENCE { 
				saHrProcessorThreadReadyIndex
					Integer32,
				saHrProcessorThreadReadyAvgOneMin
					Unsigned32,
				saHrProcessorThreadReadyAvgFiveMin
					Unsigned32,
				saHrProcessorThreadReadyAvgFifteenMin
					Unsigned32
			 }

		-- 1.3.6.1.4.1.1429.9.1.12.2.3.8.1.1.1
		saHrProcessorThreadReadyIndex OBJECT-TYPE
			SYNTAX Integer32 (1..2147483647)
			MAX-ACCESS not-accessible
			STATUS current
			DESCRIPTION
				"The index of the processor for which this entry applies.
				
				If this entry is associated with a specific hrDeviceEntry and/or
				hrProcessorEntry from the HOST-RESOURCES-MIB, then saHrProcessorThreadReadyIndex
				must match the appropriate hrDeviceIndex."
			::= { saHrProcessorThreadReadyEntry 1 }

		
		-- 1.3.6.1.4.1.1429.9.1.12.2.3.8.1.1.2
		saHrProcessorThreadReadyAvgOneMin OBJECT-TYPE
			SYNTAX Unsigned32
			UNITS "0.001"
			MAX-ACCESS read-only
			STATUS current
			DESCRIPTION
				"The average number of threads ready to run over the past minute.
				The LS Bit is 0.001."
			::= { saHrProcessorThreadReadyEntry 2 }

		
		-- 1.3.6.1.4.1.1429.9.1.12.2.3.8.1.1.3
		saHrProcessorThreadReadyAvgFiveMin OBJECT-TYPE
			SYNTAX Unsigned32
			UNITS "0.001"
			MAX-ACCESS read-only
			STATUS current
			DESCRIPTION
				"The average number of threads ready to run over the past five minutes.
				The LS Bit is 0.001."
			::= { saHrProcessorThreadReadyEntry 3 }

		
		-- 1.3.6.1.4.1.1429.9.1.12.2.3.8.1.1.4
		saHrProcessorThreadReadyAvgFifteenMin OBJECT-TYPE
			SYNTAX Unsigned32
			UNITS "0.001"
			MAX-ACCESS read-only
			STATUS current
			DESCRIPTION
				"The average number of threads ready to run over the past fifteen minutes.
				The LS Bit is 0.001."
			::= { saHrProcessorThreadReadyEntry 4 }

		
		-- 1.3.6.1.4.1.1429.9.1.12.3
		saHostResourcesEvents OBJECT-IDENTITY
			STATUS current
			DESCRIPTION 
				"Events associated with the SA-HOSTRESOURCES-MIB module"
			::= { saHostResourcesMib 3 }

		
		-- 1.3.6.1.4.1.1429.9.1.12.3.0
		saHostResourcesEventsV2 OBJECT-IDENTITY
			STATUS current
			DESCRIPTION 
				"Dummy node needed for V1 compatability."
			::= { saHostResourcesEvents 0 }

		
	
	END

--
-- SA-HOSTRESOURCES-MIB.mib
--
