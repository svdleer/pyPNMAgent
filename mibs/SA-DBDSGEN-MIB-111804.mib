--
-- SA-DBDSGEN-MIB.my
-- MIB generated by MG-SOFT Visual MIB Builder Version 4.0 Build 349
-- Wednesday, October 26, 2005 at 09:46:42
--

--  SA-DBDSGEN-MIB.my
-- MIB generated by MG-SOFT Visual MIB Builder Version 4.0 Build 349
-- Thursday, November 18, 2004 at 12:18:18
-- 
-- Revision 1 : Revision Control
-- Date: Tuesday, July 22, 2003 at 10:04:01
-- Comment:
-- Putting MIB under official revision
-- control.
-- 
-- Revision 2 : Revision 2
-- Date: Tuesday, September 23, 2003 at 16:22:07
-- Comment:
-- Added nodes for the following MIB
-- modules: SA-LIBERATE-MIB,
-- SA-NAGRA-MIB, SA-DVB-MIB,
-- SA-HOSTRESOURCES-MIB.
-- 
-- Revision 3 : Revision 3
-- Date: Tuesday, October 07, 2003 at 11:02:25
-- Comment:
-- Added node for sa1394Mib module.
-- 
-- Revision 4 : Copy Protection
-- Date: Friday, April 30, 2004 at 14:55:42
-- Comment:
-- Added copy protection node.
-- 
-- Revision 5 : Revision 5 - DSG 
-- Date: Thursday, November 18, 2004 at 12:16:00
-- Comment:
-- Added DSG MIB node: saDbdsGen.saDsgMib
-- 
--  SA-DBDSGEN-MIB.my
-- MIB generated by MG-SOFT Visual MIB Builder Version 4.0 Build 349
-- Tuesday, July 22, 2003 at 09:46:08
-- 
-- Revision 1 : Initial revision
-- Date: Tuesday, July 08, 2003 at 14:11:30
-- Comment:
-- 
-- Revision 2 : Revision 2
-- Date: Tuesday, July 08, 2003 at 14:13:02
-- Comment:
-- Added saDbdsGen.saLlcMib and 
-- saDbdsGen.saIhpMib nodes for MIB
-- modules SA-LLC-MIB and SA-IHP-MIB
-- respectively.
-- 
-- Revision 3 : For MPEG
-- Date: Tuesday, July 15, 2003 at 17:51:32
-- Comment:
-- Added MPEG node.
-- 
-- Revision 4 : Overlay, In Hone, & QAM Tx 
-- Date: Tuesday, July 22, 2003 at 09:32:44
-- Comment:
-- Added nodes to saGeneric.saDbdsGen
-- for SA-CAOVERLAY-MIB, SA-INHOME-MIB,
-- and SA-QAMTX-MIB.
-- 

	SA-DBDSGEN-MIB DEFINITIONS ::= BEGIN
 
		IMPORTS
			saModules, saDbdsGen			
				FROM SCIATL-COMMON-MIB			
			MODULE-IDENTITY, OBJECT-IDENTITY			
				FROM SNMPv2-SMI;
	
	
--  July 22, 2003 at 09:32 GMT
-- July 15, 2003 at 17:51 GMT
-- July 08, 2003 at 14:13 GMT
-- July 08, 2003 at 14:11 GMT
-- 
-- 1.3.6.1.4.1.1429.7.1.5
-- November 18, 2004 at 12:16 GMT
-- November 18, 2004 at 12:16 GMT
-- April 30, 2004 at 14:55 GMT
-- October 07, 2003 at 11:02 GMT
-- September 23, 2003 at 16:22 GMT
-- July 22, 2003 at 10:04 GMT
-- July 08, 2003 at 14:11 GMT
-- July 08, 2003 at 14:13 GMT
-- July 15, 2003 at 17:51 GMT
-- July 22, 2003 at 09:32 GMT
		-- 1.3.6.1.4.1.1429.7.1.5
		saDbdsGenMibModule MODULE-IDENTITY 
			LAST-UPDATED "200411181216Z"		-- November 18, 2004 at 12:16 GMT
			ORGANIZATION 
				"Scientific-Atlanta"
			CONTACT-INFO 
				"Contact-info."
			DESCRIPTION 
				"The initial revision of this module."
			REVISION "200307220932Z"		-- July 22, 2003 at 09:32 GMT
			DESCRIPTION 
				"Added nodes to saGeneric.saDbdsGen
				for SA-CAOVERLAY-MIB, SA-INHOME-MIB,
				and SA-QAMTX-MIB."
			REVISION "200307151751Z"		-- July 15, 2003 at 17:51 GMT
			DESCRIPTION 
				"Added MPEG node."
			REVISION "373607081413Z"		-- July 08, 3736 at 14:13 GMT
			DESCRIPTION 
				"Added IHP and LLC nodes."
			REVISION "200307081411Z"		-- July 08, 2003 at 14:11 GMT
			DESCRIPTION 
				"Fixed OID problems."
			REVISION "200307221004Z"		-- July 22, 2003 at 10:04 GMT
			DESCRIPTION 
				"Placing MIB under official revision
				control."
			REVISION "200309231622Z"		-- September 23, 2003 at 16:22 GMT
			DESCRIPTION 
				"Added nodes for the following MIB
				modules: SA-LIBERATE-MIB,
				SA-NAGRA-MIB, SA-DVB-MIB,
				SA-HOSTRESOURCES-MIB."
			REVISION "200310071102Z"		-- October 07, 2003 at 11:02 GMT
			DESCRIPTION 
				"Added node for sa1394Mib module."
			REVISION "200404301455Z"		-- April 30, 2004 at 14:55 GMT
			DESCRIPTION 
				"Added copy protection node."
			REVISION "200411181216Z"		-- November 18, 2004 at 12:16 GMT
			DESCRIPTION 
				"Added DSG MIB node: saDbdsGen.saDsgMib"
			::= { saModules 5 }

		
	
--
-- Node definitions
--
	
--  Node definitions
-- 
-- Node definitions
-- 
-- Node definitions
-- 
-- 1.3.6.1.4.1.1429.1.1.1
-- 1.3.6.1.4.1.1429.9.1.1
-- 1.3.6.1.4.1.1429.9.1.1
		-- 1.3.6.1.4.1.1429.9.1.1
		saPowerkeyMib OBJECT-IDENTITY
			STATUS current
			DESCRIPTION 
				"The PowerKey MIB."
			::= { saDbdsGen 1 }

		
--    1.3.6.1.4.1.1429.1.1.2
-- 1.3.6.1.4.1.1429.9.1.2
-- 1.3.6.1.4.1.1429.9.1.2
		-- 1.3.6.1.4.1.1429.9.1.2
		saNdsMib OBJECT-IDENTITY
			STATUS current
			DESCRIPTION 
				"The NDS MIB."
			::= { saDbdsGen 2 }

		
--   1.3.6.1.4.1.1429.9.1.3
-- 1.3.6.1.4.1.1429.9.1.3
		-- 1.3.6.1.4.1.1429.9.1.3
		saLlcMib OBJECT-IDENTITY
			STATUS current
			DESCRIPTION 
				"The S-A MIB for IEEE 802.2 LLC."
			::= { saDbdsGen 3 }

		
--   1.3.6.1.4.1.1429.9.1.4
-- 1.3.6.1.4.1.1429.9.1.4
		-- 1.3.6.1.4.1.1429.9.1.4
		saIhpMib OBJECT-IDENTITY
			STATUS current
			DESCRIPTION 
				"The Scientific-Atlanta MIB for the In-Home Protocol."
			::= { saDbdsGen 4 }

		
--   1.3.6.1.4.1.1429.9.1.5
-- 1.3.6.1.4.1.1429.9.1.5
		-- 1.3.6.1.4.1.1429.9.1.5
		saMpegMib OBJECT-IDENTITY
			STATUS current
			DESCRIPTION 
				"The Scientific-Atlanta MIB for MPEG-2."
			::= { saDbdsGen 5 }

		
--   1.3.6.1.4.1.1429.9.1.6
-- 1.3.6.1.4.1.1429.9.1.6
		-- 1.3.6.1.4.1.1429.9.1.6
		saCaOverlayMib OBJECT-IDENTITY
			STATUS current
			DESCRIPTION 
				"The S-A MIB for DBDS Network Overlay (DNO), a.k.a
				CA Overlay."
			::= { saDbdsGen 6 }

		
--   1.3.6.1.4.1.1429.9.1.7
-- 1.3.6.1.4.1.1429.9.1.7
		-- 1.3.6.1.4.1.1429.9.1.7
		saInHomeMib OBJECT-IDENTITY
			STATUS current
			DESCRIPTION 
				"The S-A MIB for In-Home Networking and associated
				infrastructure."
			::= { saDbdsGen 7 }

		
--   1.3.6.1.4.1.1429.9.1.8
-- 1.3.6.1.4.1.1429.9.1.8
		-- 1.3.6.1.4.1.1429.9.1.8
		saQamtxMib OBJECT-IDENTITY
			STATUS current
			DESCRIPTION 
				"The S-A MIB for QAM Transmitters."
			::= { saDbdsGen 8 }

		
--  1.3.6.1.4.1.1429.9.1.9
		-- 1.3.6.1.4.1.1429.9.1.9
		saLiberateMib OBJECT-IDENTITY
			STATUS current
			DESCRIPTION 
				"The Scientific-Atlanta MIB module for tracking Liberate
				application information.				
				"
			::= { saDbdsGen 9 }

		
--  1.3.6.1.4.1.1429.9.1.10
		-- 1.3.6.1.4.1.1429.9.1.10
		saNagraMib OBJECT-IDENTITY
			STATUS current
			DESCRIPTION 
				"The Scientific-Atlanta MIB module for tracking 
				Nagra information."
			::= { saDbdsGen 10 }

		
--  1.3.6.1.4.1.1429.9.1.11
		-- 1.3.6.1.4.1.1429.9.1.11
		saDvbMib OBJECT-IDENTITY
			STATUS current
			DESCRIPTION 
				"The Scientific-Atlanta MIB module for tracking 
				DVB information."
			::= { saDbdsGen 11 }

		
--  1.3.6.1.4.1.1429.9.1.12
		-- 1.3.6.1.4.1.1429.9.1.12
		saHostResourcesMib OBJECT-IDENTITY
			STATUS current
			DESCRIPTION 
				"The S-A Host Resources MIB."
			::= { saDbdsGen 12 }

		
--  1.3.6.1.4.1.1429.9.1.13
		-- 1.3.6.1.4.1.1429.9.1.13
		sa1394Mib OBJECT-IDENTITY
			STATUS current
			DESCRIPTION 
				"The Scientific-Atlanta 1394 MIB."
			::= { saDbdsGen 13 }

		
--  1.3.6.1.4.1.1429.9.1.14
		-- 1.3.6.1.4.1.1429.9.1.14
		saCProtectMib OBJECT-IDENTITY
			STATUS current
			DESCRIPTION 
				"Mib module for Copy Protection."
			::= { saDbdsGen 14 }

		
--  1.3.6.1.4.1.1429.9.1.15
		-- 1.3.6.1.4.1.1429.9.1.15
		saDsgMib OBJECT-IDENTITY
			STATUS current
			DESCRIPTION 
				"The Scientific-Atlanta proprietary MIB for DOCSIS Settop Gateway information."
			::= { saDbdsGen 15 }

		
		-- 1.3.6.1.4.1.1429.9.1.16
		saJclExtendedMib OBJECT-IDENTITY
			STATUS current
			DESCRIPTION 
				"The JCL extended MIB."
			::= { saDbdsGen 16 }

		
		-- 1.3.6.1.4.1.1429.9.1.17
		saSff8035Mib OBJECT-IDENTITY
			STATUS current
			DESCRIPTION 
				"The S-A MIB for Small Form Factor Committee
				Specification for S.M.A.R.T (SFF-8035i)."
			::= { saDbdsGen 17 }

		
	
	END

--
-- SA-DBDSGEN-MIB.my
--
