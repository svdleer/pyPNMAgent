BCSSIMULCRYPTSCS-MIB DEFINITIONS ::= BEGIN

IMPORTS
        MODULE-IDENTITY,
        IpAddress,
        OBJECT-TYPE,
        Unsigned32,
        Integer32
                FROM SNMPv2-SMI
        bcs
                FROM BCS-IDENT-MIB;
 

bcsSimulcryptScs     MODULE-IDENTITY
        LAST-UPDATED "200602090000Z"

        ORGANIZATION "Motorola Connected Home Solutions"
        CONTACT-INFO "Motorola Technical Response Center
                      Inside USA     1-888-944-HELP (1-888-944-4357)
                      Outside USA    1-215-323-0044
                      TRC Hours:
                      Monday through Friday 8am - 7pm Eastern Standard Time
                      Saturdays            10am - 5pm Eastern Standard Time"

        DESCRIPTION  "The Simulcrypt SCS MIB module for Motorola BCS products."

        REVISION     "200602090000Z"
        DESCRIPTION  "Version 1.2; February 9, 2006
                      - Updated Contact Information."

        REVISION     "200408090000Z"
        DESCRIPTION
                     "Version 1.1:

                      August 09, 2004
                      - Changed description of bcsSimScsAccessCriteriaSource.

                      July 27, 2004
                      - Changed enumerations for bcsSimScsAccessCriteriaSource."

        REVISION     "200401230000Z"
        DESCRIPTION
                     "Version 1.0:

                      June 24, 2003
                      - Initial Revision."

         ::= {bcs 7}


-- SIMULCRYPT SCS MIB STRUCTURE

   bcsSimScsConfig                                        OBJECT IDENTIFIER ::= {bcsSimulcryptScs 1}
      bcsSimScsConfigGeneral                              OBJECT IDENTIFIER ::= {bcsSimScsConfig 1}
--       bcsSimScsNetworkId                                                     {bcsSimScsConfigGeneral 1}
--       bcsSimScsMaxNetworkDelay                                               {bcsSimScsConfigGeneral 2}
--       bcsSimScsNominalCryptoPeriod                                           {bcsSimScsConfigGeneral 3}
--       bcsSimScsAccessCriteriaSource                                          {bcsSimScsConfigGeneral 4}
--       bcsSimScsEcmgTimeout                                                   {bcsSimScsConfigGeneral 5}
--       bcsSimScsEcmIdInitial                                                  {bcsSimScsConfigGeneral 6}
--    bcsSimScsEcmgConnectionTable                                              {bcsSimScsConfig 2}
--       bcsSimScsEcmgConnectionEntry                                           {bcsSimScsEcmgConnectionTable 1}
--          bcsSimScsEcmgConnectIndex                                           {bcsSimScsEcmgConnectionEntry 1}
--          bcsSimScsEcmgConnectSuperCasId                                      {bcsSimScsEcmgConnectionEntry 2}
--          bcsSimScsEcmgConnectIpAddr                                          {bcsSimScsEcmgConnectionEntry 3}
--          bcsSimScsEcmgConnectPort                                            {bcsSimScsEcmgConnectionEntry 4}
   bcsSimScsStatus                                        OBJECT IDENTIFIER ::= {bcsSimulcryptScs 2}
      bcsSimScsStatusGeneral                              OBJECT IDENTIFIER ::= {bcsSimScsStatus 1}
--       bcsSimScsMibSupportStatus                                              {bcsSimScsStatusGeneral 1}
--       bcsSimScsMaxEcmg                                                       {bcsSimScsStatusGeneral 2}
--       bcsSimScsMaxPrograms                                                   {bcsSimScsStatusGeneral 3}
--       bcsSimScsMaxProgramEcmg                                                {bcsSimScsStatusGeneral 4}
--    bcsSimScsEcmgStatusTable                                                  {bcsSimScsStatus 2}
--       bcsSimScsEcmgStatusEntry                                               {bcsSimScsEcmgStatusTable 1}
--          bcsSimScsEcmgStatusIndex                                            {bcsSimScsEcmgStatusEntry 1}
--          bcsSimScsEcmgTcpState                                               {bcsSimScsEcmgStatusEntry 2}
--          bcsSimScsEcmgChannelId                                              {bcsSimScsEcmgStatusEntry 3}
--          bcsSimScsEcmgChannelState                                           {bcsSimScsEcmgStatusEntry 4}
--          bcsSimScsEcmgSuperCasId                                             {bcsSimScsEcmgStatusEntry 5}
--    bcsSimScsProgramTable                                                     {bcsSimScsStatus 3}
--       bcsSimScsProgramEntry                                                  {bcsSimScsProgramTable 1}
--          bcsSimScsProgramIndex                                               {bcsSimScsProgramEntry 1}
--          bcsSimScsProgramEcmgIndex                                           {bcsSimScsProgramEntry 2}
--          bcsSimScsProgramState                                               {bcsSimScsProgramEntry 3}
--          bcsSimScsProgramCryptoPeriod                                        {bcsSimScsProgramEntry 4}
--          bcsSimScsProgramChannelId                                           {bcsSimScsProgramEntry 5}
--          bcsSimScsProgramEcmgSuperCasId                                      {bcsSimScsProgramEntry 6}
--          bcsSimScsProgramEcmgStreamState                                     {bcsSimScsProgramEntry 7}

EnableDisableTYPE ::=  INTEGER
   {
    disabled (1),
    enabled  (2)
   }


-- ------------------------------------------------------------------------------
--
-- bcsSimulcryptScs
--
-- bcsSimScsConfig
--
-- bcsSimScsConfigGeneral
--

bcsSimScsNetworkId OBJECT-TYPE
    SYNTAX Unsigned32
    MAX-ACCESS read-write
    STATUS current
    DESCRIPTION
        "This parameter specifies the network ID used for this
         Simulcrypt system.  The network ID is a Simulcrypt system
         parameter, please see Simulcrypt system specifications
         for a more detailed explanation.

         SEM Note:
         Once written, a save must be performed via the semSaveConfig
         parameter and the SEM must be rebooted for the change to take
         effect."
::= { bcsSimScsConfigGeneral 1 }

bcsSimScsMaxNetworkDelay OBJECT-TYPE
    SYNTAX Unsigned32
    MAX-ACCESS read-write
    STATUS current
    DESCRIPTION
        "Worst case propagation delay, in milliseconds, introduced by
         network topology.  Will be factored into negotiations of the
         actual Simulcrypt crypto-period.

         SEM Note:
         Once written, a save must be performed via the semSaveConfig
         parameter and the SEM must be rebooted for the change to take
         effect."
::= { bcsSimScsConfigGeneral 2 }

bcsSimScsNominalCryptoPeriod OBJECT-TYPE
    SYNTAX Unsigned32
    MAX-ACCESS read-write
    STATUS current
    DESCRIPTION
        "This value specifies the nominal crypto-period in seconds.
         This value is used as a target for this device during crypto-
         period negotiations.  The actual negotiated crypto-period may
         be equal to or greater than this value.

         SEM Note:
         Once written, a save must be performed via the semSaveConfig
         parameter and the SEM must be rebooted for the change to take
         effect."
::= { bcsSimScsConfigGeneral 3 }

bcsSimScsAccessCriteriaSource OBJECT-TYPE
    SYNTAX INTEGER
       {
        dtviaFixedAc (1),
        noAc         (2)
--      internal     (3),
--      motorola     (4),
--      eis          (5),
       }
    MAX-ACCESS read-write
    STATUS current
    DESCRIPTION
        "This value specifies which vendor will provide the access
         criteria information.

         SEM Note:
         Once written, a save must be performed via the semSaveConfig
         parameter and the SEM must be rebooted for the change to take
         effect."
::= { bcsSimScsConfigGeneral 4 }

bcsSimScsEcmgTimeout OBJECT-TYPE
    SYNTAX Unsigned32
    MAX-ACCESS read-write
    STATUS current
    DESCRIPTION
        "This parameter specifies how long the SCS should wait for a
         response from the ECMG.  This value is specified in seconds.

         SEM Note:
         Once written, a save must be performed via the semSaveConfig
         parameter and the SEM must be rebooted for the change to take
         effect."
::= { bcsSimScsConfigGeneral 5 }

bcsSimScsEcmIdInitial OBJECT-TYPE
    SYNTAX Unsigned32
    MAX-ACCESS read-write
    STATUS current
    DESCRIPTION
        "Each ECM ID and Super CAS ID combination in the Simulcrypt
         system must be globally unique.  To simplify configuration,
         each SCS is given a starting ECM ID to assign to the first
         ECM stream it creates.  The number is incremented as new
         ECM streams are created. Each SCS must be configured with a
         different value.  The initial values should be spaced 
         sufficiently to prevent overlapping.  Recommended spacing
         is 128.

         SEM Note:
         Once written, a save must be performed via the semSaveConfig
         parameter and the SEM must be rebooted for the change to take
         effect."
::= { bcsSimScsConfigGeneral 6 }


-- ------------------------------------------------------------------------------
--
-- bcsSimScsEcmgConnectionTable
--

bcsSimScsEcmgConnectionTable OBJECT-TYPE
    SYNTAX SEQUENCE OF BcsSimScsEcmgConnectionEntry
    MAX-ACCESS not-accessible
    STATUS current
    DESCRIPTION
        "This table persists the Simulcrypt SCS to ECMG connections
         or channels.  The device will send Simulcrypt control words to
         a maximum of bcsSimScsMaxEcmg."
::= { bcsSimScsConfig 2 }

bcsSimScsEcmgConnectionEntry OBJECT-TYPE
    SYNTAX BcsSimScsEcmgConnectionEntry
    MAX-ACCESS not-accessible
    STATUS current
    DESCRIPTION
        "A single entry in the bcsSimScsEcmgConnectionTable table."
    INDEX { bcsSimScsEcmgConnectIndex }
::= { bcsSimScsEcmgConnectionTable 1}

BcsSimScsEcmgConnectionEntry ::= SEQUENCE
    {
     bcsSimScsEcmgConnectIndex       Integer32,
     bcsSimScsEcmgConnectEnabled     EnableDisableTYPE,
     bcsSimScsEcmgConnectSuperCasId  Unsigned32,
     bcsSimScsEcmgConnectIpAddr      IpAddress,
     bcsSimScsEcmgConnectPort        Integer32
    }

bcsSimScsEcmgConnectIndex OBJECT-TYPE
    SYNTAX Integer32
    MAX-ACCESS not-accessible
    STATUS current
    DESCRIPTION
        "The Simulcrypt ECMG Connection table index."
::= { bcsSimScsEcmgConnectionEntry 1 }

bcsSimScsEcmgConnectEnabled OBJECT-TYPE
    SYNTAX EnableDisableTYPE
    MAX-ACCESS read-write
    STATUS current
    DESCRIPTION
        "Each row in the bcsSimScsEcmgConnectionTable represents a
         potential SCS<=>ECMG connection that will be attempted 
         during simulcrypt SCS initialization.

         This setting controls whether or not the attempt is made.
         This setting has two legal settings:
         disabled (1)  <= The connection will be attempted.
         enabled  (2)  <= The connection will not be attempted.

         Once written, a save must be performed via the semSaveConfig
         parameter and the SEM must be rebooted for the change to take effect."
 ::= { bcsSimScsEcmgConnectionEntry  2}


bcsSimScsEcmgConnectSuperCasId OBJECT-TYPE
    SYNTAX Unsigned32
    MAX-ACCESS read-write
    STATUS current
    DESCRIPTION
        "The Super CAS ID of the ECMG that will be connected to by
         the Simulcrypt SCS. The Super CAS ID is the 32 bit concatenation
         of the CAS ID and the Sub CAS ID. The CAS ID identifies the
         Conditional Access provider. It supplies the
         upper 16 bits of the SuperCAS ID. The Sub CAS ID identifies
         instances of a provider's ECMGs on the Simulcrypt network.
         It supplies the lower 16 bits of the Super CAS ID.
         Each ECM ID and SuperCAS ID combination in the Simulcrypt
         system must be globally unique.

         SEM Note:
         Once written, a save must be performed via the semSaveConfig
         parameter and the SEM must be rebooted for the change to take
         effect."
::= { bcsSimScsEcmgConnectionEntry 3 }

bcsSimScsEcmgConnectIpAddr OBJECT-TYPE
    SYNTAX IpAddress
    MAX-ACCESS read-write
    STATUS current
    DESCRIPTION
        "The IP address that the ECMG is listening on.
         Used to open a socket between the SCS and the ECMG.

         SEM Note:
         Once written, a save must be performed via the semSaveConfig
         parameter and the SEM must be rebooted for the change to take
         effect."
::= { bcsSimScsEcmgConnectionEntry 4 }

bcsSimScsEcmgConnectPort OBJECT-TYPE
    SYNTAX Integer32
    MAX-ACCESS read-write
    STATUS current
    DESCRIPTION
        "The remote port that the ECMG is listening on.
         Used to open a socket between the SCS and the ECMG.

         SEM Note:
         Once written, a save must be performed via the semSaveConfig
         parameter and the SEM must be rebooted for the change to take
         effect."
::= { bcsSimScsEcmgConnectionEntry 5 }


-- ------------------------------------------------------------------------------
--
-- bcsSimScsStatus
--
-- bcsSimScsStatusGeneral
--

bcsSimScsMibSupportStatus OBJECT-TYPE
    SYNTAX INTEGER
       {
        notCapable (1),
        capable    (2),
        enabled    (3)
       }
    MAX-ACCESS read-only
    STATUS current
    DESCRIPTION
        "Indicates whether the device is capable of supporting and/or
         enabled to support the functionality of the bcsSimulcryptScs MIB."
::= { bcsSimScsStatusGeneral 1 }

bcsSimScsMaxEcmg OBJECT-TYPE
    SYNTAX Unsigned32
    MAX-ACCESS read-only
    STATUS current
    DESCRIPTION
        "The maximum number of ECMGs this device can support."
::= { bcsSimScsStatusGeneral 2 }

bcsSimScsMaxPrograms OBJECT-TYPE
    SYNTAX Unsigned32
    MAX-ACCESS read-only
    STATUS current
    DESCRIPTION
        "The maximum number of programs this device can support."
::= { bcsSimScsStatusGeneral 3 }

bcsSimScsMaxProgramEcmg OBJECT-TYPE
    SYNTAX Unsigned32
    MAX-ACCESS read-only
    STATUS current
    DESCRIPTION
        "The maximum number of ECMGs that can be associated with a
         program in this device."
::= { bcsSimScsStatusGeneral 4 }


-- ------------------------------------------------------------------------------
--
-- bcsSimScsEcmgStatusTable
--

bcsSimScsEcmgStatusTable OBJECT-TYPE
    SYNTAX SEQUENCE OF BcsSimScsEcmgStatusEntry
    MAX-ACCESS not-accessible
    STATUS current
    DESCRIPTION
        "It contains status information for the SCS to ECMG connections.
         There can be up to bcsSimScsMaxEcmg active SCS to ECMG
         connections at a time."
::= { bcsSimScsStatus 2 }

bcsSimScsEcmgStatusEntry OBJECT-TYPE
    SYNTAX BcsSimScsEcmgStatusEntry
    MAX-ACCESS not-accessible
    STATUS current
    DESCRIPTION
        "A single entry in the bcsSimScsEcmgStatusTable table."
    INDEX { bcsSimScsEcmgStatusIndex }
::= { bcsSimScsEcmgStatusTable 1 }

BcsSimScsEcmgStatusEntry ::= SEQUENCE
    {
     bcsSimScsEcmgStatusIndex   Integer32,
     bcsSimScsEcmgTcpState      INTEGER,
     bcsSimScsEcmgChannelId     Unsigned32,
     bcsSimScsEcmgChannelState  INTEGER,
     bcsSimScsEcmgSuperCasId    Unsigned32
    }

bcsSimScsEcmgStatusIndex OBJECT-TYPE
    SYNTAX Integer32
    MAX-ACCESS not-accessible
    STATUS current
    DESCRIPTION
       "This index is used to traverse the bcsSimScsEcmgTable table.
        The index varies from 1..bcsSimScsMaxEcmg. In the event
        that some connections are not active this will be designated
        by the value of bcsSimScsEcmgChannelState."
::= { bcsSimScsEcmgStatusEntry 1 }

bcsSimScsEcmgTcpState OBJECT-TYPE
    SYNTAX INTEGER
        {
         open   (1),
         closed (2),
         error  (3)
        }
    MAX-ACCESS read-only
    STATUS current
    DESCRIPTION
       "This column specifies TCP connection state of this
        SCS <==> ECMG connection."
::= { bcsSimScsEcmgStatusEntry 2 }

bcsSimScsEcmgChannelId OBJECT-TYPE
    SYNTAX Unsigned32
    MAX-ACCESS read-only
    STATUS current
    DESCRIPTION
       "This column specifies channel ID."
::= { bcsSimScsEcmgStatusEntry 3 }

bcsSimScsEcmgChannelState OBJECT-TYPE
    SYNTAX INTEGER
        {
         open    (1),
         notOpen (2),
         error   (3)
        }
    MAX-ACCESS read-only
    STATUS current
    DESCRIPTION
       "This column specifies ECMG channel state of this
        SCS <==> ECMG connection."
::= { bcsSimScsEcmgStatusEntry 4 }

bcsSimScsEcmgSuperCasId OBJECT-TYPE
    SYNTAX Unsigned32
    MAX-ACCESS read-only
    STATUS current
    DESCRIPTION
       "This column specifies super CAS Id of the ECMG that
        the SCS is connected to on this connection."
::= { bcsSimScsEcmgStatusEntry 5 }


-- ------------------------------------------------------------------------------
--
-- bcsSimScsProgramTable
--

bcsSimScsProgramTable OBJECT-TYPE
    SYNTAX SEQUENCE OF BcsSimScsProgramEntry
    MAX-ACCESS not-accessible
    STATUS current
    DESCRIPTION
        "It contains status information for the SCS programs.
         There can be up to bcsSimScsMaxPrograms
         Simulcrypt programs active in the SCS at a time.
         Each program can be associated with up to
         bcsSimScsMaxProgramEcmg."
::= { bcsSimScsStatus 3 }

bcsSimScsProgramEntry OBJECT-TYPE
    SYNTAX BcsSimScsProgramEntry
    MAX-ACCESS not-accessible
    STATUS current
    DESCRIPTION
        "A single entry in the bcsSimScsProgramTable table."
    INDEX { bcsSimScsProgramIndex, bcsSimScsProgramEcmgIndex }
::= { bcsSimScsProgramTable 1}

BcsSimScsProgramEntry ::= SEQUENCE
    {
     bcsSimScsProgramIndex             Integer32,
     bcsSimScsProgramEcmgIndex         Integer32,
     bcsSimScsProgramState             INTEGER,
     bcsSimScsProgramCryptoPeriod      Unsigned32,
     bcsSimScsProgramChannelId         Unsigned32,
     bcsSimScsProgramEcmgSuperCasId    Unsigned32,
     bcsSimScsProgramEcmgStreamState   INTEGER
    }

bcsSimScsProgramIndex OBJECT-TYPE
    SYNTAX Integer32
    MAX-ACCESS not-accessible
    STATUS current
    DESCRIPTION
       "This index is used to traverse the bcsSimScsProgramTable
        table.  Limited by bcsSimScsMaxPrograms."
::= { bcsSimScsProgramEntry 1 }

bcsSimScsProgramEcmgIndex OBJECT-TYPE
    SYNTAX Integer32
    MAX-ACCESS not-accessible
    STATUS current
    DESCRIPTION
       "ECMG index.  This index is used to traverse the
        bcsSimScsProgramTable table.
        Limited by bcsSimScsMaxProgramEcmg."
::= { bcsSimScsProgramEntry 2 }

bcsSimScsProgramState OBJECT-TYPE
    SYNTAX INTEGER
        {
         noEventRunning (1),
         eventRunning   (2),
         notConfigured  (3)
        }
    MAX-ACCESS read-only
    STATUS current
    DESCRIPTION
       "This column displays the service state of this program.
          (1) - program configured, no event running
          (2) - program configured, event running normally
          (3) - program not configured"
::= { bcsSimScsProgramEntry 3 }

bcsSimScsProgramCryptoPeriod OBJECT-TYPE
    SYNTAX Unsigned32
    MAX-ACCESS read-only
    STATUS current
    DESCRIPTION
       "This column displays the actual crypto-period in
        seconds that is in use for this program."
::= { bcsSimScsProgramEntry 4 }

bcsSimScsProgramChannelId OBJECT-TYPE
    SYNTAX Unsigned32
    MAX-ACCESS read-only
    STATUS current
    DESCRIPTION
       "This column displays the channel ID."
::= { bcsSimScsProgramEntry 5 }

bcsSimScsProgramEcmgSuperCasId OBJECT-TYPE
    SYNTAX Unsigned32
    MAX-ACCESS read-only
    STATUS current
    DESCRIPTION
       "This column displays the Super CAS-ID of the 1st
        ECMG on this service."
::= { bcsSimScsProgramEntry 6 }

bcsSimScsProgramEcmgStreamState OBJECT-TYPE
    SYNTAX INTEGER
       {
          open          (1),
          closed        (2),
          error         (3),
          notConfigured (4),
          invalidCasId  (5)
       }
    MAX-ACCESS read-only
    STATUS current
    DESCRIPTION
       "This column displays the stream state for an ECMG
        on this service."
::= { bcsSimScsProgramEntry 7 }


-- ------------------------------------------------------------------------------
END
