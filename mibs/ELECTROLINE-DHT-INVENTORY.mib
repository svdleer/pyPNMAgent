--*****************************************************************************
--                                                                          
--    Copyright 2003-2004 Electroline Equipment Inc.                                   
--    All Rights Reserved                                                                          
--                                                                                                                            
--                                                                          
--*****************************************************************************
--    Filename: ELECTROLINE-DHT-INVENTORY.mib
--    Author:   Eric Alarie
--    Creation Date: 2003.03.20
--*****************************************************************************
--    Description:
--
--     SNMPv2 Inventory branch MIB definition for DHT product.
--
--    Note that these MIBs are read-only during normal operation, and are intended
--    for Electroline inventory tracking purpose. 
--	
--    When the DHT is in factory mode, the value of these MIBS can be configured 
--    by the factory programming station.
--    To save the value of these MIBs in non-volatile memory, the
--    factory program must set the "commit" MIB to one (1).
--		
--*****************************************************************************
--    Revision History:
--	  2003.03.20	Eric Alarie	First Draft						
--	  2003.03.21	Carlene Gardner	Linguistic revision
--	  2003.05.13    Eric Alarie     Re-work MIBs to keep necessary info only.
--	  2003.05.21	Carlene Gardner	Linguistic revision
--	  2003.07.07	Carlene Gardner	Linguistic revision 
--        2004.01.15    Eric Alarie     Changed MIB name of HwRev to HwMinorRev
--                                      Changed MIB name of HwRev HwBatchNumber to HwMajorRev
--                                      Changed MIB name of HwRev SwAppType to HwDrvRev
--	  2004.01.26	Carlene Gardner	Linguistic revision  
--	  2008-07-25	Alain Leclerc		Added Eline private model number string.  This is need for the ECMM
--*****************************************************************************

ELECTROLINE-DHT-INVENTORY-MIB DEFINITIONS ::= BEGIN

IMPORTS
    MODULE-IDENTITY,
    OBJECT-TYPE,
    Integer32 	   FROM SNMPv2-SMI
	DateAndTime    FROM SNMPv2-TC
    dhtInventory   FROM ELECTROLINE-DHT-ROOT-MIB;

                

--*****************************************************************************
-- * GLOBAL INVENTORY DATA
-- *
-- * The following information is used to determine the type of PCB / Assembly
-- * and its revision number.  Additional information required by the DHT
-- * software for proper operation on all board variations is also stored here.
-- * 
-- * The values defined for these MIBs are kept in a separate document.
--*****************************************************************************

dhtInvHwType OBJECT-TYPE
    SYNTAX   	INTEGER   
    MAX-ACCESS  read-only
    STATUS      current
    DESCRIPTION
       "DHT Hardware Model Identification Number. This information is used by the DHT 
       software to differentiate the hardware platform on which it is running.
       For example, the HMS022 compatible version and the legacy version of the DHT
       have different hardware types."
    ::= { dhtInventory 1 }

dhtInvHwMinorRev OBJECT-TYPE
    SYNTAX   	INTEGER   
    MAX-ACCESS  read-only
    STATUS      current
    DESCRIPTION
       "DHT Hardware Revision Identification Number, representing the PCB version 
       and / or the assembly modification level."
    ::= { dhtInventory 2 }

dhtInvHwMajorRev OBJECT-TYPE
	SYNTAX 		INTEGER
	MAX-ACCESS	read-only
	STATUS		current
	DESCRIPTION
		"This information is used to represent a family of hardware revisions.
		 Major functional changes will trigger a modification of this value"
	::= { dhtInventory 3 }

dhtInvHwDrvRev OBJECT-TYPE
    SYNTAX   	INTEGER   
    MAX-ACCESS  read-only
    STATUS      current
    DESCRIPTION
       "This information is used to track any changes in the manufacturing process
	    not covered by a PCB/Assembly revision and that have an impact on the drivers.
       "
    ::= { dhtInventory 4 }

dhtModelNumber  OBJECT-TYPE
     SYNTAX OCTET STRING (SIZE(0..255))
     ACCESS read-only
     STATUS current
     DESCRIPTION 
          "Displays the private electroline model number. 
          Displayed in human-readable format."
     ::= { dhtInventory 5 }

--*****************************************************************************
-- * MANUFACTURING INVENTORY DATA
-- *
-- * This section contains additional manufacturing process related information 
-- * for tracking purposes.
--*****************************************************************************
dhtManufacturingInfo OBJECT-IDENTITY
	STATUS current
	DESCRIPTION "Electroline Private sub-tree to access manufacturing information"
	::= { dhtInventory 10 }

dhtMfcDateTime OBJECT-TYPE
	SYNTAX 		DateAndTime
	MAX-ACCESS	read-only
	STATUS		current
	DESCRIPTION
		"Date and time when this unit was tested (in a string format)."
	::= { dhtManufacturingInfo 1 }

dhtMfcTestSwVersion OBJECT-TYPE
	SYNTAX 		OCTET STRING
	MAX-ACCESS	read-only
	STATUS		current
	DESCRIPTION
		"Version of the test station with which this DHT was tested."
	::= { dhtManufacturingInfo 2 }

dhtMfcJobNumber OBJECT-TYPE
	SYNTAX 		OCTET STRING
	MAX-ACCESS	read-only
	STATUS		current
	DESCRIPTION
		"Electroline production Job Number for this unit."
	::= { dhtManufacturingInfo 3 }
END
