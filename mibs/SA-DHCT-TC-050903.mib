--
-- SA-DHCT-TC.my
-- MIB generated by MG-SOFT Visual MIB Builder Version 4.0 Build 349
-- Friday, May 09, 2003 at 10:44:07
--

-- Revision 1 : Initial Revision
-- Date: Friday, May 09, 2003 at 10:43:45
-- Comment:
-- Initial Revision
-- 
	SA-DHCT-TC DEFINITIONS ::= BEGIN
 
		IMPORTS
			saModules			
				FROM SCIATL-COMMON-MIB			
			Unsigned32, MODULE-IDENTITY			
				FROM SNMPv2-SMI;
	
	
		saDhctTcModule MODULE-IDENTITY 
			LAST-UPDATED "200305091043Z"		-- May 09, 2003 at 10:43 GMT
			ORGANIZATION 
				"Scientific Atlanta"
			CONTACT-INFO 
				"DBDS Software Engineering & Architecture
				Scientific-Atlanta
				5030 Sugarloaf Parkway
				Lawrencville, GA 30044
				"
			DESCRIPTION 
				"This module holds textual conventions and type assignments
				common for DHCTs."
			REVISION "200305091043Z"		-- May 09, 2003 at 10:43 GMT
			DESCRIPTION 
				"Initial Revision"
			::= { saModules 4 }

		
	
--
-- Type definitions
--
	
		DhctTimeStampType ::= Unsigned32
-- If the object definition does not specify otherwise,
-- this is the number of milli-seconds since January 1, 1970, 12:00:00AM GMT.
	
--
-- Node definitions
--
	
	
	END

--
-- SA-DHCT-TC.my
--
