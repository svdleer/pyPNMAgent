--
-- SA-CAOVERLAY-MIB.mib
-- MIB generated by MG-SOFT Visual MIB Builder Version 4.0 Build 349
-- Tuesday, July 22, 2003 at 17:49:02
--

	SA-CAOVERLAY-MIB DEFINITIONS ::= BEGIN
 
		IMPORTS
			saCaOverlayMib			
				FROM SA-DBDSGEN-MIB			
			saModules			
				FROM SCIATL-COMMON-MIB			
			OBJECT-GROUP, MODULE-COMPLIANCE			
				FROM SNMPv2-CONF			
			Integer32, OBJECT-TYPE, MODULE-IDENTITY, OBJECT-IDENTITY			
				FROM SNMPv2-SMI;
	
	
		saCaOverlayMibModule MODULE-IDENTITY 
			LAST-UPDATED "200304291054Z"		-- April 29, 2003 at 10:54 GMT
			ORGANIZATION 
				"Scientific-Atlanta"
			CONTACT-INFO 
				"DBDS Software Engineering & Architecture
				Scientific-Atlanta
				5030 Sugarloaf Parkway
				Lawrencville, GA 30044
				"
			DESCRIPTION 
				"Scientific-Atlanta CA Overlay MIB
				
				This MIB module Copyright 2003 Scientific-Atlanta
				
				
				THIS VERSION IS PRELIMINARY FOR REVIEW PURPOSES ONLY!
				"
			::= { saModules 12 }

		
	
--
-- Node definitions
--
	
		saCaOverlayConf OBJECT-IDENTITY
			STATUS current
			DESCRIPTION 
				"Conformance"
			::= { saCaOverlayMib 1 }

		
		saCaOverlayGroups OBJECT-IDENTITY
			STATUS current
			DESCRIPTION 
				"Object Groups of the SA-CAOVERLAY-MIB"
			::= { saCaOverlayConf 1 }

		
		saCaOverlayDecodeGroup OBJECT-GROUP
			OBJECTS { saCaOverlayDecoderIndex, saCaOverlayDecodeVideoPidB, saCaOverlayDecodeAudioPidB }
			STATUS current
			DESCRIPTION 
				"Description."
			::= { saCaOverlayGroups 1 }

		
		saCaOverlayCompls OBJECT-IDENTITY
			STATUS current
			DESCRIPTION 
				"Compliances of the SA-CAOVERLAY-MIB"
			::= { saCaOverlayConf 2 }

		
		saCaOverlayDecoderCompliance MODULE-COMPLIANCE
			STATUS current
			DESCRIPTION 
				"Devices that decode CA Overlay streams must comply with 
				these requirements."
			MODULE -- this module
				MANDATORY-GROUPS { saCaOverlayDecodeGroup }
			::= { saCaOverlayCompls 1 }

		
		saCaOverlayObjs OBJECT-IDENTITY
			STATUS current
			DESCRIPTION 
				"The MIB Objects defined for the SA-CAOVERLAY-MIB module."
			::= { saCaOverlayMib 2 }

		
		saCaOverlayDecode OBJECT-IDENTITY
			STATUS current
			DESCRIPTION 
				"Decoder Information"
			::= { saCaOverlayObjs 1 }

		
		saCaOverlayDecodeTable OBJECT-TYPE
			SYNTAX SEQUENCE OF SaCaOverlayDecodeEntry
			MAX-ACCESS not-accessible
			STATUS current
			DESCRIPTION
				"Information about the decoding of CA Overlay Streams."
			::= { saCaOverlayDecode 1 }

		
		saCaOverlayDecodeEntry OBJECT-TYPE
			SYNTAX SaCaOverlayDecodeEntry
			MAX-ACCESS not-accessible
			STATUS current
			DESCRIPTION
				"An entry in the table. Each decoder resource that is actively engaged in
				decoding a CA-Overlay stream must be represented in the table. Decoder 
				resources not actively decoding a CA-Overlay stream may be represented in 
				the table or may be absent. In any case, the value of saCaOverlayDecoderIndex
				must always correspond to the same decoder resource."
			INDEX { saCaOverlayDecoderIndex }
			::= { saCaOverlayDecodeTable 1 }

		
		SaCaOverlayDecodeEntry ::=
			SEQUENCE { 
				saCaOverlayDecoderIndex
					Integer32,
				saCaOverlayDecodeVideoPidB
					Integer32,
				saCaOverlayDecodeAudioPidB
					Integer32
			 }

		saCaOverlayDecoderIndex OBJECT-TYPE
			SYNTAX Integer32 (1..2147483647)
			MAX-ACCESS read-only
			STATUS current
			DESCRIPTION
				"A unique value for each entry in the table. Corresponds to the
				decoder resource being utilized. This must always correspond to
				the same decoder resource."
			::= { saCaOverlayDecodeEntry 1 }

		
		saCaOverlayDecodeVideoPidB OBJECT-TYPE
			SYNTAX Integer32
			MAX-ACCESS read-only
			STATUS current
			DESCRIPTION
				"Video PID B for the CA-Overlay stream. If this decoder resource is
				not currently decoding a CA-Overlay video stream, then this value is 0."
			::= { saCaOverlayDecodeEntry 2 }

		
		saCaOverlayDecodeAudioPidB OBJECT-TYPE
			SYNTAX Integer32
			MAX-ACCESS read-only
			STATUS current
			DESCRIPTION
				"Audio PID B for the CA-Overlay stream. If this decoder resource is
				not currently decoding a CA-Overlay audio stream, then this value is 0."
			::= { saCaOverlayDecodeEntry 3 }

		
		saCaOverlayEvents OBJECT-IDENTITY
			STATUS current
			DESCRIPTION 
				"Events associated with the CA Overlay."
			::= { saCaOverlayMib 3 }

		
		saCaOverlayEventsV2 OBJECT-IDENTITY
			STATUS current
			DESCRIPTION 
				"Dummy node under which all events must be defined. 
				This is required for SNMP v1/v2 compatability."
			::= { saCaOverlayEvents 0 }

		
	
	END

--
-- SA-CAOVERLAY-MIB.mib
--
