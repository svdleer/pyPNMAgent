--****************************************************************************
--
-- Copyright (c) 2003-2012 Broadcom Corporation
--
-- This program is the proprietary software of Broadcom Corporation and/or
-- its licensors, and may only be used, duplicated, modified or distributed
-- pursuant to the terms and conditions of a separate, written license
-- agreement executed between you and Broadcom (an "Authorized License").
-- Except as set forth in an Authorized License, Broadcom grants no license
-- (express or implied), right to use, or waiver of any kind with respect to
-- the Software, and Broadcom expressly reserves all rights in and to the
-- Software and all intellectual property rights therein.  IF YOU HAVE NO
-- AUTHORIZED LICENSE, THEN YOU HAVE NO RIGHT TO USE THIS SOFTWARE IN ANY WAY,
-- AND SHOULD IMMEDIATELY NOTIFY BROADCOM AND DISCONTINUE ALL USE OF THE
-- SOFTWARE.  
--
-- Except as expressly set forth in the Authorized License,
--
-- 1.     This program, including its structure, sequence and organization,
-- constitutes the valuable trade secrets of Broadcom, and you shall use all
-- reasonable efforts to protect the confidentiality thereof, and to use this
-- information only in connection with your use of Broadcom integrated circuit
-- products.
--
-- 2.     TO THE MAXIMUM EXTENT PERMITTED BY LAW, THE SOFTWARE IS PROVIDED
-- "AS IS" AND WITH ALL FAULTS AND BROADCOM MAKES NO PROMISES, REPRESENTATIONS
-- OR WARRANTIES, EITHER EXPRESS, IMPLIED, STATUTORY, OR OTHERWISE, WITH
-- RESPECT TO THE SOFTWARE.  BROADCOM SPECIFICALLY DISCLAIMS ANY AND ALL
-- IMPLIED WARRANTIES OF TITLE, MERCHANTABILITY, NONINFRINGEMENT, FITNESS FOR
-- A PARTICULAR PURPOSE, LACK OF VIRUSES, ACCURACY OR COMPLETENESS, QUIET
-- ENJOYMENT, QUIET POSSESSION OR CORRESPONDENCE TO DESCRIPTION. YOU ASSUME
-- THE ENTIRE RISK ARISING OUT OF USE OR PERFORMANCE OF THE SOFTWARE.
--
-- 3.     TO THE MAXIMUM EXTENT PERMITTED BY LAW, IN NO EVENT SHALL BROADCOM
-- OR ITS LICENSORS BE LIABLE FOR (i) CONSEQUENTIAL, INCIDENTAL, SPECIAL,
-- INDIRECT, OR EXEMPLARY DAMAGES WHATSOEVER ARISING OUT OF OR IN ANY WAY
-- RELATING TO YOUR USE OF OR INABILITY TO USE THE SOFTWARE EVEN IF BROADCOM
-- HAS BEEN ADVISED OF THE POSSIBILITY OF SUCH DAMAGES; OR (ii) ANY AMOUNT IN
-- EXCESS OF THE AMOUNT ACTUALLY PAID FOR THE SOFTWARE ITSELF OR U.S. $1,
-- WHICHEVER IS GREATER. THESE LIMITATIONS SHALL APPLY NOTWITHSTANDING ANY
-- FAILURE OF ESSENTIAL PURPOSE OF ANY LIMITED REMEDY.
--
--****************************************************************************
--    Filename: brcm-cabledata-mgmt.mib
--    Author:   Kevin O'Neal
--    Creation Date: 3-march-2002
--
--****************************************************************************
--    Description:
--
--		private MIB for cableData products
--		
--****************************************************************************
--    Revision History:
--
--****************************************************************************

BRCM-CABLEDATA-MGMT-MIB DEFINITIONS ::= BEGIN

IMPORTS
    MODULE-IDENTITY,
    OBJECT-TYPE
        FROM SNMPv2-SMI
    cableDataMgmt
        FROM BRCM-CABLEDATA-SMI;
                
cableDataMgmtMIB MODULE-IDENTITY
    LAST-UPDATED "201103010000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadcom proprietary MIB for runtime management and configuration
         of objects related to cableData products."
    REVISION      "201103010000Z"
    DESCRIPTION
        "Corrected node for BRCM-FTP-MGMT-MIB.  Added nodes for 
         BRCM-EUE-MGMT-MIB and BRCM-HOST-SEC-MIB."
    REVISION      "201008160000Z"
    DESCRIPTION
        "Added node for BRCM-SW-DLOAD-MIB."
    REVISION      "200908270000Z"
    DESCRIPTION
        "Added node for BRCM-IPTV-MGMT-MIB."
    REVISION      "200908260000Z"
    DESCRIPTION
        "Added node for BRCM-FTP-MGMT-MIB."
    REVISION      "200702050000Z"
    DESCRIPTION
        "Module description was updated."
    REVISION      "200206040000Z"
    DESCRIPTION
        "Initial version of this MIB module."
    ::= { cableDataMgmt 2 }
        
cableDataMgmtMIBObjects OBJECT IDENTIFIER ::= { cableDataMgmtMIB 1}

--
-- The cableDataMgmtMIBObjects branch will follow the same model as the
-- cableDataFactory branch.  In general we'll try to keep these synced
-- up just for consistency.  Branches are indicated below as comments,
-- see specific MIBs as indicated.
--

cableDataMgmtBase OBJECT IDENTIFIER ::= { cableDataMgmtMIBObjects 1 }

-- BRCM-CM-MGMT-MIB
-- cablemodemMgmt OBJECT IDENTIFIER ::= { cableDataMgmtMIBObjects 2 }

-- BRCM-CABLEHOME-MGMT-MIB
-- cableHomeMgmt OBJECT IDENTIFIER ::= { cableDataMgmtMIBObjects 3 }

-- BRCM-V2-MGMT-MIB
-- v2Mgmt OBJECT IDENTIFIER ::= { cableDataMgmtMIBObjects 4 }

-- BRCM-80211-MGMT-MIB
-- ieee802dot11Mgmt OBJECT IDENTIFIER ::= { cableDataMgmtMIBObjects 5 }

-- BRCM-EMTA-MGMT-MIB
-- emtaMgmt OBJECT IDENTIFIER ::= { cableDataMgmtMIBObjects 6 }

-- BRCM-RG-MGMT-MIB
-- residentialGatewayMgmt OBJECT IDENTIFIER ::= { cableDataMgmtMIBObjects 7 }

-- BRCM-PARENTALCONTROL-MGMT-MIB
-- parentalControlMgmt OBJECT IDENTIFIER ::= { cableDataMgmtMIBObjects 8 }

-- BRCM-BFC-MGMT-MIB
-- bfcMgmt  OBJECT IDENTIFIER ::= { cableDataMgmtMIBObjects 9 }

-- BRCM-BATTERY-MGMT-MIB
-- batteryMgmt OBJECT IDENTIFIER ::= { cableDataMgmtMIBObjects 10 }

-- BRCM-THERMAL-MGMT-MIB
-- thermalMgmt OBJECT IDENTIFIER ::= { cableDataMgmtMIBObjects 11 }

-- BRCM-EUE-MGMT-MIB
-- eueMgmt OBJECT IDENTIFIER ::= { cableDataMgmtMIBObjects 12 }

-- BRCM-IPTV-MGMT-MIB
-- iptvMgmt OBJECT IDENTIFIER ::= { cableDataMgmtMIBObjects 13 }

-- BRCM-L2TPV3-MGMT-MIB
-- l2tpv3Mgmt OBJECT IDENTIFIER ::= { cableDataMgmtMIBObjects 14 }

-- BRCM-SW-DLOAD-MIB
-- swDownloadMgmt OBJECT IDENTIFIER ::= { cableDataMgmtMIBObjects 15 }

-- BRCM-HOST-SEC-MIB
-- brcmHostSecurityMgmt OBJECT IDENTIFIER ::= { cableDataMgmtMIBObjects 16 }

-- BRCM-FTP-MGMT-MIB
-- ftpMgmt OBJECT IDENTIFIER ::= { cableDataMgmtMIBObjects 17 }

-- BRCM-WIFI-MGMT-MIB
-- wifiMgmt OBJECT IDENTIFIER ::= { cableDataMgmtMIBObjects 18 }

-- BRCM-CMC-MGMT-MIB
-- cmcMgmt OBJECT IDENTIFIER ::= { cableDataMgmtMIBObjects 19 }

-- BRCM-POWER-MGMT-MIB
-- powerMgmt OBJECT IDENTIFIER ::= { cableDataMgmtMIBObjects 20 }

-- This node is provided for vendor extensions to this MIB.
-- Each vendor may request any objects under a node which is located at
-- cableDataFactoryVendor.vendorEnterpriseNumber.
cableDataMgmtVendor OBJECT IDENTIFIER ::= { cableDataMgmt 99 }

-- Broadcom vendor node.  This may seem peculiar but in fact is actually
-- used for objects associated with the Broadcom generic vendor extension.
broadcomCableDataMgmt OBJECT IDENTIFIER ::= { cableDataMgmtVendor 4413 }
        
END
