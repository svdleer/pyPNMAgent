MPS-MIB DEFINITIONS ::= BEGIN

-- 
--  MPS-MIB MODULE-IDENTITY
--      ORGANIZATION "Motorola Broadband Communications Sector"
--      Copyright 1998, 1999, 2000, 2001, Motorola Broadband Communications Sector
--      CONTACT-INFO "Charles Zimmerman
--        Motorola Broadband Communications Sector
--        Digital Network Systems
--        101 Tournament Drive
--        Horsham, PA  19044
--
--        Tel: +1 215 323 1524
--        Fax: +1 215 NA
--        E-mail: czimmerm@gi.com"
--
--      DESCRIPTION  "The MIB module for the MPS.
--        
--       Revision Number 2.15
--

IMPORTS
        IpAddress       FROM RFC1155-SMI
        DisplayString   FROM RFC1213-MIB
        mps             FROM NLS-BBNIDENT-MIB
        OBJECT-TYPE     FROM RFC-1212
        TRAP-TYPE       FROM RFC-1215
--      dnsAlarms       FROM DNS-TRAPS-MIB
        trapIdentifier,     
        trapNetworkElemModelNumber,
        trapNetworkElemSerialNum,
        trapPerceivedSeverity,
        trapNetworkElemOperState,
        trapNetworkElemAlarmStatus,
        trapNetworkElemAdminState,
        trapNetworkElemAvailStatus, 
        trapText,
        trapNETrapLastTrapTimeStamp,
        trapChangedObjectId,
        trapAdditionalInfoInteger1, 
        trapAdditionalInfoInteger2, 
        trapAdditionalInfoInteger3,     
        trapChangedValueDisplayString,  
        trapChangedValueOID, 
        trapChangedValueIpAddress,         
        trapChangedValueInteger  
          FROM NLSBBN-TRAPS-MIB;
    
-- groups in the MPS  1000 MIB
        mpsSysConf                    OBJECT IDENTIFIER ::= {mps 1}
        mpsSysStatus                  OBJECT IDENTIFIER ::= {mps 2}
        mpsSysAlarms                  OBJECT IDENTIFIER ::= {mps 3} 
        mpsSysEvent                   OBJECT IDENTIFIER ::= {mps 4} 
        mpsSysDebug                   OBJECT IDENTIFIER ::= {mps 5}
        mpsSysLED                     OBJECT IDENTIFIER ::= {mps 6} 
        mpsDvbInput                   OBJECT IDENTIFIER ::= {mps 7}
        mpsDvbOutput                  OBJECT IDENTIFIER ::= {mps 8}
        mpsEncryptInsert              OBJECT IDENTIFIER ::= {mps 9}
        mpsQam                        OBJECT IDENTIFIER ::= {mps 10}
        mpsDheiInput                  OBJECT IDENTIFIER ::= {mps 11}
        mpsDS3                        OBJECT IDENTIFIER ::= {mps 12}
        mpsDheiOutput                 OBJECT IDENTIFIER ::= {mps 13}
        mpsRemux                      OBJECT IDENTIFIER ::= {mps 14}
        mpsDvbQam                     OBJECT IDENTIFIER ::= {mps 15}
        mpsDvbAsi                     OBJECT IDENTIFIER ::= {mps 16}
        mpsLbandIn                    OBJECT IDENTIFIER ::= {mps 17}
        mpsDecryptExtract             OBJECT IDENTIFIER ::= {mps 18}
        mpsDualDvbAsiOutput           OBJECT IDENTIFIER ::= {mps 19}
        mpsDualDvbAsiInput            OBJECT IDENTIFIER ::= {mps 20}
        mpsEie                        OBJECT IDENTIFIER ::= {mps 21}
        mpsQam3                       OBJECT IDENTIFIER ::= {mps 22}
-- mpsSysConf groups
--      mpsSysConfSaveConfig                                 mpsSysConf 1
--      mpsSysConfACPmode                                    mpsSysConf 2
--      mpsSysConfIPAddress                                  mpsSysConf 3
--      mpsSysConfSubnetMask                                 mpsSysConf 4
--      mpsSysConfMpsId                                      mpsSysConf 5
--      mpsSysConfProductName                                mpsSysConf 6
--      mpsSysConfNetworkAddress                             mpsSysConf 7
--      mpsSysConfMuxTable                                   mpsSysConf 8
--      mpsSysConfSlotTable                                  mpsSysConf 9
        mpsSysConfTime                OBJECT IDENTIFIER ::= {mpsSysConf 10}
        mpsSysConfUDP                 OBJECT IDENTIFIER ::= {mpsSysConf 11}
        mpsSysConfPidRemapping        OBJECT IDENTIFIER ::= {mpsSysConf 12}
--      mpsSysConfNullPacketsReserved                        mpsSysConf 13
        mpsSysConfNationalControl     OBJECT IDENTIFIER ::= {mpsSysConf 14}
        mpsSysConfCommands            OBJECT IDENTIFIER ::= {mpsSysConf 15}
--      mpsSysConfBaseAcpUnitAddressChange                   mpsSysConf 16
--      mpsSysConfInsertMode                                 mpsSysConf 17
        mpsSysConfPsip                OBJECT IDENTIFIER ::= {mpsSysConf 18}
-- mpsSysStatus groups
        mpsSysStatusTime              OBJECT IDENTIFIER ::= {mpsSysStatus 1}
--      mpsSysStatusMACAddress                               mpsSysStatus 2
--      mpsSysStatusSlotTable                                mpsSysStatus 3
--      mpsSysStatusErrorSummaryTable                        mpsSysStatus 4
        mpsSysStatusCommands          OBJECT IDENTIFIER ::= {mpsSysStatus 5}
        mpsSysStatusEnvironment       OBJECT IDENTIFIER ::= {mpsSysStatus 6}
--      mpsSysStatusLoadMPSTable                             mpsSysStatus 7
--      mpsSysStatusInsertionQueueTable                      mpsSysStatus 8
--      mpsSysStatusPsiTable                                 mpsSysStatus 9
--      mpsSysStatusPidTable                                 mpsSysStatus 10
--      mpsSysStatusOutputServiceTable                       mpsSysStatus 11
--      not currently implemented                            mpsSysStatus 12
        mpsSysStatusSysHardware       OBJECT IDENTIFIER ::= {mpsSysStatus 13}
        mpsSysStatusNationalControl   OBJECT IDENTIFIER ::= {mpsSysStatus 14}
--      mpsSysStatusTimeSourceTable                          mpsSysStatus 15
--      mpsSysStatusNCSourceTable                            mpsSysStatus 16
        mpsSysStatusSysSoftware       OBJECT IDENTIFIER ::= {mpsSysStatus 17}
-- mpsSysDebug groups
        mpsSysDebugUDP                OBJECT IDENTIFIER ::= {mpsSysDebug 1}
        mpsSysDebugMCM                OBJECT IDENTIFIER ::= {mpsSysDebug 2}
        mpsSysDebugModule             OBJECT IDENTIFIER ::= {mpsSysDebug 3}
-- mpsDvbInput groups
        mpsDvbInputConf               OBJECT IDENTIFIER ::= {mpsDvbInput 1}
        mpsDvbInputStatus             OBJECT IDENTIFIER ::= {mpsDvbInput 2}
        mpsDvbInputAlarms             OBJECT IDENTIFIER ::= {mpsDvbInput 3}
-- mpsDvbOutput groups
        mpsDvbOutputConf              OBJECT IDENTIFIER ::= {mpsDvbOutput 1}
        mpsDvbOutputStatus            OBJECT IDENTIFIER ::= {mpsDvbOutput 2}
        mpsDvbOutputAlarms            OBJECT IDENTIFIER ::= {mpsDvbOutput 3}
-- mpsEncryptInsert groups
        mpsEncryptInsertConf          OBJECT IDENTIFIER ::= {mpsEncryptInsert 1}
        mpsEncryptInsertStatus        OBJECT IDENTIFIER ::= {mpsEncryptInsert 2} 
        mpsEncryptInsertAlarms        OBJECT IDENTIFIER ::= {mpsEncryptInsert 3} 
-- mpsDecryptExtract groups
        mpsDecryptExtractConf         OBJECT IDENTIFIER ::= {mpsDecryptExtract 1}
        mpsDecryptExtractStatus       OBJECT IDENTIFIER ::= {mpsDecryptExtract 2} 
        mpsDecryptExtractAlarms       OBJECT IDENTIFIER ::= {mpsDecryptExtract 3} 
-- mpsQam groups
        mpsQamConf                    OBJECT IDENTIFIER ::= {mpsQam 1}
        mpsQamStatus                  OBJECT IDENTIFIER ::= {mpsQam 2}
-- mpsDheiInput groups
        mpsDheiInputConf              OBJECT IDENTIFIER ::= {mpsDheiInput 1}
        mpsDheiInputStatus            OBJECT IDENTIFIER ::= {mpsDheiInput 2}
-- mpsDS3 groups
        mpsDS3Conf                    OBJECT IDENTIFIER ::= {mpsDS3 1}
        mpsDS3Status                  OBJECT IDENTIFIER ::= {mpsDS3 2}
-- mpsDheiOutput groups
        mpsDheiOutputStatus           OBJECT IDENTIFIER ::= {mpsDheiOutput 1}
-- mpsRemux groups
        mpsRemuxConf                  OBJECT IDENTIFIER ::= {mpsRemux 1}
        mpsRemuxStatus                OBJECT IDENTIFIER ::= {mpsRemux 2}
        mpsRemuxStatistics            OBJECT IDENTIFIER ::= {mpsRemux 3}
-- mpsDvbQam groups
        mpsDvbQamConf                 OBJECT IDENTIFIER ::= {mpsDvbQam 1}
        mpsDvbQamStatus               OBJECT IDENTIFIER ::= {mpsDvbQam 2}
-- mpsDvbAsi groups
        mpsDvbAsiConf                 OBJECT IDENTIFIER ::= {mpsDvbAsi 1}
        mpsDvbAsiStatus               OBJECT IDENTIFIER ::= {mpsDvbAsi 2}
-- mpsLbandIn groups
        mpsLbandInConf                OBJECT IDENTIFIER ::= {mpsLbandIn 1}
        mpsLbandInStatus              OBJECT IDENTIFIER ::= {mpsLbandIn 2}
-- mpsDualDvbAsiOut groups
        mpsDualDvbAsiOutConf          OBJECT IDENTIFIER ::= {mpsDualDvbAsiOutput 1}
        mpsDualDvbAsiOutStatus        OBJECT IDENTIFIER ::= {mpsDualDvbAsiOutput 2}
-- mpsDualDvbAsiInput groups
        mpsDualDvbAsiInConf           OBJECT IDENTIFIER ::= {mpsDualDvbAsiInput 1}
        mpsDualDvbAsiInStatus         OBJECT IDENTIFIER ::= {mpsDualDvbAsiInput 2}
-- mpsEie groups
        mpsEieConf                    OBJECT IDENTIFIER ::= {mpsEie 1}
        mpsEieStatus                  OBJECT IDENTIFIER ::= {mpsEie 2} 
        mpsEieAlarms                  OBJECT IDENTIFIER ::= {mpsEie 3} 
-- mpsQam3 groups
        mpsQam3Conf                   OBJECT IDENTIFIER ::= {mpsQam3 1}
        mpsQam3Status                 OBJECT IDENTIFIER ::= {mpsQam3 2} 
        mpsQam3Alarms                 OBJECT IDENTIFIER ::= {mpsQam3 3} 
-- mpsPsip groups
        mpsSysConfPsipGeneral         OBJECT IDENTIFIER ::= {mpsSysConfPsip 1}

mpsSysConfSaveConfig OBJECT-TYPE
    SYNTAX INTEGER
        {
          saveNotInProgress     (1),
          startSaveToFlash      (2),
          savingConfigToFlash   (3)
        }
    ACCESS  read-write
    STATUS  mandatory
    DESCRIPTION 
        "Writing this object will commit the current
         configuration to Flash.  While a read returns the
         value savingConfigToFlash, the flash is being saved;
         the save may not have been initiated by an SNMP set"
    REFERENCE   " -- "
::= { mpsSysConf 1}

mpsSysConfACPmode OBJECT-TYPE
    SYNTAX INTEGER
        { 
          des (1),
          csa (2)
        }
    ACCESS read-write
    STATUS mandatory
    DESCRIPTION  
        "Controls the current scrambling mode of the MPS ACPs.  
         1 - North American DES
         2 - DVB Common Scrambling Algorithm 
         This parameter applies to all MPS ACPs in the Chassis.
         Once written, a save must be performed via the mpsSysConfSaveConfig
         parameter and the MPS must be rebooted for the change to take effect."
    REFERENCE " -- "
::= { mpsSysConf 2}

mpsSysConfIPAddress OBJECT-TYPE
    SYNTAX  IpAddress
    ACCESS  read-write
    STATUS  mandatory
    DESCRIPTION 
        "This is the IP address of the MPS.  It is used for input 
         UDP logical ports.  The IP address is set via a BootP when connected
         to a Bootp server.  When not connected to a BootP server, the IP
         address may directly be changed by setting this parameter.  
         Once written, a save must be performed via the mpsSysConfSaveConfig
         parameter and the MPS must be rebooted for the change to take effect."
    REFERENCE   " -- "
::= { mpsSysConf 3}

mpsSysConfSubnetMask OBJECT-TYPE
    SYNTAX  IpAddress
    ACCESS  read-write
    STATUS  mandatory
    DESCRIPTION 
        "This is subnet mask for this MPS.  The subnet mask is normally
         via a BootP when connected to a BootP server.  When not connected
         to a Bootp Server, the Subnet Mask may directly be changed by
         setting this parameter.
         Once written, a save must be performed via the mpsSysConfSaveConfig
         parameter and the MPS must be rebooted for the change to take effect."
    REFERENCE   " -- "
::= { mpsSysConf 4}

mpsSysConfMpsId OBJECT-TYPE
    SYNTAX  INTEGER
    ACCESS  read-only
    STATUS  mandatory
    DESCRIPTION  
        "This is the Id of the MPS used for building service
         ids in WKE messages.  Changed to read only but kept 
         in the conf section" 
    REFERENCE   " -- "
::= { mpsSysConf 5}

mpsSysConfProductName OBJECT-TYPE
    SYNTAX  DisplayString
    ACCESS  read-write
    STATUS  mandatory
    DESCRIPTION 
        "This is the Product Name of the mps loaded at initialization from
         the config.ini file.  Specific configurations of the MPS have 
         specific purposes and are identified by their product name.  
         While this field is read-write, it is not recommended that the 
         product name be changed so that the unit configuration can
         remain easily identifiable when getting field support.
         If written, a save must be performed via the mpsSysConfSaveConfig
         parameter and the MPS must be rebooted for the change to take effect."
    REFERENCE   " -- "
::= { mpsSysConf 6}

mpsSysConfNetworkAddress OBJECT-TYPE
    SYNTAX  OCTET STRING
    ACCESS  read-write
    STATUS  mandatory
    DESCRIPTION 
        "This is the 40 bit Network Address of the MPS in human 
         readable format x-x-x-x.  This value is used when sending Load
         MPS Commands to the MPS via a tunneled National Control Stream 
         and for authorization of decrypt ACPs.
         If the MPS is capable of receiving commands via National Control
         or has Decryption capability, then this value will be set at 
         initialization to indicate the appropriate address for sending 
         messages.  
         While this parameter is read-write, there is no current application
         for writing a value to it.  The writable aspect is reserved for 
         later use.  Currently, any value written will be overwritten on 
         the next reboot."
    REFERENCE   " -- "
::= { mpsSysConf 7}

mpsSysConfMuxTable OBJECT-TYPE
    SYNTAX SEQUENCE OF MpsSysConfMuxEntry
    ACCESS not-accessible
    STATUS mandatory
    DESCRIPTION  
        "A table of mux settings for the MPS backplane.  The table
         reports the current configuration of muxes on the MPS backplane.
         While the table is writable, there is no current application
         for writing values to it.  The writable aspect is reserved for
         later use.  Currently, this table is overwritten with appropriate
         mux settings for the current configuration on each reboot."
    REFERENCE" - - - "
::= { mpsSysConf 8}

mpsSysConfMuxEntry OBJECT-TYPE
    SYNTAX  MpsSysConfMuxEntry
    ACCESS  not-accessible
    STATUS  mandatory
    INDEX {mpsSysConfMuxNumber}
::= { mpsSysConfMuxTable 1}

MpsSysConfMuxEntry ::= SEQUENCE
    {
      mpsSysConfMuxNumber   INTEGER,
      mpsSysConfMuxSetting  INTEGER
    }

mpsSysConfMuxNumber OBJECT-TYPE
    SYNTAX  INTEGER (1..11)
    ACCESS  not-accessible
    STATUS  mandatory
    DESCRIPTION  
        "This is the only index for the table.  This index specifies
         the number of the mux from 1 to 11 corresponding to the 
         eleven Infobus muxes of the MPS backplane."
    REFERENCE " -- "
::= { mpsSysConfMuxEntry 1}

mpsSysConfMuxSetting OBJECT-TYPE
    SYNTAX  INTEGER { zero (1),
                      one  (2) }
    ACCESS  read-write
    STATUS  mandatory
    DESCRIPTION  
        "The Mux Setting.  Zero or One.  Please reference a diagram
         of the MPS backplane for more information."
    REFERENCE " -- "
::= { mpsSysConfMuxEntry 2}

mpsSysConfSlotTable OBJECT-TYPE
    SYNTAX  SEQUENCE OF MpsSysConfSlotEntry
    ACCESS  not-accessible
    STATUS  mandatory
    DESCRIPTION  
        "A table of slot population for the MPS. This table
         reports what cards may be installed for this 
         configuration of the MPS.  Different MPS products 
         require different card compliments.  

         While this table is writable, there is no current
         application for writing it.  The writable aspect of
         this table is reserved for later use.  This table is 
         always overwritten on each reboot to coorespond to the
         current configuration of the MPS.

         The Allowed Type column of the table tells the
         mps which kind of cards are allowed in the slot.
         Allowed types are empty, specified, input only,
         output only, any, missing, or combinations of the above.

         When the type is specified the second column of
         the table specifies the allowable module id for
         that slot.

         Module MCN and Software Rev are not currently 
         used. "
    REFERENCE" - - - "
::= { mpsSysConf 9}

mpsSysConfSlotEntry OBJECT-TYPE
    SYNTAX  MpsSysConfSlotEntry
    ACCESS  not-accessible
    STATUS  mandatory
    INDEX {mpsSysConfSlotNumber}
::= { mpsSysConfSlotTable 1}

MpsSysConfSlotEntry ::= SEQUENCE
    {
     mpsSysConfSlotNumber       INTEGER,
     mpsSysConfSlotAllowedType  INTEGER,
     mpsSysConfSlotModuleId     INTEGER,
     mpsSysConfSlotModuleMCN    INTEGER,
     mpsSysConfSlotSoftwareRev  DisplayString
    }

mpsSysConfSlotNumber OBJECT-TYPE
    SYNTAX  INTEGER (1..8)
    ACCESS  not-accessible
    STATUS  mandatory
    DESCRIPTION  
        "Slot number is the only index to this table. 
         The MPS may have up to 8 slots with cards installed."  
    REFERENCE " -- "
::= { mpsSysConfSlotEntry 1}

mpsSysConfSlotAllowedType OBJECT-TYPE
    SYNTAX INTEGER 
        {  
         empty              (1),
         any                (2),
         anyOrEmpty         (3),
         specified          (4),
         specifiedOrEmpty   (5),
         input              (8),
         inputOrEmpty       (9),
         output             (16),
         outputOrEmpty      (17),
         specifiedOrMissing (36)
        }
    ACCESS read-write
    STATUS mandatory
    DESCRIPTION  
        "Specifies the Type of card installed for the slot.
         empty - slot must not contain a module.
         any - slot may contain any supported module.
         specified - slot must contain module id specified below.
         input - slot must contain an input module.
         output - slot must contain an output module.
         missing - if module not found, the MPS will continue to
                   boot but will report a major alarm."
    REFERENCE " -- "
::= { mpsSysConfSlotEntry 2}

mpsSysConfSlotModuleId OBJECT-TYPE
    SYNTAX INTEGER   
    ACCESS read-write
    STATUS mandatory
    DESCRIPTION  
        "The Module Id of the card that should be 
         installed in the slot.  N/A when Allowed
         Type is not specified."
    REFERENCE " -- "
::= { mpsSysConfSlotEntry 3}

mpsSysConfSlotModuleMCN OBJECT-TYPE
    SYNTAX INTEGER
    ACCESS read-write
    STATUS mandatory
    DESCRIPTION  
        "This field is not currently used."
    REFERENCE " -- "
::= { mpsSysConfSlotEntry 4}

mpsSysConfSlotSoftwareRev OBJECT-TYPE
    SYNTAX DisplayString
    ACCESS read-write
    STATUS mandatory
    DESCRIPTION  
        "This field is not currently used"
    REFERENCE " -- "
::= { mpsSysConfSlotEntry 5}

mpsSysConfTimeSource OBJECT-TYPE
    SYNTAX INTEGER 
        {
         loadMPS     (1),
         inputStream (2),
         sntp        (3)
        }
    ACCESS read-write
    STATUS mandatory
    DESCRIPTION  
        "The source for system time.  The MPS requires a
         time source in order to execute Load MPS commands.
         The time source can be configured to come from
         Load MPS Commands, be extracted from an input stream
         or come from an SNTP time source.  
         When configured to receive time via SNTP the 
         SntpServerSpecified object and SntpServiceIP objects
         can be used to optionally define the SNTP server.
         If configured to
         be extracted from an input stream then the MPS must
         contain a DE or REMUX card and have a valid multiplex
         containing time messages configured as an input to
         one of these cards.
         Once written, a save must be performed via the mpsSysConfSaveConfig
         parameter and the MPS must be rebooted for the change to take effect."
    REFERENCE " -- "
::= { mpsSysConfTime 1}

mpsSysConfUTCoffset OBJECT-TYPE
    SYNTAX INTEGER 
    ACCESS read-write
    STATUS mandatory
    DESCRIPTION 
        "The value of this object is the Universal Time
         Coordinated (UTC) offset from GPS time.  Subtract
         this from GPS time to convert from GPS to UTC.
         When time source is SNTP, this object can be set
         to specify the UTC offset that the MPS will use
         in calculating GPS time.
         When time source is from an inputStream, this object
         can be set to specify the UTC offset the MPS will
         use in converting GPS time to UTC.
         When time source is Load MPS, the UTC offset is 
         provided in the Load MPS Set GPS command and cannot
         be set here.  It may be read.
         Once written, a save must be performed via the mpsSysConfSaveConfig
         parameter and the MPS must be rebooted for the change to take effect."
    REFERENCE   " -- "
::= { mpsSysConfTime 2 }

mpsSysConfSntpServerSpecified OBJECT-TYPE
    SYNTAX INTEGER 
        {
         notSpecified (1),
         specified    (2)
        }
    ACCESS read-write
    STATUS mandatory
    DESCRIPTION  
        "When the TimeSource is SNTP, this object specifies whether 
         the MPS will only accept time for a single SNTP server or 
         from any server that broadcasts time.  
         When notSpecified, the MPS will accept time from any SNTP 
         server.
         When specified, the MPS will only accept time from the address
         of an SNTP server specified by the SntpServerIP address object.
         Once written, a save must be performed via the mpsSysConfSaveConfig
         parameter and the MPS must be rebooted for the change to take effect."
    REFERENCE " -- "
::= { mpsSysConfTime 3}

mpsSysConfSntpServerIP OBJECT-TYPE
    SYNTAX IpAddress
    ACCESS read-write
    STATUS mandatory
    DESCRIPTION 
        "This contains the IP address of the specified SNTP server.
         If mpsSysConfTimeSource is SNTP and mpsSysConfSntpServerSpecified 
         is set to specified, then the mps will only accept time from 
         this ip address.
         Once written, a save must be performed via the mpsSysConfSaveConfig
         parameter and the MPS must be rebooted for the change to take effect."
    REFERENCE   " -- "
::= { mpsSysConfTime  4}

mpsSysConfTimeInputId OBJECT-TYPE
    SYNTAX INTEGER
    ACCESS read-write
    STATUS mandatory
    DESCRIPTION 
        "This parameter is no longer used."
    REFERENCE   " -- "
::= { mpsSysConfTime  5}

mpsSysConfTimeInputSlot OBJECT-TYPE
    SYNTAX INTEGER (1..8)
    ACCESS read-write
    STATUS mandatory
    DESCRIPTION 
        "Contains the Slot of the input card from which the MPS should extract
         time when configured for receiving time from an input.
         Once written, a save must be performed via the mpsSysConfSaveConfig
         parameter and the MPS must be rebooted for the change to take effect."
    REFERENCE   " -- "
::= { mpsSysConfTime  6}

mpsSysConfTimeInputPort OBJECT-TYPE
    SYNTAX INTEGER
    ACCESS read-write
    STATUS mandatory
    DESCRIPTION 
        "Contains the Port of the input card from which the MPS should extract
         time when configured for receiving time from an input.
         Once written, a save must be performed via the mpsSysConfSaveConfig
         parameter and the MPS must be rebooted for the change to take effect."
    REFERENCE   " -- "
::= { mpsSysConfTime  7}

mpsSysConfUDPcontrollerIP OBJECT-TYPE
    SYNTAX IpAddress
    ACCESS read-write
    STATUS mandatory
    DESCRIPTION 
        "This contains the IP address of the local controller.
         This is most often an ACC-4000D, but may be some other
         device.  The MPS needs to have an IP address of the local
         controller to begin operations.  The default value for 
         this object is an IP address of '0.0.0.0' (which is an
         invalid IP Address).  This means that when an MPS is first 
         powered on, it will internally set this object to this 
         default value.  If the configuration fails to set this
         object to a non-zero IP address, the MPS will not begin
         normal operation.
         Once written, the change to this parameter will take immediate
         affect.  However, in order for the change to persist through 
         subsequent reboots or power cycles, the change must be saved via
         the mpsSysConfSaveConfig parameter."
    REFERENCE   " -- "
 ::= { mpsSysConfUDP  1}

mpsSysConfUDPcontrollerPort OBJECT-TYPE
    SYNTAX INTEGER
    ACCESS read-write
    STATUS mandatory
    DESCRIPTION 
        "This contains the port of the local controller.  The MPS uses
         this port when establishing UDP communications with the controller
         for the purpose of receiving Load MPS Commands. 
         Once written, the change to this parameter will take immediate
         affect.  However, in order for the change to persist through 
         subsequent reboots or power cycles, the change must be saved via
         the mpsSysConfSaveConfig parameter."
    REFERENCE   " -- "
 ::= { mpsSysConfUDP  2}

mpsSysConfUDPmpsPort OBJECT-TYPE
    SYNTAX INTEGER
    ACCESS read-write
    STATUS mandatory
    DESCRIPTION 
        "This contains the port of the mps.  This is the port which the MPS
         uses to receive UDP messages from the local controller.  These 
         messages include Load MPS Messages and Acks of reportbacks that 
         the MPS has sent.
         Once written, the change to this parameter will take immediate
         affect.  However, in order for the change to persist through 
         subsequent reboots or power cycles, the change must be saved via
         the mpsSysConfSaveConfig parameter."
    REFERENCE   " -- "
 ::= { mpsSysConfUDP  3}

mpsSysConfUDPmsgRetryTimeout OBJECT-TYPE
    SYNTAX INTEGER
    ACCESS read-write
    STATUS mandatory
    DESCRIPTION 
        "This contains the Timeout before retransmitting a Reportback.
         If the MPS does not receive an ack of the last reportback sent
         and this time has expired then the MPS attempts to resend the 
         reportback.
         Once written, a save must be performed via the mpsSysConfSaveConfig
         parameter and the MPS must be rebooted for the change to take effect."
    REFERENCE   " -- "
 ::= { mpsSysConfUDP  4}

mpsSysConfUDPmsgNumRetries OBJECT-TYPE
    SYNTAX INTEGER
    ACCESS read-write
    STATUS mandatory
    DESCRIPTION 
        "This contains the Num of Retries before deciding that the
         connection needs to be reestablished.  Each time a reportback
         message from the MPS timesouts on the ack then the MPS increments
         a count of retries.  When the count reaches this value the MPS
         assumes a broken connection and attempts to reconnect.
         Once written, a save must be performed via the mpsSysConfSaveConfig
         parameter and the MPS must be rebooted for the change to take effect."
    REFERENCE   " -- "
 ::= { mpsSysConfUDP  5}

mpsSysConfServicesPerECM OBJECT-TYPE
    SYNTAX INTEGER
    ACCESS read-write
    STATUS mandatory
    DESCRIPTION 
        "The Pid Remapping parameters are used at initialization to 
         deterministically partition the range of output elementary PIDs 
         that the MPS uses when remultiplexing.  The available elementary
         PID range is broken up into services with an equal distribution
         of available PIDs as defined by these parameters.
         Specifically, the Services Per ECM parameter specifies how many
         services are available per ECM PID when encrypting.  Since the 
         MPS currently only supports encryption of one service per ECM PID
         this parameter should always be set to one.  If set to any other
         value, the MPS will ignor the setting and assume a value of one.
         Use of this parameter at values other than one is reserved for later
         use."
    REFERENCE   " -- "
 ::= { mpsSysConfPidRemapping  1}

mpsSysConfPidsPerService OBJECT-TYPE
    SYNTAX INTEGER
    ACCESS read-write
    STATUS mandatory
    DESCRIPTION 
        "The Pid Remapping parameters are used at initialization to 
         deterministically partition the range of output elementary PIDs 
         that the MPS uses when remultiplexing.  The available elementary
         PID range is broken up into services with an equal distribution
         of available PIDs as defined by these parameters.
         Specifically, the PIDs per Service parameter specifies how many
         PIDs are to be allocated for each service.  The elementary PID 
         range consists of 4096 available PIDs.  Currently, this parameter
         may be set to values of 64, 32, and 16.  For multiplexes with many
         services with fewer PIDs per service the value 16 will allow up to
         252 services to be multiplexed.  For multiplexes with fewer services
         that contain many elementary PIDs per service, the value of 64 will
         allow 64 services to be multiplexed each with up to 64 components. 
         The value 32 allows a 128 multiplexed services with 
         up to 32 components per service.
         Once written, a save must be performed via the mpsSysConfSaveConfig
         parameter and the MPS must be rebooted for the change to take effect."
    REFERENCE   " -- "
 ::= { mpsSysConfPidRemapping  2}

mpsConfNonPesPidsPerService OBJECT-TYPE
    SYNTAX INTEGER
    ACCESS read-write
    STATUS mandatory
    DESCRIPTION 
        "The Pid Remapping parameters are used at initialization to 
         deterministically partition the range of output elementary PIDs 
         that the MPS uses when remultiplexing.  The available elementary
         PID range is broken up into services with an equal distribution
         of available PIDs as defined by these parameters.
         The Non PES Pids Per Service parameter is only used when PID Mask
         Encryption is specified per the below parameter.  If PID Mask 
         Encryption is disabled, this parameter is ignored and services may be
         made up of PES and non-PES PIDs in any distribution in numbers as
         specified by the PIDs per Service parameter.  
         If PID Mask Encryption is enabled, then this parameter is used to 
         further partition the allocation of PIDs at the service level.  Of the
         allocated PIDs per Service as defined above, the Non PES PIDs per
         Service parameter identifies how many of these PIDs are researved as
         non-PES components.  Currently, this parameter may be set to values 
         of 64, 32, and 16.  For example, if PIDs per Service is set to 64 and
         Non PES PIDs per Service is set for 16, then for each of the 64 
         supported services, 48 of the components may be PES PIDs and 16 may
         be non-PES.
         Once written, a save must be performed via the mpsSysConfSaveConfig
         parameter and the MPS must be rebooted for the change to take effect."
    REFERENCE   " -- "
 ::= { mpsSysConfPidRemapping  3}

mpsSysConfPidMaskingEnabled OBJECT-TYPE
    SYNTAX INTEGER
        {
         disabled (1),
         enabled (2)
        }
    ACCESS read-write
    STATUS mandatory
    DESCRIPTION 
        "This parameter is used to enable or disable PID Masking encryption (1 = disabled, 2 = enabled). 
         This parameter is only applicable when the MPS is configured with an E/I module that contains 
         version 1.7 or greater of the ACPs.  Note that when set to disabled, the PID Selection parameter, 
         mpsSysConfNonPesPidsPerService, is not used and is set to 0 by the MPS.  Also note that PID
         mask encryption is only applicable in configurations of the MPS that support remultiplexing.  
         When the current configuration of the MPS does not support remultiplexing, then the Pid Mask
         Encryption parameter is not used and encryption is performed without using masking.
         Once written, a save must be performed via the mpsSysConfSaveConfig
         parameter and the MPS must be rebooted for the change to take effect."
    REFERENCE   " -- "
 ::= { mpsSysConfPidRemapping  4}

mpsSysConfNullPacketsReserved OBJECT-TYPE
    SYNTAX INTEGER
    ACCESS read-write
    STATUS mandatory
    DESCRIPTION 
        "This parameter is used to indicate the minimum percentage of Null Packets that 
         must be made available for use by another device down stream from the
         MPS.  This reserved bandwidth will not be overwritten by the MPS when inserting
         messages.  This will be applied to each output from the MPS.
         Once written, a save must be performed via the mpsSysConfSaveConfig
         parameter and the MPS must be rebooted for the change to take effect."
    REFERENCE   " -- "
 ::= { mpsSysConf 13}

mpsSysConfBaseAcpUnitAddressChange OBJECT-TYPE
    SYNTAX INTEGER
        {
         notChanged (1),
         changed    (2)
        }
    ACCESS read-write
    STATUS mandatory
    DESCRIPTION
         "Indicates that the MPS detected a different MPS Base ACP Unit Address than 
          the one saved in non-volatile memory.  Once set to 'changed' it will remain 
          'changed' until an outside controller sets to 'reset'.  On detecting 'reset' 
          the MPS will save the new Base ACP Unit Address to non-volatile memory for 
          use after the next system restart.
          This immeadiate parameter does not require a save to take affect."
    REFERENCE   " -- "
::= { mpsSysConf 16 }

mpsSysConfInsertMode OBJECT-TYPE
    SYNTAX INTEGER
        {
         efficient (1),
         singleSection (2),
         twentyByte (3)
        }
    ACCESS read-write
    STATUS mandatory
    DESCRIPTION 
        "This parameter is used to set the insertion mode for the MPS.
        The MPS may be configured to insert messages as efficiently as
        possible (efficient), restrict insertion to a single section starting per 
        packet (singleSection), or restrict insertion to prevent any section from 
        starting in the last 20 bytes of a packet (twentyByte).
        Once written, the change to this parameter will take immediate
        effect.  However, in order for the change to persist through 
        subsequent reboots or power cycles, the change must be saved via
        the mpsSysConfSaveConfig parameter."

    REFERENCE   " -- "
 ::= { mpsSysConf 17}

-- ------------------------------------------------------------------------------
--
-- mpsPsip
--
-- mpsSysConfPsip
--
-- mpsSysConfPsipGeneral
--

mpsPsipConfigEnable OBJECT-TYPE
    SYNTAX INTEGER
        {
         disabled (1),
         enabled  (2)
        }

    ACCESS read-write
    STATUS mandatory
    DESCRIPTION
        "This parameter indicates that PSIP is enabled for the Output
         Transport Stream.
         Once written, a save must be performed via the mpsSaveConfig
         parameter and the MPS must be rebooted for the change to take effect."
::= {mpsSysConfPsipGeneral 1}

mpsPsipMgtMsgInsertionPeriod OBJECT-TYPE
    SYNTAX INTEGER (150..'7fffffff'h)
    ACCESS read-write
    STATUS mandatory
    DESCRIPTION
        "Message insertion period in milliseconds for the PSIP Master Guide
         Table (MGT).
         This message is sent on the PSIP Base PID.
         This is the time between start of insertion of the first packet
         of the message.  For the packet insertion period refer to
         mpsPsipBasePidPacketInsertionPeriod.
         Once written, the change to this parameter will take immediate
         effect.  However, in order for the change to persist through
         subsequent reboots or power cycles, the change must be saved via
         the mpsSaveConfig parameter."
::= {mpsSysConfPsipGeneral 2}


mpsPsipSttMsgInsertionPeriod OBJECT-TYPE
    SYNTAX INTEGER (1000..'7fffffff'h)
    ACCESS read-write
    STATUS mandatory
    DESCRIPTION
        "Message insertion period in milliseconds for the PSIP System Time
         Table (STT).
         This message is sent on the PSIP Base PID.
         This is the time between start of insertion of the first packet
         of the message.  For the packet insertion period refer to
         mpsPsipBasePidPacketInsertionPeriod.
         Once written, the change to this parameter will take immediate
         effect.  However, in order for the change to persist through
         subsequent reboots or power cycles, the change must be saved via
         the mpsSaveConfig parameter."
::= {mpsSysConfPsipGeneral 3}

mpsPsipCvctMsgInsertionPeriod OBJECT-TYPE
    SYNTAX INTEGER (400..'7fffffff'h)
    ACCESS read-write
    STATUS mandatory
    DESCRIPTION
        "Message insertion period in milliseconds for the PSIP Cable Virtual
         Channel Table (CVCT).
         This message is sent on the PSIP Base PID.
         This is the time between start of insertion of the first packet
         of the message.  For the packet insertion period refer to
         mpsPsipBasePidPacketInsertionPeriod.
         Once written, the change to this parameter will take immediate
         effect.  However, in order for the change to persist through
         subsequent reboots or power cycles, the change must be saved via
         the mpsSaveConfig parameter."
::= {mpsSysConfPsipGeneral 4}

mpsPsipRrtMsgInsertionPeriod OBJECT-TYPE
    SYNTAX INTEGER (60000..'7fffffff'h)
    ACCESS read-write
    STATUS mandatory
    DESCRIPTION
        "Message insertion period in milliseconds for the PSIP Rating Region
         Table (RRT).
         This message is sent on the PSIP Base PID.
         This is the time between start of insertion of the first packet
         of the message.  For the packet insertion period refer to
         mpsPsipBasePidPacketInsertionPeriod.
         Once written, the change to this parameter will take immediate
         effect.  However, in order for the change to persist through
         subsequent reboots or power cycles, the change must be saved via
         the mpsSaveConfig parameter."
::= {mpsSysConfPsipGeneral 5}

mpsPsipBasePidPacketInsertionPeriod OBJECT-TYPE
    SYNTAX INTEGER (1..'7fffffff'h)
    ACCESS read-write
    STATUS mandatory
    DESCRIPTION
        "Packet insertion period in milliseconds for Base PID packets.
         Messages sent on the PSIP Base PID include the MGT, SST,
         CVCT and RRT.
         This is the minimum time between packet insertions.  The
         actual packet insertion period could be delayed depending
         on MPS processor load.
         Once written, the change to this parameter will take immediate
         effect.  However, in order for the change to persist through
         subsequent reboots or power cycles, the change must be saved via
         the mpsSaveConfig parameter."
::= {mpsSysConfPsipGeneral 6}

mpsPsipNumEitPerOutputStream OBJECT-TYPE
    SYNTAX INTEGER(0..4)
    ACCESS read-write
    STATUS mandatory
    DESCRIPTION
        "Number of Event Information Tables per Output Transport Stream.
         Once written, a save must be performed via the mpsSaveConfig
         parameter and the MPS must be rebooted for the change to take effect."
::= {mpsSysConfPsipGeneral 7}


-- ------------------------------------------------------------------------------
--
-- mpsPsipEitConfigTable
--

mpsPsipEitConfigTable OBJECT-TYPE
    SYNTAX SEQUENCE OF MpsPsipEitConfigEntry
    ACCESS not-accessible
    STATUS mandatory
    DESCRIPTION
        "This is a table of PSIP Event Information Table
         configuration parameters."
::= { mpsSysConfPsip 3 }

mpsPsipEitConfigEntry OBJECT-TYPE
    SYNTAX MpsPsipEitConfigEntry
    ACCESS not-accessible
    STATUS mandatory
    DESCRIPTION
        "PSIP EIT Configuration Table Entry."
    INDEX {mpsPsipEitConfigEitIndex}
::= { mpsPsipEitConfigTable 1}

MpsPsipEitConfigEntry ::= SEQUENCE
    {
     mpsPsipEitConfigEitIndex               INTEGER,
     mpsPsipEitConfigMsgInsertionPeriod     INTEGER,
     mpsPsipEitConfigPacketInsertionPeriod  INTEGER
    }

mpsPsipEitConfigEitIndex OBJECT-TYPE
    SYNTAX INTEGER(1..4)
    ACCESS not-accessible
    STATUS mandatory
    DESCRIPTION
        "EIT index.  This index is one greater than the EIT Number
         which is zero based."
::= { mpsPsipEitConfigEntry 1 }

mpsPsipEitConfigMsgInsertionPeriod OBJECT-TYPE
    SYNTAX INTEGER (500..'7fffffff'h)
    ACCESS read-write
    STATUS mandatory
    DESCRIPTION
        "Message insertion period in milliseconds for the PSIP Event
         Information Table (EIT).
         This is the time between start of insertion of the first packet
         of the message.  For the packet insertion period refer to
         mpsPsipBasePidPacketInsertionPeriod.
         Once written, the change to this parameter will take immediate
         effect.  However, in order for the change to persist through
         subsequent reboots or power cycles, the change must be saved via
         the mpsSaveConfig parameter."
::= { mpsPsipEitConfigEntry 2 }

mpsPsipEitConfigPacketInsertionPeriod OBJECT-TYPE
    SYNTAX INTEGER (1..'7fffffff'h)
    ACCESS read-write
    STATUS mandatory
    DESCRIPTION
        "Packet insertion period in milliseconds for a packet of the PSIP
         Event Information Table (EIT) message.
         This is the minimum time between packet insertions.  The
         actual packet insertion period could be delayed depending
         on MPS processor load.
         Once written, the change to this parameter will take immediate
         effect.  However, in order for the change to persist through
         subsequent reboots or power cycles, the change must be saved via
         the mpsSaveConfig parameter."
::= { mpsPsipEitConfigEntry 3 }


mpsSysLEDdcPowerOK OBJECT-TYPE
    SYNTAX INTEGER
        {
         off (1),
         on  (2)
        }
    ACCESS read-only
    STATUS mandatory
    DESCRIPTION
        "This LED indicates if the unit has good DC power. The object
         mirrors the LED on the front panel"
    REFERENCE   " -- "
 ::= { mpsSysLED  1}

mpsSysLEDconfigured OBJECT-TYPE
    SYNTAX INTEGER
        {
         off (1),
         on  (2)
        }
    ACCESS read-only
    STATUS mandatory
    DESCRIPTION
        "This LED indicates if the unit has been successfully configured.
         After a reboot, the MPS will connect to a bootp server, determine
         whether code download is needed, and will download code.  The MPS
         will determine what cards are present in the chassis and will
         configure these cards.  It will also determine what input to output
         connections are made.  When all these operations are complete this
         LED will come on.  If an fatal error is found during configuration
         the LED will not come on.  Until the MPS is configured, other LED
         objects will be off and have no meaning.
         The object mirrors the LED on the front panel."
    REFERENCE   " -- "
 ::= { mpsSysLED  2}

mpsSysLEDauthorized OBJECT-TYPE
    SYNTAX INTEGER 
        {
         off (1),
         on  (2)
        }
    ACCESS read-only
    STATUS mandatory
    DESCRIPTION 
        "This LED indicates whether the MPS has proper encryption and decryption
         authorization.  If the unit is not commanded to encrypt or decrypt the
         LED is off.  If the unit is commanded to encrypt or decrypt and does
         not have proper authorization then the LED is off.  If the unit is
         commanded to encrypt or decrypt and does have authorization for all
         services then the light is on.  The object mirrors the LED on the front
         panel."
    REFERENCE   " -- "
 ::= { mpsSysLED  3}

mpsSysLEDinputFailure OBJECT-TYPE
    SYNTAX INTEGER 
        {
         off (1),
         on  (2)
        }
    ACCESS read-only
    STATUS mandatory
    DESCRIPTION 
        "This LED indicates if any modules have an input failure.  For a module
         to have an input failure the input must be enabled and must not be
         receiving input.  Further detail as to which module is having the failure
         can be determined by reading the input failure objects for each module type.
         The object mirrors the LED on the MPS chassis front panel."
    REFERENCE   " -- "
 ::= { mpsSysLED  4}

mpsSysLEDoutputMuting OBJECT-TYPE
    SYNTAX INTEGER 
        {
         off (1),
         on  (2)
        }
    ACCESS read-only
    STATUS mandatory
    DESCRIPTION 
        "This LED indicates if any outputs are muted.  The object mirrors the LED
         on the MPS chassis front panel."
    REFERENCE   " -- "
 ::= { mpsSysLED  5}

mpsSysLEDfaultSumm OBJECT-TYPE
    SYNTAX INTEGER 
        {
         off  (1),
         on   (2)
        }
    ACCESS read-only
    STATUS mandatory
    DESCRIPTION 
        "This LED indicates if the unit has a current alarm greater than Major.  
         If the MPS has an alarm the mpsAlarm objects can be read to determine
         the cause.  This object mirrors the LED on the MPS chassis front panel."
    REFERENCE   " -- "
 ::= { mpsSysLED  6}


mpsSysDebugMCMerrorTable OBJECT-TYPE
    SYNTAX SEQUENCE OF MpsSysDebugMCMerrorEntry
    ACCESS not-accessible
    STATUS mandatory
    DESCRIPTION  
        "A table of mcm error by slot and code. The MCM is the
         task within the MPS that is responsible for configuring the cards 
         within the MPS and assuring connections between cards.  Errors that
         occur during the process of configuring the MPS are stored in this
         table.  The last 10 errors are stored."
    REFERENCE " - - - "
::= { mpsSysDebugMCM 1}

mpsSysDebugMCMerrorEntry OBJECT-TYPE
    SYNTAX MpsSysDebugMCMerrorEntry
    ACCESS not-accessible
    STATUS mandatory
    INDEX {mpsSysDebugMCMerrorIndex}
::= { mpsSysDebugMCMerrorTable 1}

MpsSysDebugMCMerrorEntry ::= SEQUENCE
    {
     mpsSysDebugMCMerrorIndex INTEGER,
     mpsSysDebugMCMerrorSlot  INTEGER,
     mpsSysDebugMCMerrorCode  INTEGER
    }

mpsSysDebugMCMerrorIndex OBJECT-TYPE
    SYNTAX INTEGER (1..100)
    ACCESS not-accessible
    STATUS mandatory
    DESCRIPTION  
        "The Index of which error to view." 
    REFERENCE " -- "
::= { mpsSysDebugMCMerrorEntry 1}

mpsSysDebugMCMerrorSlot OBJECT-TYPE
    SYNTAX INTEGER (1..9)  
    ACCESS read-only
    STATUS mandatory
    DESCRIPTION  
        "The chassis slot of the error."
    REFERENCE " -- "
::= { mpsSysDebugMCMerrorEntry 2}

mpsSysDebugMCMerrorCode OBJECT-TYPE
    SYNTAX INTEGER
    ACCESS read-only
    STATUS mandatory
    DESCRIPTION  
        "The error code.  Error codes are not enumerated here."
    REFERENCE " -- "
::= { mpsSysDebugMCMerrorEntry 3}

mpsSysDebugModuleTable OBJECT-TYPE
    SYNTAX SEQUENCE OF MpsSysDebugModuleEntry
    ACCESS not-accessible
    STATUS mandatory
    DESCRIPTION  
        "This table is undocumented and is used for testing only.  
         This table should not be written."
    REFERENCE" - - - "
::= { mpsSysDebugModule 1}

mpsSysDebugModuleEntry OBJECT-TYPE
    SYNTAX MpsSysDebugModuleEntry
    ACCESS not-accessible
    STATUS mandatory
    INDEX {mpsSysDebugModuleIndex}
::= { mpsSysDebugModuleTable 1}

MpsSysDebugModuleEntry ::= SEQUENCE
    {
     mpsSysDebugModuleIndex  INTEGER,
     mpsSysDebugModuleDebug  INTEGER,
     mpsSysDebugModuleStart  INTEGER
    }

mpsSysDebugModuleIndex OBJECT-TYPE
    SYNTAX INTEGER (1..8)
    ACCESS not-accessible
    STATUS mandatory
    DESCRIPTION  
        "The Index." 
    REFERENCE " -- "
::= { mpsSysDebugModuleEntry 1}

mpsSysDebugModuleDebug OBJECT-TYPE
    SYNTAX INTEGER 
        {
         off (1), 
         on  (2)
        }  
    ACCESS read-write
    STATUS mandatory
    DESCRIPTION  
        "Which module to debug"
    REFERENCE " -- "
::= { mpsSysDebugModuleEntry 2}

mpsSysDebugModuleStart OBJECT-TYPE
    SYNTAX INTEGER 
        {
         paused (1),
         start  (2)
        }
    ACCESS read-write
    STATUS mandatory
    DESCRIPTION  
        "Debugging started"
    REFERENCE " -- "
::= { mpsSysDebugModuleEntry 3}

mpsSysDebugModuleLbandAllowDebugButton OBJECT-TYPE
    SYNTAX INTEGER 
    ACCESS read-write
    STATUS mandatory
    DESCRIPTION  
        "The parameter is used for internal debug only and should not be written."
    REFERENCE " -- "
::= { mpsSysDebugModule 2 }

mpsSysDebugUDPsocketCreated OBJECT-TYPE
    SYNTAX INTEGER
    ACCESS read-only
    STATUS mandatory
    DESCRIPTION 
        "This object indicates that the UDP socket has been created.  The
         UDP socket is created as the Load MPS command interface to the MPS.
         If the socket is not created then the MPS cannot receive commands. "
    REFERENCE   " -- "
 ::= { mpsSysDebugUDP  1}

mpsSysDebugUDPmsgsReceivedFromLC OBJECT-TYPE
    SYNTAX INTEGER
    ACCESS read-only
    STATUS mandatory
    DESCRIPTION 
        "This object indicates the number of UDP messages that have been 
         received from the Local Controller.  If the local controller is
         sending messages and this object is not incrementing there is a
         networking problem in the command interface.  However, since UDP
         is not perfect, this need not exactly match the number of messages
         sent"
    REFERENCE   " -- "
 ::= { mpsSysDebugUDP  2}

mpsSysDebugUDPacksSentToLC OBJECT-TYPE
    SYNTAX INTEGER
    ACCESS read-only
    STATUS mandatory
    DESCRIPTION 
        "This object indicates the number of UDP messages that have been
         sent to the Local Controller.  If the MPS is sending messages and
         the local controller is not getting them then there may be a 
         networking problem.   "
    REFERENCE   " -- "
 ::= { mpsSysDebugUDP  3}

mpsSysDebugUDPnacksSentToLC OBJECT-TYPE
    SYNTAX INTEGER
    ACCESS read-only
    STATUS mandatory
    DESCRIPTION 
        "This object indicates the number of Nacks sent to the Local Controller
         by the MPS.  When messages are received that the MPS cannot process, the
         MPS may generate a Nack. "
    REFERENCE   " -- "
 ::= { mpsSysDebugUDP  4}

mpsSysDebugUDPloadMPSmsgsSentToCP OBJECT-TYPE
    SYNTAX INTEGER
    ACCESS read-only
    STATUS mandatory
    DESCRIPTION 
        "Internal Debug information.  Undocumented."
    REFERENCE   " -- "
 ::= { mpsSysDebugUDP  5}

mpsSysDebugUDPackMPSmsgsSentToLCT OBJECT-TYPE
    SYNTAX INTEGER
    ACCESS read-only
    STATUS mandatory
    DESCRIPTION 
        "Internal Debug information. Undocumented."
    REFERENCE   " -- "
 ::= { mpsSysDebugUDP  6}

mpsSysDebugUDPlctMsgQueueFullDetected OBJECT-TYPE
    SYNTAX INTEGER
    ACCESS read-only
    STATUS mandatory
    DESCRIPTION 
        "Internal Debug Information.  Undocumented."
    REFERENCE   " -- "
 ::= { mpsSysDebugUDP  7}

mpsSysDebugUDPcpMsgQueueFullDetected OBJECT-TYPE
    SYNTAX INTEGER
    ACCESS read-only
    STATUS mandatory
    DESCRIPTION 
        "Internal Debug information .  Undocumented. "
    REFERENCE   " -- "
 ::= { mpsSysDebugUDP  8}

mpsSysDebugUDPreportbacksSent OBJECT-TYPE
    SYNTAX INTEGER
    ACCESS read-only
    STATUS mandatory
    DESCRIPTION 
        "This object indicates the number of reportbacks sent by the MPS to
         the local controller.  If reportbacks are being sent and are not being
         received then their may be a networking problem."
    REFERENCE   " -- "
 ::= { mpsSysDebugUDP  9}

mpsSysDebugUDPcorrectAcksReceived OBJECT-TYPE
    SYNTAX INTEGER
    ACCESS read-only
    STATUS mandatory
    DESCRIPTION 
        "This object indicates the number of Acks received by the MPS that
         the MPS considers correct in format and content. "
    REFERENCE   " -- "
 ::= { mpsSysDebugUDP  10}

mpsSysDebugUDPcorrectNacksReceived OBJECT-TYPE
    SYNTAX INTEGER
    ACCESS read-only
    STATUS mandatory
    DESCRIPTION 
        "This object indicates the number of Nacks received by the MPS that
         the MPS considers correct in format and content. "
    REFERENCE   " -- "
 ::= { mpsSysDebugUDP  11}

mpsSysDebugUDPacksReceived OBJECT-TYPE
    SYNTAX INTEGER
    ACCESS read-only
    STATUS mandatory
    DESCRIPTION 
        "This object indicates the total number of acks received by the MPS "
    REFERENCE   " -- "
 ::= { mpsSysDebugUDP  12}

mpsSysDebugUDPnacksReceived OBJECT-TYPE
    SYNTAX INTEGER
    ACCESS read-only
    STATUS mandatory
    DESCRIPTION 
        "This object indicates the total number of Nacks received by the MPS "
    REFERENCE   " -- "
 ::= { mpsSysDebugUDP  13}

mpsSysDebugUDPretriesLastReportback OBJECT-TYPE
    SYNTAX INTEGER
    ACCESS read-only
    STATUS mandatory
    DESCRIPTION 
        "This object indicates the number of retries the MPS made on the last
         reportback sent.  "
    REFERENCE   " -- "
 ::= { mpsSysDebugUDP  14}

mpsSysDebugUDPretriesTotal OBJECT-TYPE
    SYNTAX INTEGER
    ACCESS read-only
    STATUS mandatory
    DESCRIPTION 
        "This object indicates the number of retries the MPS has made since it
         was last rebooted.  "
    REFERENCE   " -- "
 ::= { mpsSysDebugUDP  15}

mpsSysStatusSystemTime OBJECT-TYPE
    SYNTAX INTEGER
    ACCESS read-only
    STATUS mandatory
    DESCRIPTION 
        "The value of this object is the System Time the MPS 
         is using for commands and encryption purposes.  The time is the MPSs
         internal time.  The MPS maintains an internal time that it uses
         to start and stop Load MPS Commands.  The internal time is initialized 
         when the MPS gets its first time update from the designated
         mpsSysConfTimeSource.  The internal time is then compared to each time
         update from the time source and corrections are made to keep the 
         internal time consistent with the Time Source.  
         The system time is reported in GPS seconds.  To determine the
         MPSs system time in UTC the mpsSysConfUTCoffset object must also
         be read and used in the calculation."
    REFERENCE   " -- "
::= { mpsSysStatusTime 1 }

mpsSysStatusMACAddress OBJECT-TYPE
    SYNTAX  DisplayString
    ACCESS  read-only
    STATUS  mandatory
    DESCRIPTION 
        "This is the MAC address of the MPS System Controller board.  
         It is set at the factory and cannot be changed."
    REFERENCE   " -- "
::= { mpsSysStatus 2}

mpsSysStatusSlotTable OBJECT-TYPE
    SYNTAX SEQUENCE OF MpsSysStatusSlotEntry
    ACCESS not-accessible
    STATUS mandatory
    DESCRIPTION  
        "A table of slot population of the mps.
         The StatusSlotTable is developed by the MPS at
         initialization based upon what cards are actually
         installed in the MPS.  Differences between this 
         table and the ConfSlotTable indicate that the MPS
         is not properly configured for its product designation
         and may result in the MPS not configuring or producing
         configuration errors."
    REFERENCE" - - - "
::= { mpsSysStatus 3}

mpsSysStatusSlotEntry OBJECT-TYPE
    SYNTAX MpsSysStatusSlotEntry
    ACCESS not-accessible
    STATUS mandatory
    INDEX {mpsSysStatusSlotNumber}
::= { mpsSysStatusSlotTable 1}

MpsSysStatusSlotEntry ::= SEQUENCE
    {
     mpsSysStatusSlotNumber             INTEGER,
     mpsSysStatusSlotModuleId           INTEGER,
     mpsSysStatusSlotModuleMCN          INTEGER,
     mpsSysStatusSlotSoftwareCRC        INTEGER,
     mpsSysStatusSlotSoftwareRev        DisplayString,
     mpsSysStatusSlotBootCodeRev        DisplayString,
     mpsSysStatusSlotSoftwarePath       DisplayString,
     mpsSysStatusSlotModuleConfigured   INTEGER
    }

mpsSysStatusSlotNumber OBJECT-TYPE
    SYNTAX INTEGER (1..8)
    ACCESS not-accessible
    STATUS mandatory
    DESCRIPTION  
        "The Slot Number.  The MPS may contain
         cards in each of its 8 slots."
    REFERENCE " -- "
::= { mpsSysStatusSlotEntry 1}

mpsSysStatusSlotModuleId OBJECT-TYPE
    SYNTAX INTEGER 
    ACCESS read-only
    STATUS mandatory
    DESCRIPTION  
        "The Module Id of the installed Card"
    REFERENCE " -- "
::= { mpsSysStatusSlotEntry 2}

mpsSysStatusSlotModuleMCN OBJECT-TYPE
    SYNTAX INTEGER
    ACCESS read-only
    STATUS mandatory
    DESCRIPTION  
        "The MCN Number of the module"
    REFERENCE " -- "
::= { mpsSysStatusSlotEntry 3}

mpsSysStatusSlotSoftwareCRC OBJECT-TYPE
    SYNTAX INTEGER
    ACCESS read-only
    STATUS mandatory
    DESCRIPTION  
        "The Software CRC"
    REFERENCE " -- "
::= { mpsSysStatusSlotEntry 4}

mpsSysStatusSlotSoftwareRev OBJECT-TYPE
    SYNTAX DisplayString
    ACCESS read-only
    STATUS mandatory
    DESCRIPTION  
        "The Software Revision Level"
    REFERENCE " -- "
::= { mpsSysStatusSlotEntry 5}

mpsSysStatusSlotBootCodeRev OBJECT-TYPE
    SYNTAX DisplayString
    ACCESS read-only
    STATUS mandatory
    DESCRIPTION  
        "The Boot Code Revision Level"
    REFERENCE " -- "
::= { mpsSysStatusSlotEntry 6}

mpsSysStatusSlotSoftwarePath OBJECT-TYPE
    SYNTAX DisplayString
    ACCESS read-only
    STATUS mandatory
    DESCRIPTION  
        "The Software File Path of the code that is 
         loaded on the functional module"
    REFERENCE " -- "
::= { mpsSysStatusSlotEntry 7}

mpsSysStatusSlotModuleConfigured OBJECT-TYPE
    SYNTAX INTEGER
    ACCESS read-only
    STATUS mandatory
    DESCRIPTION  
        "The Configured status of the module.  0=not configured; 1=configured."
    REFERENCE " -- "
::= { mpsSysStatusSlotEntry 8}

mpsSysStatusErrorSummaryTable OBJECT-TYPE
    SYNTAX SEQUENCE OF MpsSysStatusErrorSummaryEntry
    ACCESS not-accessible
    STATUS mandatory
    DESCRIPTION  
        "A table of Module and backplane communication
         errors/failures.  This is meant to provide more detail
         than is in an alarm and direct the user to even
         more detail to be found in module specific status."
    REFERENCE" - - - "
::= { mpsSysStatus 4}

mpsSysStatusErrorSummaryEntry OBJECT-TYPE
    SYNTAX MpsSysStatusErrorSummaryEntry
    ACCESS not-accessible
    STATUS mandatory
    INDEX {mpsErrorSummaryIndex}
::= { mpsSysStatusErrorSummaryTable 1}

MpsSysStatusErrorSummaryEntry ::= SEQUENCE
    {
     mpsErrorSummaryIndex           INTEGER,
     mpsErrorSummaryGpsTimeLogged   INTEGER,
     mpsErrorSummaryCleared         INTEGER,
     mpsErrorSummaryGpsTimeCleared  INTEGER,
     mpsErrorSummaryModuleId        INTEGER,
     mpsErrorSummarySlot            INTEGER,
     mpsErrorSummaryChannel         INTEGER,
     mpsErrorSummaryCode            INTEGER
    }

mpsErrorSummaryIndex OBJECT-TYPE
    SYNTAX INTEGER
    ACCESS not-accessible
    STATUS mandatory
    DESCRIPTION  
        "The index into the table."
    REFERENCE " -- "
::= { mpsSysStatusErrorSummaryEntry 1}

mpsErrorSummaryGpsTimeLogged OBJECT-TYPE
    SYNTAX INTEGER 
    ACCESS read-only
    STATUS mandatory
    DESCRIPTION  
        "The GPS time at which the error was logged.
         Time of zero indicates the MPS did not have
         source time when the error was logged."
    REFERENCE " -- "
::= { mpsSysStatusErrorSummaryEntry 2}

mpsErrorSummaryCleared OBJECT-TYPE
    SYNTAX INTEGER 
    ACCESS read-only
    STATUS mandatory
    DESCRIPTION  
        "Flag to indicate that the error was cleared.
         O=FALSE=not clear; 1=TRUE=cleared"
    REFERENCE " -- "
::= { mpsSysStatusErrorSummaryEntry 3}

mpsErrorSummaryGpsTimeCleared OBJECT-TYPE
    SYNTAX INTEGER 
    ACCESS read-only
    STATUS mandatory
    DESCRIPTION  
        "The GPS time at which the error was cleared.
         Time of zero indicates the MPS did not have
         source time when the error was cleared."
    REFERENCE " -- "
::= { mpsSysStatusErrorSummaryEntry 4}

mpsErrorSummaryModuleId OBJECT-TYPE
    SYNTAX INTEGER 
    ACCESS read-only
    STATUS mandatory
    DESCRIPTION  
        "The Module Id of the card that generated the
         error or to which the error relates."
    REFERENCE " -- "
::= { mpsSysStatusErrorSummaryEntry 5}

mpsErrorSummarySlot OBJECT-TYPE
    SYNTAX INTEGER 
    ACCESS read-only
    STATUS mandatory
    DESCRIPTION  
        "The slot of the card to which the
         error relates.  This may not be the
         same as the slot of the ModuleId
         listed above."
    REFERENCE " -- "
::= { mpsSysStatusErrorSummaryEntry 6}

mpsErrorSummaryChannel OBJECT-TYPE
    SYNTAX INTEGER 
    ACCESS read-only
    STATUS mandatory
    DESCRIPTION  
        "If applicable, the channel to which the
         error relates."
    REFERENCE " -- "
::= { mpsSysStatusErrorSummaryEntry 7}

mpsErrorSummaryCode OBJECT-TYPE
    SYNTAX INTEGER 
    ACCESS read-only
    STATUS mandatory
    DESCRIPTION  
        "The error code."
    REFERENCE " -- "
::= { mpsSysStatusErrorSummaryEntry 8}


mpsSysStatusCommandsActive OBJECT-TYPE
    SYNTAX INTEGER
    ACCESS read-only
    STATUS mandatory
    DESCRIPTION 
        "The value of this object is number of LOAD MPS 
         commands currently active.  A Load MPS command is
         considered to be active if it is past its start time
         but has not yet reached its stop time."
    REFERENCE   " -- "
::= { mpsSysStatusCommands 1 }

mpsSysStatusCommandsWaiting OBJECT-TYPE
    SYNTAX INTEGER
    ACCESS read-only
    STATUS mandatory
    DESCRIPTION 
        "The value of this object is number of LOAD MPS 
         commands currently waiting to execute.  Commands
         counted here have not yet reached their start time."
    REFERENCE   " -- "
::= { mpsSysStatusCommands 2 }

mpsSysStatusBlocksAvailable OBJECT-TYPE
    SYNTAX INTEGER
    ACCESS read-only
    STATUS mandatory
    DESCRIPTION 
        "The value of this object is amount of free memory 
         blocks available for Load MPS commands.  Each block
         contains 64 bytes of storage space. "
    REFERENCE   " -- "
::= { mpsSysStatusCommands 3 }

mpsSysStatusBlocksTotal OBJECT-TYPE
    SYNTAX INTEGER
    ACCESS read-only
    STATUS mandatory
    DESCRIPTION 
        "The value of this object is the total amount of 
         memory blocks available for Load MPS Commands." 
    REFERENCE   " -- "
::= { mpsSysStatusCommands 4 }

mpsSysStatusLoadMPSTable OBJECT-TYPE
    SYNTAX SEQUENCE OF MpsSysStatusLoadMPSEntry
    ACCESS not-accessible
    STATUS mandatory
    DESCRIPTION
        "A table of LOAD MPS Command status information.
         This table contains status information on every command
         currently stored within the MPS.  The table is ordered in
         such a way as the dependencies of Load MPS Commands can be
         extracted and a tree of commands can be created.  Commands
         that are not dependent upon other commands have a level of
         0.  Commands that are at the top of a dependency tree have
         a level of 1.  The structure of the rest of the dependency tree
         can be determined by the order of the entries to the table. The
         entries are ordered as if doing a depth first decent of
         the tree with the depth of each command indicated by its level.
         Therefore, if a command has a level other than 0 or 1 then
         the first previous command that has a level 1 less than it
         is the command to which it is dependent.
         Example:
         This partial table
 
           Index  Level ... sequenceNumber ...
            1        0             1
            2        1             2
            3        2             3
            4        3             4
            5        2             5
            6        1             6
            7        2             7
 
         translates to these trees of sequence numbers
                2           6
               / \          |
              3   5         7
            /
           4
 
         with sequence number 1 existing on its own not part of a tree.
         "
::= { mpsSysStatus 7}
 
mpsSysStatusLoadMPSEntry OBJECT-TYPE
    SYNTAX MpsSysStatusLoadMPSEntry
    ACCESS not-accessible
    STATUS mandatory
    INDEX {mpsSysStatusLoadMPSindex}
::= { mpsSysStatusLoadMPSTable 1}

MpsSysStatusLoadMPSEntry ::= SEQUENCE
    {
     mpsSysStatusLoadMPSindex                INTEGER,
     mpsSysStatusLoadMPSlevel                INTEGER,
     mpsSysStatusLoadMPSstate                INTEGER,
     mpsSysStatusLoadMPSsubState             INTEGER,
     mpsSysStatusLoadMPSsequenceNumber       INTEGER,
     mpsSysStatusLoadMPSsubcommandId         INTEGER,
     mpsSysStatusLoadMPSsubcommandErrorCode  INTEGER,
     mpsSysStatusLoadMPSsubcommandRetryCount INTEGER,
     mpsSysStatusLoadMPScommandBlock1        DisplayString
    }

mpsSysStatusLoadMPSindex OBJECT-TYPE
    SYNTAX INTEGER 
    ACCESS not-accessible
    STATUS mandatory
    DESCRIPTION  
        "The index of the Load MPS"
    REFERENCE " -- "
::= { mpsSysStatusLoadMPSEntry 1}

mpsSysStatusLoadMPSlevel OBJECT-TYPE
    SYNTAX INTEGER 
    ACCESS read-only
    STATUS mandatory
    DESCRIPTION  
        "The level of the command in the tree of load MPS
         commands."
    REFERENCE " -- "
::= { mpsSysStatusLoadMPSEntry 2}

mpsSysStatusLoadMPSstate OBJECT-TYPE
    SYNTAX INTEGER 
        { 
         waitingForStart (1),
         executing       (2),
         waitingForStop  (3),
         deleting        (4),
         error           (5)
        }
    ACCESS read-only
    STATUS mandatory
    DESCRIPTION  
        "The current state of the Command.  "
    REFERENCE " -- "
::= { mpsSysStatusLoadMPSEntry 3}

mpsSysStatusLoadMPSsubState OBJECT-TYPE
    SYNTAX INTEGER 
        { 
         none                      (1),
         deletingDependants        (2),
         waitingForDependantDelete (3),
         waitingForAck             (4),
         waitingForResponse        (5),
         suspended                 (6),
         waitingForExtractAck      (7),
         waitingForExtractData     (8),
         waitingForValidInputPsi   (9),
         reserved10                (10),
         rebooting                 (11),
         deletingInactive          (12),
         deletingActive            (13),
         deletingSuspended         (14),
         deletedAll                (15),
         deletingOne               (16)
        }
    ACCESS read-only
    STATUS mandatory
    DESCRIPTION  
        "The current substate of the command.  
         Command specific"
    REFERENCE " -- "
::= { mpsSysStatusLoadMPSEntry 4}

mpsSysStatusLoadMPSsequenceNumber OBJECT-TYPE
    SYNTAX INTEGER 
    ACCESS read-only
    STATUS mandatory
    DESCRIPTION  
        "The sequence number from the LOAD MPS Message"
    REFERENCE " -- "
::= { mpsSysStatusLoadMPSEntry 5}

mpsSysStatusLoadMPSsubcommandId OBJECT-TYPE
    SYNTAX INTEGER (1..4)
    ACCESS read-only
    STATUS mandatory
    DESCRIPTION  
        "The subcommand id from the load MPS Message"
    REFERENCE " -- "
::= { mpsSysStatusLoadMPSEntry 6}

mpsSysStatusLoadMPSsubcommandErrorCode OBJECT-TYPE
    SYNTAX INTEGER
    ACCESS read-only
    STATUS mandatory
    DESCRIPTION  
        "The error code for the error causing retry of the load MPS Message"
    REFERENCE " -- "
::= { mpsSysStatusLoadMPSEntry 7}

mpsSysStatusLoadMPSsubcommandRetryCount OBJECT-TYPE
    SYNTAX INTEGER
    ACCESS read-only
    STATUS mandatory
    DESCRIPTION  
        "The number of retries of the load MPS Message"
    REFERENCE " -- "
::= { mpsSysStatusLoadMPSEntry 8}

mpsSysStatusLoadMPScommandBlock1 OBJECT-TYPE
    SYNTAX      DisplayString
    ACCESS read-only
    STATUS mandatory
    DESCRIPTION 
        "This object contains the text of block 1 (up to 255 bytes)
         of a LOAD MPS command.  Additional blocks are not currently
         accessible. "
    REFERENCE   " -- "
::= { mpsSysStatusLoadMPSEntry 9 }

mpsSysStatusEnvAmbientTemp1 OBJECT-TYPE
    SYNTAX INTEGER 
    ACCESS read-only
    STATUS mandatory
    DESCRIPTION 
         "The ambient temp of temp sensor 1 in degrees C."
    REFERENCE   " -- "
 ::= { mpsSysStatusEnvironment 1 }

mpsSysStatusEnvAmbientTemp2 OBJECT-TYPE
    SYNTAX INTEGER 
    ACCESS read-only
    STATUS mandatory
    DESCRIPTION 
         "The ambient temp of temp sensor 2 in degrees C."
    REFERENCE   " -- "
 ::= { mpsSysStatusEnvironment 2 }

mpsSysStatusEnvPowerTemp OBJECT-TYPE
    SYNTAX INTEGER 
    ACCESS read-only
    STATUS mandatory
    DESCRIPTION 
         "The ambient temp of power supply temp sensor in degrees C."
    REFERENCE   " -- "
 ::= { mpsSysStatusEnvironment 3 }

mpsSysStatusEnvFanAsetting OBJECT-TYPE
    SYNTAX INTEGER { high(1),
     low(2) }
    ACCESS read-only
    STATUS mandatory
    DESCRIPTION 
         "The setting of Fan bank A."
    REFERENCE   " -- "
 ::= { mpsSysStatusEnvironment 4 }

mpsSysStatusEnvFanBsetting OBJECT-TYPE
    SYNTAX INTEGER { high(1),
     low(2),
     off(3) }
    ACCESS read-only
    STATUS mandatory
    DESCRIPTION 
         "The setting of Fan bank B."
    REFERENCE   " -- "
 ::= { mpsSysStatusEnvironment 5 }

mpsSysStatusInsertionQueueTable OBJECT-TYPE
    SYNTAX SEQUENCE OF MpsSysStatusInsertionQueueEntry
    ACCESS not-accessible
    STATUS mandatory
    DESCRIPTION  
        "A table of Insertion Queue subqueue information. This table 
     shows what messages the MPS is currently inserting for each 
     output.  The slot number, message type, sequence number, pid, 
     service number, start time, and stop time are shown. This table 
     is indexed by output id, subqueue id and slot number. For each 
     index the message type and sequence number are provided."
::= { mpsSysStatus 8}

mpsSysStatusInsertionQueueEntry OBJECT-TYPE
    SYNTAX MpsSysStatusInsertionQueueEntry
    ACCESS not-accessible
    STATUS mandatory
    INDEX {mpsSysStatusSubqueueOutputId,mpsSysStatusSubqueueIndex,mpsSysStatusSubqueueSlotNumber}
::= { mpsSysStatusInsertionQueueTable 1}

MpsSysStatusInsertionQueueEntry ::= SEQUENCE
    {
     mpsSysStatusSubqueueOutputId         INTEGER,
     mpsSysStatusSubqueueIndex            INTEGER,
     mpsSysStatusSubqueueSlotNumber       INTEGER,
     mpsSysStatusMessageType              INTEGER,
     mpsSysStatusInsLoadMPSsequenceNumber INTEGER,
     mpsSysStatusPid                  INTEGER,
     mpsSysStatusServiceNumber            INTEGER,
     mpsSysStatusStartTime            INTEGER,
     mpsSysStatusStopTime             INTEGER
    }

mpsSysStatusSubqueueOutputId OBJECT-TYPE
    SYNTAX INTEGER 
    ACCESS not-accessible
    STATUS mandatory
    DESCRIPTION  
        "The output id index.  "
    REFERENCE " -- "
::= { mpsSysStatusInsertionQueueEntry 1}

mpsSysStatusSubqueueIndex OBJECT-TYPE
    SYNTAX INTEGER 
    ACCESS not-accessible
    STATUS mandatory
    DESCRIPTION  
        "The Index of the Subqueue"
    REFERENCE " -- "
::= { mpsSysStatusInsertionQueueEntry 2}

mpsSysStatusSubqueueSlotNumber OBJECT-TYPE
    SYNTAX INTEGER 
    ACCESS not-accessible
    STATUS mandatory
    DESCRIPTION  
        "The slot number of the Subqueue.  This index is one
         greater than the actual slot number.  Subtract one when
         displaying."
    REFERENCE " -- "
::= { mpsSysStatusInsertionQueueEntry 3}

mpsSysStatusMessageType OBJECT-TYPE
    SYNTAX INTEGER (0..255)
    ACCESS read-only
    STATUS mandatory
    DESCRIPTION  
        "The message type of the message being inserted"
    REFERENCE " -- "
::= { mpsSysStatusInsertionQueueEntry 4}

mpsSysStatusInsLoadMPSsequenceNumber OBJECT-TYPE
    SYNTAX INTEGER
    ACCESS read-only
    STATUS mandatory
    DESCRIPTION  
        "The LOAD MPS sequence number of the command 
         responsible for the insert"
    REFERENCE " -- "
::= { mpsSysStatusInsertionQueueEntry 5}

mpsSysStatusPid OBJECT-TYPE
    SYNTAX INTEGER (0..8191)
    ACCESS read-only
    STATUS mandatory
    DESCRIPTION  
        "The PID of the message being inserted"
    REFERENCE " -- "
::= { mpsSysStatusInsertionQueueEntry 6}

mpsSysStatusServiceNumber OBJECT-TYPE
    SYNTAX INTEGER (0..65535)
    ACCESS read-only
    STATUS mandatory
    DESCRIPTION  
        "The Service Number of the message being inserted. Service
         number is 0 for all non-Service related messags (messages
         that are inserted on Ancillary Subqueues)."
    REFERENCE " -- "
::= { mpsSysStatusInsertionQueueEntry 7}

mpsSysStatusStartTime OBJECT-TYPE
    SYNTAX INTEGER
    ACCESS read-only
    STATUS mandatory
    DESCRIPTION  
        "The Start Time of the message. This is the time that the
         message is inserted into the Output transport stream."
    REFERENCE " -- "
::= { mpsSysStatusInsertionQueueEntry 8}

mpsSysStatusStopTime OBJECT-TYPE
    SYNTAX INTEGER
    ACCESS read-only
    STATUS mandatory
    DESCRIPTION  
        "The Stop Time of the message. This is the time that the
         message is removed from the Output transport stream."
    REFERENCE " -- "
::= { mpsSysStatusInsertionQueueEntry 9}

mpsSysStatusPsiTable OBJECT-TYPE
    SYNTAX SEQUENCE OF MpsSysStatusPsiEntry
    ACCESS not-accessible
    STATUS mandatory
    DESCRIPTION  
        "The following table contains a list of messages that are either being extracted
         from the input side or being inserted to the output side of the mps.  On the
         input side all extracted messages that are being used by the MPS are displayed.
         On the output side, only PATs, PMTs, and CATs are displayed.  These messages
         were either given to the mps when it is in external mode or created by the mps
         when it is in internal mode."
::= { mpsSysStatus 9}

mpsSysStatusPsiEntry OBJECT-TYPE
    SYNTAX MpsSysStatusPsiEntry
    ACCESS not-accessible
    STATUS mandatory
    INDEX {mpsSysStatusPsiTableType, mpsSysStatusPsiId, mpsSysStatusPsiPid, mpsSysStatusPsiMessageType,
           mpsSysStatusPsiServiceNumber, mpsSysStatusPsiSegment, mpsSysStatusPsiPart}
::= { mpsSysStatusPsiTable 1}

MpsSysStatusPsiEntry ::= SEQUENCE
    {
     mpsSysStatusPsiTableType     INTEGER,
     mpsSysStatusPsiId            INTEGER,
     mpsSysStatusPsiPid           INTEGER,
     mpsSysStatusPsiMessageType   INTEGER,
     mpsSysStatusPsiServiceNumber INTEGER,
     mpsSysStatusPsiSegment       INTEGER,
     mpsSysStatusPsiPart          INTEGER,
     mpsSysStatusPsiBody          DisplayString
    }

mpsSysStatusPsiTableType OBJECT-TYPE
    SYNTAX INTEGER {
       inputPsiTable (1),
       outputPsiTable (2),
       unknownPsiTable (3)
     } 
    ACCESS not-accessible
    STATUS mandatory
    DESCRIPTION  
        "Indicates whether this message comes from the input or output side of the mps."
    REFERENCE " -- "
::= { mpsSysStatusPsiEntry 1}

mpsSysStatusPsiId OBJECT-TYPE
    SYNTAX INTEGER (0..65535)
    ACCESS not-accessible
    STATUS mandatory
    DESCRIPTION  
        "Indicates the input or output id for which this message applies"
    REFERENCE " -- "
::= { mpsSysStatusPsiEntry 2}

mpsSysStatusPsiPid OBJECT-TYPE
    SYNTAX INTEGER (0..8191)
    ACCESS not-accessible
    STATUS mandatory
    DESCRIPTION  
        "Indicates the Pid that this message is contained in."
    REFERENCE " -- "
::= { mpsSysStatusPsiEntry 3}

mpsSysStatusPsiMessageType OBJECT-TYPE
    SYNTAX INTEGER (0..255)
    ACCESS not-accessible
    STATUS mandatory
    DESCRIPTION  
        "Indicates the message type of this message"
    REFERENCE " -- "
::= { mpsSysStatusPsiEntry 4}

mpsSysStatusPsiServiceNumber OBJECT-TYPE
    SYNTAX INTEGER 
    ACCESS not-accessible
    STATUS mandatory
    DESCRIPTION  
        "Indicates the Service Number which this message is part of.  When a
         message is not specifically related to a service, this value is 0."
    REFERENCE " -- "
::= { mpsSysStatusPsiEntry 5}

mpsSysStatusPsiSegment OBJECT-TYPE
    SYNTAX INTEGER 
    ACCESS not-accessible
    STATUS mandatory
    DESCRIPTION  
        "Indicates the segment number of this message.  Useful for PAT messages.  
         Otherwise this is 0."
    REFERENCE " -- "
::= { mpsSysStatusPsiEntry 6}

mpsSysStatusPsiPart OBJECT-TYPE
    SYNTAX INTEGER 
    ACCESS not-accessible
    STATUS mandatory
    DESCRIPTION  
        " Since a message can be 1024 bytes long the message may divided into parts.
          Each part of the message is indexed using this index."
    REFERENCE " -- "
::= { mpsSysStatusPsiEntry 7}

mpsSysStatusPsiBody OBJECT-TYPE
    SYNTAX DisplayString 
    ACCESS read-only
    STATUS mandatory
    DESCRIPTION  
        "  "
    REFERENCE " -- "
::= { mpsSysStatusPsiEntry 8}

mpsSysStatusPidTable OBJECT-TYPE
    SYNTAX SEQUENCE OF MpsSysStatusPidEntry
    ACCESS not-accessible
    STATUS mandatory
    DESCRIPTION  
        "This Table is NOT YET IMPLEMENTED."
::= { mpsSysStatus 10}

mpsSysStatusPidEntry OBJECT-TYPE
    SYNTAX MpsSysStatusPidEntry
    ACCESS not-accessible
    STATUS mandatory
    INDEX {mpsSysStatusPidOutputId, mpsSysStatusPidOutputPid} 
::= { mpsSysStatusPidTable 1}

MpsSysStatusPidEntry ::= SEQUENCE
    {
     mpsSysStatusPidOutputId              INTEGER,
     mpsSysStatusPidOutputPid             INTEGER,
     mpsSysStatusPidType                  INTEGER,
     mpsSysStatusPidPidType               INTEGER,
     mpsSysStatusPidStreamType            INTEGER,
     mpsSysStatusPidInputId               INTEGER,
     mpsSysStatusPidInputPid              INTEGER,
     mpsSysStatusPidInputServiceNumber    INTEGER
    }

mpsSysStatusPidOutputId OBJECT-TYPE
    SYNTAX INTEGER 
    ACCESS not-accessible
    STATUS mandatory
    DESCRIPTION  
        "  "
    REFERENCE " -- "
::= { mpsSysStatusPidEntry 1}

mpsSysStatusPidOutputPid OBJECT-TYPE
    SYNTAX INTEGER 
    ACCESS not-accessible
    STATUS mandatory
    DESCRIPTION  
        "  "
    REFERENCE " -- "
::= { mpsSysStatusPidEntry 2}

mpsSysStatusPidType OBJECT-TYPE
    SYNTAX INTEGER 
    ACCESS read-only
    STATUS mandatory
    DESCRIPTION  
        "  "
    REFERENCE " -- "
::= { mpsSysStatusPidEntry 3}

mpsSysStatusPidPidType OBJECT-TYPE
    SYNTAX INTEGER 
    ACCESS read-only
    STATUS mandatory
    DESCRIPTION  
        "  "
    REFERENCE " -- "
::= { mpsSysStatusPidEntry 4}

mpsSysStatusPidStreamType OBJECT-TYPE
    SYNTAX INTEGER 
    ACCESS read-only
    STATUS mandatory
    DESCRIPTION  
        "  "
    REFERENCE " -- "
::= { mpsSysStatusPidEntry 5}

mpsSysStatusPidInputId OBJECT-TYPE
    SYNTAX INTEGER 
    ACCESS read-only
    STATUS mandatory
    DESCRIPTION  
        "  "
    REFERENCE " -- "
::= { mpsSysStatusPidEntry 6}

mpsSysStatusPidInputPid OBJECT-TYPE
    SYNTAX INTEGER 
    ACCESS read-only
    STATUS mandatory
    DESCRIPTION  
        "  "
    REFERENCE " -- "
::= { mpsSysStatusPidEntry 7}

mpsSysStatusPidInputServiceNumber OBJECT-TYPE
    SYNTAX INTEGER 
    ACCESS read-only
    STATUS mandatory
    DESCRIPTION  
        "  "
    REFERENCE " -- "
::= { mpsSysStatusPidEntry 8}

mpsSysStatusOutputServiceTable OBJECT-TYPE
    SYNTAX SEQUENCE OF MpsSysStatusOutputServiceEntry
    ACCESS not-accessible
    STATUS mandatory
    DESCRIPTION  
        "This table shows what services on what inputs are being
         remapped to what services on what outputs."
::= { mpsSysStatus 11}

mpsSysStatusOutputServiceEntry OBJECT-TYPE
    SYNTAX MpsSysStatusOutputServiceEntry
    ACCESS not-accessible
    STATUS mandatory
    INDEX {mpsSysStatusOutputServiceOutputId, mpsSysStatusOutputServiceOutputProgramNumber} 
::= { mpsSysStatusOutputServiceTable 1}

MpsSysStatusOutputServiceEntry ::= SEQUENCE
    {
     mpsSysStatusOutputServiceOutputId              INTEGER,
     mpsSysStatusOutputServiceOutputProgramNumber   INTEGER,
     mpsSysStatusOutputServiceInputId               INTEGER,
     mpsSysStatusOutputServiceInputProgramNumber    INTEGER,
     mpsSysStatusOutputServiceState                 INTEGER,
     mpsSysStatusOutputServiceDSseqNumber           INTEGER,
     mpsSysStatusOutputServicePsipState             INTEGER
    }

mpsSysStatusOutputServiceOutputId OBJECT-TYPE
    SYNTAX INTEGER 
    ACCESS not-accessible
    STATUS mandatory
    DESCRIPTION  
        "Logical Output ID of of output service "
    REFERENCE " -- "
::= { mpsSysStatusOutputServiceEntry 1}

mpsSysStatusOutputServiceOutputProgramNumber OBJECT-TYPE
    SYNTAX INTEGER 
    ACCESS not-accessible
    STATUS mandatory
    DESCRIPTION  
        "Output MPEG Program Number assigned to this service "
    REFERENCE " -- "
::= { mpsSysStatusOutputServiceEntry 2}

mpsSysStatusOutputServiceInputId OBJECT-TYPE
    SYNTAX INTEGER 
    ACCESS read-only
    STATUS mandatory
    DESCRIPTION  
        "Logical Input ID of input service assigned  "
    REFERENCE " -- "
::= { mpsSysStatusOutputServiceEntry 3}

mpsSysStatusOutputServiceInputProgramNumber OBJECT-TYPE
    SYNTAX INTEGER 
    ACCESS read-only
    STATUS mandatory
    DESCRIPTION  
        "Input MPEG Program Number of input service "
    REFERENCE " -- "
::= { mpsSysStatusOutputServiceEntry 4}

mpsSysStatusOutputServiceState OBJECT-TYPE
    SYNTAX INTEGER
    {
     outputserviceUndefined      (1),
     outputServiceDefined        (2),
     serviceMappingDefined       (3),
     waitingForInitialInputPAT   (4),
     waitingForPATnoPMTfound     (5),
     waitingForInputPMT          (6),
     errorInputPIDsAlreadyMapped (7),
     errorMaxComponentsExceeded  (8),
     errorInvalidPCRPIDinPMT     (9),
     startingServicePassthru     (10),
     startingPIDremultiplexing   (11),
     startingPIDPassthru         (12),
     passingthruInputService     (13),
     remultiplexingInputPIDs     (14),
     passingthruInputPIDs        (15),
     stoppingServicePassthru     (16),
     stoppingPIDremultiplexing   (17),
     stoppingPIDpassthru         (18)
    }
    ACCESS read-only
    STATUS mandatory
    DESCRIPTION  
        "Current Service State "
    REFERENCE " -- "
::= { mpsSysStatusOutputServiceEntry 5}

mpsSysStatusOutputServiceDSseqNumber OBJECT-TYPE
    SYNTAX INTEGER 
    ACCESS read-only
    STATUS mandatory
    DESCRIPTION  
        "Load MPS Define Service command sequence number "
    REFERENCE " -- "
::= { mpsSysStatusOutputServiceEntry 6}

mpsSysStatusOutputServicePsipState OBJECT-TYPE
    SYNTAX INTEGER 
        {
         notApplicable               (1),
         incompleteWaitingForMGT     (2),
         incompleteWaitingForVCT     (3),
         incompleteWaitingForEIT     (4),
         psipFixingComplete          (5),
         errorEITPIDsAlreadyMapped   (6)
        }
    ACCESS read-only
    STATUS mandatory
    DESCRIPTION  
        "Current PSIP State"
    REFERENCE " -- "
::= { mpsSysStatusOutputServiceEntry 7}

mpsSysStatusSysContHwVersion OBJECT-TYPE
    SYNTAX INTEGER 
    ACCESS read-only
    STATUS mandatory
    DESCRIPTION 
         "The System Controller Board Hardware Version or MCN number."
    REFERENCE   " -- "
 ::= { mpsSysStatusSysHardware 1 }

mpsSysStatusSysContSifVersion OBJECT-TYPE
    SYNTAX INTEGER 
    ACCESS read-only
    STATUS mandatory
    DESCRIPTION 
         "The System Controller Board SIF PROM Version or MCN number."
    REFERENCE   " -- "
 ::= { mpsSysStatusSysHardware 2 }

mpsSysStatusBackplaneVersion OBJECT-TYPE
    SYNTAX INTEGER 
    ACCESS read-only
    STATUS mandatory
    DESCRIPTION 
         "The MPS System Chassis Backplane Version or MCN number."
    REFERENCE   " -- "
 ::= { mpsSysStatusSysHardware 3 }

mpsSysStatusSysContBootCodeVersion OBJECT-TYPE
    SYNTAX DisplayString
    ACCESS read-only
    STATUS mandatory
    DESCRIPTION  
        "The System Controller Boot Code Version"
    REFERENCE " -- "
::= { mpsSysStatusSysHardware 4}

mpsSysStatusPowerSupplyHwVersion OBJECT-TYPE
    SYNTAX INTEGER 
    ACCESS read-only
    STATUS mandatory
    DESCRIPTION  
        "The Power Supply Hardware Version or MCN number."
    REFERENCE " -- "
::= { mpsSysStatusSysHardware 5}


mpsSysConfLoadMpsSource OBJECT-TYPE
    SYNTAX INTEGER
        {
         local    (1),
         national (2)
        }
    ACCESS read-write
    STATUS mandatory
    DESCRIPTION
        "Selects whether the MPS will be receiving Load MPS commands from 
         Local or National controller.  Note that setting this parameter to
         Local when the MPS is configured in either secondary mode of National
         Control, mpsNationalControlConfig, is illegal and should be avoided. 
         Once written, a save must be performed via the mpsSysConfSaveConfig
         parameter and the MPS must be rebooted for the change to take effect."
    REFERENCE   " -- "
::= { mpsSysConfCommands 1}

mpsSysConfLoadMpsCommandRetryPeriod OBJECT-TYPE
    SYNTAX INTEGER
    ACCESS read-write
    STATUS mandatory
    DESCRIPTION
        "Number of seconds MPS will retry Load MPS commands before invalidating
         them and sending a reportback.  Note that not all errors will be result
         in a retry.  Some errors will result in immediate reportback and
         deletion.
         Once written, a save must be performed via the mpsSysConfSaveConfig
         parameter and the MPS must be rebooted for the change to take effect."
    REFERENCE   " -- "
::= { mpsSysConfCommands 2}


mpsNationalControlConfig OBJECT-TYPE
    SYNTAX INTEGER
        {
         disabled          (1),
         secondaryEthernet (2),
         secondaryRs530    (3),
         primaryEthernet   (4),
         primaryRs530      (5)
        }
    ACCESS read-write
    STATUS mandatory
    DESCRIPTION
        "Selects whether the MPS will be Primary or Secondary and whether
         the MPS will be using Ethernet or RS530 to transmit/receive the
         National Control Stream.  Note that setting this parameter to
         either secondary mode of operation while the mps is configured to
         receive commands from a Local Controller is illegal and should be 
         avoided.  Note also that other mpsSysConfNationalControl parameters
         either apply or do not apply based on the setting of this parameter. 
         Reference their descriptions for more information.
         Once written, a save must be performed via the mpsSysConfSaveConfig
         parameter and the MPS must be rebooted for the change to take effect."
    REFERENCE   " -- "
::= { mpsSysConfNationalControl 1}

mpsNationalControlEmmProvId OBJECT-TYPE
    SYNTAX INTEGER
    ACCESS read-write
    STATUS mandatory
    DESCRIPTION 
        "When in secondary or primary national control modes, this parameter
         specifies the EMM Provider ID of the EMM PID stream carrying the Load
         MPS Commands.  The MPS uses this parameter to derive the EMM PID and 
         to set up extraction of the Load MPS Commands.
         Once written, a save must be performed via the mpsSysConfSaveConfig
         parameter and the MPS must be rebooted for the change to take effect."
    REFERENCE   " -- "
::= { mpsSysConfNationalControl 2}

mpsNationalControlInputSlot OBJECT-TYPE
    SYNTAX INTEGER (1..8)
    ACCESS read-write
    STATUS mandatory
    DESCRIPTION 
        "Contains the Slot number of the input card from which the MPS should detunnel
         the National Control stream when the MPS is configured as the Primary MPS.  
         This parameter only applies when in a primary mode of operation.
         Once written, a save must be performed via the mpsSysConfSaveConfig
         parameter and the MPS must be rebooted for the change to take effect."
    REFERENCE   " -- "
::= { mpsSysConfNationalControl 3}

mpsNationalControlInputPort OBJECT-TYPE
    SYNTAX INTEGER
    ACCESS read-write
    STATUS mandatory
    DESCRIPTION 
        "Contains the Port number of the input card from which the MPS should detunnel
         the National Control stream when the MPS is configured as the Primary MPS.
         This parameter only applies when in a primary mode of operation.
         Once written, a save must be performed via the mpsSysConfSaveConfig
         parameter and the MPS must be rebooted for the change to take effect."
    REFERENCE   " -- "
::= { mpsSysConfNationalControl 4}

mpsNationalControlDetunneling OBJECT-TYPE
    SYNTAX INTEGER
        {
         pid     (1),
         service (2)
        }
    ACCESS read-write
    STATUS mandatory
    DESCRIPTION 
        "Determines whether the detunneling will be PID based or Service based.
         This parameter only applies when in a primary mode of operation.  When set
         to Service based, the MPS will derive the National Control stream ISO PID
         value from the PMT Message for the service specified in the 
         mpsNationalControlServiceNum parameter.  When set to PID based, the MPS
         will attempt to detunnel the PID specified by the mpsNationalControlPid
         parameter.
         Once written, a save must be performed via the mpsSysConfSaveConfig
         parameter and the MPS must be rebooted for the change to take effect."
    REFERENCE   " -- "
::= { mpsSysConfNationalControl 5}

mpsNationalControlServiceNum OBJECT-TYPE
    SYNTAX INTEGER
    ACCESS read-write
    STATUS mandatory
    DESCRIPTION 
        "Service number to use when deriving the ISO PID value for the National
         Control stream.  This parameter is only used if the mpsNationalControlDetunneling
         parameter is set to service based.  
         Once written, a save must be performed via the mpsSysConfSaveConfig
         parameter and the MPS must be rebooted for the change to take effect."
    REFERENCE   " -- "
::= { mpsSysConfNationalControl 6}

mpsNationalControlPid OBJECT-TYPE
    SYNTAX INTEGER
    ACCESS read-write
    STATUS mandatory
    DESCRIPTION 
        "PID number to detunnel.  This parameter is only used if the 
         mpsNationalControlDetunneling parameter is Pid based.
         Once written, a save must be performed via the mpsSysConfSaveConfig
         parameter and the MPS must be rebooted for the change to take effect."
    REFERENCE   " -- "
::= { mpsSysConfNationalControl 7}

mpsNationalControlDestIPAddress OBJECT-TYPE
    SYNTAX  IpAddress
    ACCESS  read-write
    STATUS  mandatory
    DESCRIPTION 
        "This parameter is not used."
    REFERENCE   " -- "
::= { mpsSysConfNationalControl 8}

mpsNationalControlMulticastMac OBJECT-TYPE
    SYNTAX  DisplayString
    ACCESS  read-write
    STATUS  mandatory
    DESCRIPTION 
        "This is the multicast MAC address for the detunneled National Control
         stream for an MPS that is using Ethernet.  When in primary mode, packets
         are sent using this address.  When in secondary mode, packets are 
         received that contain this address.
         Once written, a save must be performed via the mpsSysConfSaveConfig
         parameter and the MPS must be rebooted for the change to take effect."
    REFERENCE   " -- "
::= { mpsSysConfNationalControl 9}

mpsNationalControlUdpPort OBJECT-TYPE
    SYNTAX INTEGER
    ACCESS read-write
    STATUS mandatory
    DESCRIPTION 
        "This is the Ethernet UDP port for the detunneled National Control
         stream for an MPS that is using Ethernet.
         Once written, a save must be performed via the mpsSysConfSaveConfig
         parameter and the MPS must be rebooted for the change to take effect."
    REFERENCE   " -- "
::= { mpsSysConfNationalControl 10}


mpsNationalControlRestartCounter OBJECT-TYPE
    SYNTAX INTEGER 
    ACCESS read-only
    STATUS mandatory
    DESCRIPTION  
        "This parameter specifies the number of times that the National
         Control process has restarted.  Typically, two or three restarts
         occur during the initial acquisition period of the National Control
         stream.  Once aquired, restarts are an indication of errors in the
         stream resulting in loss of sync.  Restart events are counted in 
         both secondary and primary modes of operation."
    REFERENCE " -- "
::= { mpsSysStatusNationalControl 1}

mpsNationalControlPacketCounter OBJECT-TYPE
    SYNTAX INTEGER 
    ACCESS read-only
    STATUS mandatory
    DESCRIPTION  
        "This parameter is a count of the number of UDP packets processed
         by the National Control processing."
    REFERENCE " -- "
::= { mpsSysStatusNationalControl 2}

mpsNationalControlStreamPres OBJECT-TYPE
    SYNTAX INTEGER 
        { 
         notPresent (1),
         present    (2)
        }
    ACCESS read-only
    STATUS mandatory
    DESCRIPTION  
        "Indicates whether the National Control stream is present in the MPS.
         This status is reported by the D/E module performing the detunneling 
         operation."
    REFERENCE " -- "
::= { mpsSysStatusNationalControl 3}

mpsNationalControlManagerState OBJECT-TYPE
    SYNTAX INTEGER 
        {
          start                (1),
          ncmError             (2),
          idle                 (3),
          running              (4),
          wait                 (5),
          noWait               (6),
          waitForPat           (7),
          waitForPmt           (8),
          waitForCat           (9),
          noEmmPidFound        (10),
          noIsoServiceFound    (11),
          noServiceFound       (12),
          waitForMtcStopAck1   (13),
          waitForMtcSetupAck   (14),
          waitForMtcStartAck1  (15),
          waitForMtcStopAck2   (16),
          waitForMtcStopAck3   (17)
        }
    ACCESS read-only
    STATUS mandatory
    DESCRIPTION  
        "State of the MPS System Controller SW module known as the
         National Control Manager.  Typically the NC state will go
         to running once National Control is selected.  When National
         Control processing cannot be established, it is typical to
         see this state oscillating while attempting to restart the NC
         processes."
    REFERENCE " -- "
::= { mpsSysStatusNationalControl 4}

mpsSysStatusTimeSourceTable OBJECT-TYPE
    SYNTAX SEQUENCE OF MpsSysStatusTimeSourceEntry
    ACCESS not-accessible
    STATUS mandatory
    DESCRIPTION  
        "This Table contains information on whether the physical
         slot and port are a valid source of system time.  The MPS generates
         this table so that a user can determine what Slots and Ports are valid
         when setting up the input time source."
::= { mpsSysStatus 15}

mpsSysStatusTimeSourceEntry OBJECT-TYPE
    SYNTAX MpsSysStatusTimeSourceEntry
    ACCESS not-accessible
    STATUS mandatory
    INDEX {mpsSysStatusTimeSourceSlot, mpsSysStatusTimeSourcePort}
::= { mpsSysStatusTimeSourceTable 1 }

MpsSysStatusTimeSourceEntry ::= SEQUENCE
    {
     mpsSysStatusTimeSourceSlot       INTEGER,
     mpsSysStatusTimeSourcePort       INTEGER,
     mpsSysStatusTimeSourceValid      INTEGER
    }

mpsSysStatusTimeSourceSlot OBJECT-TYPE
    SYNTAX INTEGER 
    ACCESS not-accessible
    STATUS mandatory
    DESCRIPTION  
        "The slot index to the table."
    REFERENCE " -- "
::= { mpsSysStatusTimeSourceEntry 1 }

mpsSysStatusTimeSourcePort OBJECT-TYPE
    SYNTAX INTEGER 
    ACCESS not-accessible
    STATUS mandatory
    DESCRIPTION  
        "The port index to the table."
    REFERENCE " -- "
::= { mpsSysStatusTimeSourceEntry 2 }

mpsSysStatusTimeSourceValid OBJECT-TYPE
    SYNTAX INTEGER 
    ACCESS read-only
    STATUS mandatory
    DESCRIPTION 
        "Set to one (1) indicates the physical slot and port contain a stream that is
         a valid source of time.  Zero (0) indicates no time source in the stream."
    REFERENCE   " -- "
 ::= { mpsSysStatusTimeSourceEntry 3 }

mpsSysStatusNCSourceTable OBJECT-TYPE
    SYNTAX SEQUENCE OF MpsSysStatusNCSourceEntry
    ACCESS not-accessible
    STATUS mandatory
    DESCRIPTION  
        "This Table contains information on whether the physical
         slot and port are a valid source of National Control data. The MPS generates
         this table so that a user can determine what Slots and Ports are valid
         when setting up the primary mode National Control."
::= { mpsSysStatus 16}

mpsSysStatusNCSourceEntry OBJECT-TYPE
    SYNTAX MpsSysStatusNCSourceEntry
    ACCESS not-accessible
    STATUS mandatory
    DESCRIPTION  
        "."
    INDEX {mpsSysStatusNCSourceSlot, mpsSysStatusNCSourcePort}
::= { mpsSysStatusNCSourceTable 1 }

MpsSysStatusNCSourceEntry ::= SEQUENCE
    {
     mpsSysStatusNCSourceSlot       INTEGER,
     mpsSysStatusNCSourcePort       INTEGER,
     mpsSysStatusNCSourceValid      INTEGER
    }

mpsSysStatusNCSourceSlot OBJECT-TYPE
    SYNTAX INTEGER 
    ACCESS not-accessible
    STATUS mandatory
    DESCRIPTION  
        "The slot index into the table."
    REFERENCE " -- "
::= { mpsSysStatusNCSourceEntry 1 }

mpsSysStatusNCSourcePort OBJECT-TYPE
    SYNTAX INTEGER 
    ACCESS not-accessible
    STATUS mandatory
    DESCRIPTION  
        "The port index into the table."
    REFERENCE " -- "
::= { mpsSysStatusNCSourceEntry 2 }

mpsSysStatusNCSourceValid OBJECT-TYPE
    SYNTAX INTEGER 
    ACCESS read-only
    STATUS mandatory
    DESCRIPTION 
        "Set to one (1) indicates the physical slot and port contain an input
         from which a National Control stream may be detunneled.  This is not 
         an indication of a valid stream on the port.  It is simply an indication
         that if this port is selected for national control and a valid stream is
         applied to the port, then the MPS is capable of detunneling."
    REFERENCE   " -- "
 ::= { mpsSysStatusNCSourceEntry 3 }

mpsSysStatusSysOperationalState OBJECT-TYPE
    SYNTAX INTEGER 
        {
          configuring           (1),
          configurationFailure  (2),
          operational           (3)
        }
    ACCESS read-only
    STATUS mandatory
    DESCRIPTION 
         "This parameter is not currently used."
    REFERENCE   " -- "
 ::= { mpsSysStatusSysSoftware 1 }


mpsDvbInputConfTable OBJECT-TYPE
    SYNTAX SEQUENCE OF MpsDvbInputConfEntry
    ACCESS not-accessible
    STATUS mandatory
    DESCRIPTION  
       "A table of configuration parameters for DVB input cards.
       This table is indexed by slot number.  Only slots
       that contain DVB Input Module as reported in the 
       mpsSysStatusSlotTable contain valid data.  For 
       each module PacketSize is configurable."
::= { mpsDvbInputConf 1}

mpsDvbInputConfEntry OBJECT-TYPE
    SYNTAX MpsDvbInputConfEntry
    ACCESS not-accessible
    STATUS mandatory
    DESCRIPTION  
        "A row in the DVB Input Configuration table"
    INDEX {mpsDvbInputConfSlotNumber}
::= { mpsDvbInputConfTable 1}

MpsDvbInputConfEntry ::= SEQUENCE
    {
     mpsDvbInputConfSlotNumber    INTEGER,
     mpsDvbInputConfInputEnabled  INTEGER,
     mpsDvbInputConfPacketSize    INTEGER
    }

mpsDvbInputConfSlotNumber OBJECT-TYPE
    SYNTAX INTEGER (1..8) 
    ACCESS not-accessible
    STATUS mandatory
    DESCRIPTION  
        "The slot number of the DVB input card"
    REFERENCE " -- "
::= { mpsDvbInputConfEntry 1}

mpsDvbInputConfInputEnabled OBJECT-TYPE
    SYNTAX INTEGER
        {
         disabled (1),
         enabled (2)
        }
    ACCESS read-write
    STATUS mandatory
    DESCRIPTION  
        "Whether the input is enabled to be used.  When disabled, for this input,
         all errors are suppressed from causing alarms.  Typically, a user will 
         set an input that has nothing connected to it to disabled to eliminate
         errors on the path.
         Once written, a save must be performed via the mpsSysConfSaveConfig
         parameter and the MPS must be rebooted for the change to take effect."
    REFERENCE " -- "
::= { mpsDvbInputConfEntry 2}

mpsDvbInputConfPacketSize OBJECT-TYPE
    SYNTAX INTEGER 
        { 
         byte188 (1),
         byte204 (2)
        }
    ACCESS read-write
    STATUS mandatory
    DESCRIPTION
        "The input packet size for the DVB Input Card.
         Once written, a save must be performed via the mpsSysConfSaveConfig
         parameter and the MPS must be rebooted for the change to take effect."
    REFERENCE " -- "
::= { mpsDvbInputConfEntry 3}

mpsDvbInputStatusTable OBJECT-TYPE
    SYNTAX SEQUENCE OF MpsDvbInputStatusEntry
    ACCESS not-accessible
    STATUS mandatory
    DESCRIPTION  
      "A table of status parameters for DVB input cards.
       This table is indexed by slot number.  Only slots
       that contain DVB Input Module as reported in the 
       mpsSysStatusSlotTable contain valid data.  For 
       each module InputActive, PacketSize, ProcessingError,
       and PllLock are reported."
::= { mpsDvbInputStatus 1}

mpsDvbInputStatusEntry OBJECT-TYPE
    SYNTAX MpsDvbInputStatusEntry
    ACCESS not-accessible
    STATUS mandatory
    DESCRIPTION  
        "A row in the DVB Input Configuration table"
    INDEX {mpsDvbInputStatusSlotNumber}
::= { mpsDvbInputStatusTable 1}

MpsDvbInputStatusEntry ::= SEQUENCE
    {
     mpsDvbInputStatusSlotNumber      INTEGER,
     mpsDvbInputStatusInputActive     INTEGER,
     mpsDvbInputStatusPacketSize      INTEGER,
     mpsDvbInputStatusProcessingError INTEGER,
     mpsDvbInputStatusPllLock         INTEGER
    }

mpsDvbInputStatusSlotNumber OBJECT-TYPE
    SYNTAX INTEGER (1..8) 
    ACCESS not-accessible
    STATUS mandatory
    DESCRIPTION  
        "The slot number of the DVB input card"
    REFERENCE " -- "
::= { mpsDvbInputStatusEntry 1}

mpsDvbInputStatusInputActive OBJECT-TYPE
    SYNTAX INTEGER 
        { 
         notActive (1),
         active (2)
        }
    ACCESS read-only
    STATUS mandatory
    DESCRIPTION  
        "This object reports whether the input is active."
    REFERENCE " -- "
::= { mpsDvbInputStatusEntry 2}

mpsDvbInputStatusPacketSize OBJECT-TYPE
    SYNTAX INTEGER 
        { 
         byte188 (1),
         byte204 (2)
        }
    ACCESS read-only
    STATUS mandatory
    DESCRIPTION  
        "The packet size for the DVB Input Card"
    REFERENCE " -- "
::= { mpsDvbInputStatusEntry 3}

mpsDvbInputStatusProcessingError OBJECT-TYPE
    SYNTAX INTEGER 
        { 
         noError (1),
         error (2)
        }
    ACCESS read-only
    STATUS mandatory
    DESCRIPTION  
        "Indicates an under flow, over flow, or sync error has occurred"
    REFERENCE " -- "
::= { mpsDvbInputStatusEntry 4}

mpsDvbInputStatusPllLock OBJECT-TYPE
    SYNTAX INTEGER 
        {  
         notLocked (1),
         locked (2)
        }
    ACCESS read-only
    STATUS mandatory
    DESCRIPTION  
        "The PLL Lock indicator for the DVB Input Card"
    REFERENCE " -- "
::= { mpsDvbInputStatusEntry 5}


mpsDvbOutputConfTable OBJECT-TYPE
    SYNTAX SEQUENCE OF MpsDvbOutputConfEntry
    ACCESS not-accessible
    STATUS mandatory
    DESCRIPTION  
       "A table of configuration parameters for DVB output cards
       This table is indexed by slot number.  Only slots
       that contain DVB Output Module as reported in the 
       mpsSysStatusSlotTable contain valid data.  For 
       each module PacketSize is configurable."
::= { mpsDvbOutputConf 1}

mpsDvbOutputConfEntry OBJECT-TYPE
    SYNTAX MpsDvbOutputConfEntry
    ACCESS not-accessible
    STATUS mandatory
    DESCRIPTION  
        "A row in the DVB Output Configuration table"
    INDEX {mpsDvbOutputConfSlotNumber}
::= { mpsDvbOutputConfTable 1}

MpsDvbOutputConfEntry ::= SEQUENCE
    {
     mpsDvbOutputConfSlotNumber      INTEGER,
     mpsDvbOutputConfPacketSize      INTEGER
    }

mpsDvbOutputConfSlotNumber OBJECT-TYPE
    SYNTAX INTEGER (1..8) 
    ACCESS not-accessible
    STATUS mandatory
    DESCRIPTION  
        "The slot number of the DVB output card"
    REFERENCE " -- "
::= { mpsDvbOutputConfEntry 1}

mpsDvbOutputConfPacketSize OBJECT-TYPE
    SYNTAX INTEGER 
        { 
         byte188 (1),
         byte204 (2)
        }
    ACCESS read-write
    STATUS mandatory
    DESCRIPTION  
        "The packet size for the DVB Output Card
         Once written, a save must be performed via the mpsSysConfSaveConfig
         parameter and the MPS must be rebooted for the change to take effect."
    REFERENCE " -- "
::= { mpsDvbOutputConfEntry 2}

mpsDvbOutputStatusTable OBJECT-TYPE
    SYNTAX SEQUENCE OF MpsDvbOutputStatusEntry
    ACCESS not-accessible
    STATUS mandatory
    DESCRIPTION  
       "A table of status parameters for DVB output cards.
       This table is indexed by slot number.  Only slots
       that contain DVB Output Module as reported in the 
       mpsSysStatusSlotTable contain valid data.  For 
       each module Input Active, Packet Size, and Processing
       Error are reported."
::= { mpsDvbOutputStatus 1}

mpsDvbOutputStatusEntry OBJECT-TYPE
    SYNTAX MpsDvbOutputStatusEntry
    ACCESS not-accessible
    STATUS mandatory
    DESCRIPTION  
        "A row in the DVB Output Configuration table"
    INDEX {mpsDvbOutputStatusSlotNumber}
::= { mpsDvbOutputStatusTable 1}

MpsDvbOutputStatusEntry ::= SEQUENCE
    {
     mpsDvbOutputStatusSlotNumber            INTEGER,
     mpsDvbOutputStatusInputActive           INTEGER,
     mpsDvbOutputStatusPacketSize            INTEGER,
     mpsDvbOutputStatusProcessingError       INTEGER
    }

mpsDvbOutputStatusSlotNumber OBJECT-TYPE
    SYNTAX INTEGER (1..8) 
    ACCESS not-accessible
    STATUS mandatory
    DESCRIPTION  
        "The slot number of the DVB output card"
    REFERENCE " -- "
::= { mpsDvbOutputStatusEntry 1}

mpsDvbOutputStatusInputActive OBJECT-TYPE
    SYNTAX INTEGER 
        { 
         notActive (1),
         active (2)
        }
    ACCESS read-only
    STATUS mandatory
    DESCRIPTION  
        "Whether the output is active"
    REFERENCE " -- "
::= { mpsDvbOutputStatusEntry 2}

mpsDvbOutputStatusPacketSize OBJECT-TYPE
    SYNTAX INTEGER 
        { 
         byte188 (1),
         byte204 (2)
        }
    ACCESS read-only
    STATUS mandatory
    DESCRIPTION  
        "The packet size for the DVB Output Card"
    REFERENCE " -- "
::= { mpsDvbOutputStatusEntry 3}

mpsDvbOutputStatusProcessingError OBJECT-TYPE
    SYNTAX INTEGER 
       { 
        noError (1),
        error (2)
       }
    ACCESS read-only
    STATUS mandatory
    DESCRIPTION  
        "Indicates an under flow, over flow, or sync error has occurred"
    REFERENCE " -- "
::= { mpsDvbOutputStatusEntry 4}

mpsEncryptInsertConfCascadeTable OBJECT-TYPE
    SYNTAX SEQUENCE OF MpsEncryptInsertConfCascadeEntry
    ACCESS not-accessible
    STATUS mandatory
    DESCRIPTION  
        "A table of cascade settings for EI cards.
         This table is indexed by slot number.  Only slots
         that contain E/I Modules as reported in the 
         mpsSysStatusSlotTable contain valid data.   
         The cascade setting controls how input streams are 
         passed through the ACP devices on the module.  
         When not cascaded the first input is
         passed through the first 8 ACPs and the second input
         is passed through the second group of 8 ACPs.
         When cascaded one input stream is passed through all 16
         ACPs (MC1s) originating at IB1 and outputting on IB5.
         When inverse cascaded one input stream is passed through all 16
         ACPs (MC1s) originating at IB2 and outputting on IB6.
         Once written, a save must be performed via the mpsSysConfSaveConfig
         parameter and the MPS must be rebooted for the change to take effect."
::= { mpsEncryptInsertConf 1}

mpsEncryptInsertConfCascadeEntry OBJECT-TYPE
    SYNTAX MpsEncryptInsertConfCascadeEntry
    ACCESS not-accessible
    STATUS mandatory
    DESCRIPTION  
        "A row in the table"
    INDEX {mpsEncryptInsertConfCascadeSlotNumber}
::= { mpsEncryptInsertConfCascadeTable 1}

MpsEncryptInsertConfCascadeEntry ::= SEQUENCE
    {
     mpsEncryptInsertConfCascadeSlotNumber   INTEGER,
     mpsEncryptInsertConfCascadeSetting      INTEGER
    }

mpsEncryptInsertConfCascadeSlotNumber OBJECT-TYPE
    SYNTAX INTEGER (1..8) 
    ACCESS not-accessible
    STATUS mandatory
    DESCRIPTION  
        "The slot number index of the EI card"
    REFERENCE " -- "
::= { mpsEncryptInsertConfCascadeEntry 1}

mpsEncryptInsertConfCascadeSetting OBJECT-TYPE
    SYNTAX INTEGER 
       {
        notCascaded (1),
        cascaded (2),
        inverseCascaded (3)
       }
    ACCESS read-write
    STATUS mandatory
    DESCRIPTION  
       "The cascade setting controls how input streams are 
       passed through the ACP devices on the module.  
       When not cascaded the first input is
       passed through the first 8 ACPs and the second input
       is passed through the second group of 8 ACPs.
       When cascaded the first input is passed through all
       16 ACPs originating on IB1 and outputting on IB5.
       When inverse cascaded the second input is passed through
       all 16 ACPs originating on IB2 and outputting on IB6.
       Once written, a save must be performed via the mpsSysConfSaveConfig
       parameter and the MPS must be rebooted for the change to take effect."
    REFERENCE " -- "
::= { mpsEncryptInsertConfCascadeEntry 2}

mpsEncryptInsertConfIOTable OBJECT-TYPE
    SYNTAX SEQUENCE OF MpsEncryptInsertConfIOEntry
    ACCESS not-accessible
    STATUS mandatory
    DESCRIPTION  
       "A table of configuration parameters for EI cards
       This table is indexed by slot number.  Only slots
       that contain E/I Modules as reported in the 
       mpsSysStatusSlotTable contain valid data.   
       The table is also indexed by path.  Depending upon
       the cascade setting for this module the first or
       both paths will contain valid data.  When cascaded
       only the first path index will reference valid data
       When not cascaded both paths will have valid data.
       When inverse cascaded only the second path will have
       valid data.
       For each E/I and each valid path, Input, Enabled, and
       Output are configurable.
       Once written, a save must be performed via the mpsSysConfSaveConfig
       parameter and the MPS must be rebooted for the change to take effect."
::= { mpsEncryptInsertConf 2}

mpsEncryptInsertConfIOEntry OBJECT-TYPE
    SYNTAX MpsEncryptInsertConfIOEntry
    ACCESS not-accessible
    STATUS mandatory
    DESCRIPTION  
        "A row in the table"
    INDEX {mpsEncryptInsertConfIOslotNumber, mpsEncryptInsertConfIOpath}
::= { mpsEncryptInsertConfIOTable 1}

MpsEncryptInsertConfIOEntry ::= SEQUENCE
    {
     mpsEncryptInsertConfIOslotNumber INTEGER,
     mpsEncryptInsertConfIOpath       INTEGER,
     mpsEncryptInsertConfIOinput      INTEGER,
     mpsEncryptInsertConfIOenabled    INTEGER,
     mpsEncryptInsertConfIOoutput     INTEGER
    }

mpsEncryptInsertConfIOslotNumber OBJECT-TYPE
    SYNTAX INTEGER (1..8) 
    ACCESS not-accessible
    STATUS mandatory
    DESCRIPTION  
        "The slot number of the EI card"
    REFERENCE " -- "
::= { mpsEncryptInsertConfIOEntry 1}

mpsEncryptInsertConfIOpath OBJECT-TYPE
    SYNTAX INTEGER (1..2)
    ACCESS not-accessible
    STATUS mandatory
    DESCRIPTION  
        "The path for which the setting is associated"
    REFERENCE " -- "
::= { mpsEncryptInsertConfIOEntry 2}

mpsEncryptInsertConfIOinput OBJECT-TYPE
    SYNTAX INTEGER 
        {
         ib   (1),
         dhei (2)
        } 
    ACCESS read-write
    STATUS mandatory
    DESCRIPTION  
      "Controls whether the input for the path comes from
       InfoBus (IB) or from a DHEI connector (dhei).  When
       from IB path index 1 will always come from ib1 on the
       backplane. IB path index 2 will always come from ib2.
       When from DHEI path index 1 will come from the first 
       DHEI connector and path 2 will come from the second.
       Once written, a save must be performed via the mpsSysConfSaveConfig
       parameter and the MPS must be rebooted for the change to take effect."
    REFERENCE " -- "
::= { mpsEncryptInsertConfIOEntry 3}

mpsEncryptInsertConfIOenabled OBJECT-TYPE
    SYNTAX INTEGER
       {
        dheiDisabled (1),
        dheiEnabled  (2)
       }
    ACCESS read-write
    STATUS mandatory
    DESCRIPTION  
      "This object controls if the DHEI input is enabled or not.
       When a DHEI input is enabled the module will generate input
       failures if data is not being received at the DHEI input.  If
       the DHEI input is disabled the module will not generate input
       failures for the DHEI input.  This setting has no effect on 
       input when the backplane infobus inputs are being used.
       Once written, a save must be performed via the mpsSysConfSaveConfig
       parameter and the MPS must be rebooted for the change to take effect."
    REFERENCE " -- "
::= { mpsEncryptInsertConfIOEntry 4}

mpsEncryptInsertConfIOoutput OBJECT-TYPE
    SYNTAX INTEGER 
        {
         ib5 (1),
         ib6 (2)
        } 
    ACCESS read-only
    STATUS mandatory
    DESCRIPTION  
      "Reports which InfoBus output the path is going to"
    REFERENCE " -- "
::= { mpsEncryptInsertConfIOEntry 5}

mpsEncryptInsertStatusIOTable OBJECT-TYPE
    SYNTAX SEQUENCE OF MpsEncryptInsertStatusIOEntry
    ACCESS not-accessible
    STATUS mandatory
    DESCRIPTION  
       "A table of status for EI cards.
       This table is indexed by slot number.  Only slots
       that contain E/I Modules as reported in the 
       mpsSysStatusSlotTable contain valid data.   
       The table is also indexed by path.  Depending upon
       the cascade setting for this module the first or
       both paths will contain valid data.  When cascaded
       only the first path index will reference valid data
       When not cascaded both paths will have valid data.
       Input Active and Packets Inserted is reported for 
       each path."
::= { mpsEncryptInsertStatus 1}

mpsEncryptInsertStatusIOEntry OBJECT-TYPE
    SYNTAX MpsEncryptInsertStatusIOEntry
    ACCESS not-accessible
    STATUS mandatory
    DESCRIPTION  
        "A row in the table"
    INDEX {mpsEncryptInsertStatusIOslotNumber, mpsEncryptInsertStatusIOpath}
::= { mpsEncryptInsertStatusIOTable 1}

MpsEncryptInsertStatusIOEntry ::= SEQUENCE
    {
     mpsEncryptInsertStatusIOslotNumber      INTEGER,
     mpsEncryptInsertStatusIOpath            INTEGER,
     mpsEncryptInsertStatusIOinputActive     INTEGER,
     mpsEncryptInsertStatusIOpacketsInserted INTEGER
    }

mpsEncryptInsertStatusIOslotNumber OBJECT-TYPE
    SYNTAX INTEGER (1..8) 
    ACCESS not-accessible
    STATUS mandatory
    DESCRIPTION  
        "The slot number of the EI card"
    REFERENCE " -- "
::= { mpsEncryptInsertStatusIOEntry 1}

mpsEncryptInsertStatusIOpath OBJECT-TYPE
    SYNTAX INTEGER (1..2) 
    ACCESS not-accessible
    STATUS mandatory
    DESCRIPTION  
        "The path"
    REFERENCE " -- "
::= { mpsEncryptInsertStatusIOEntry 2}

mpsEncryptInsertStatusIOinputActive OBJECT-TYPE
    SYNTAX INTEGER  
       { 
        notActive (1),
        active (2)
       }
    ACCESS read-only
    STATUS mandatory
    DESCRIPTION  
        "This object reports whether the input for the path
         is currently active. This object only applies if the
         path is enabled (for DHEI) or connected (for backplane
         infobus)." 
    REFERENCE " -- "
::= { mpsEncryptInsertStatusIOEntry 3}

mpsEncryptInsertStatusIOpacketsInserted OBJECT-TYPE
    SYNTAX INTEGER  
    ACCESS read-only
    STATUS mandatory
    DESCRIPTION  
        "This object stores the number of packets inserted 
         from the message queue for the path specified.  This
         object will increment and eventually wrap."
    REFERENCE " -- "
::= { mpsEncryptInsertStatusIOEntry 4}

mpsEncryptInsertAcpTable OBJECT-TYPE
    SYNTAX SEQUENCE OF MpsEncryptInsertAcpEntry
    ACCESS not-accessible
    STATUS mandatory
    DESCRIPTION  
        "This table contains a table of references to the acpStatus
         MIB.  The references can be used to identify which ACPs in
         the acpStatus MIB are located on which modules and in which
         paths.  The table is indexed by slot and by acpIndex.  If 
         an EI module is not located in the specified slot in the
         mpsSysStatusSlotTable then the corresponding row in this
         table is not valid and should not be used.  acpIndex is a
         number between 1 and 16.  For each acp in this table, the
         AcpUnitIndex is given.  This index is the index in the 
         acpStatus MIB at which status for this ACP can be found.
         Each acp also has a group identification.  ACPs that are in
         the same group can be used together to encrypt the same
         service.  
         To obtain meaningful information about the status of ACPs
         the acpStatus MIB must be read."
::= { mpsEncryptInsertStatus 2}

mpsEncryptInsertAcpEntry OBJECT-TYPE
    SYNTAX MpsEncryptInsertAcpEntry
    ACCESS not-accessible
    STATUS mandatory
    DESCRIPTION
        "A row in the table"
    INDEX {mpsEncryptInsertAcpSlotNumber, mpsEncryptInsertAcpIndex}
::= { mpsEncryptInsertAcpTable 1}

MpsEncryptInsertAcpEntry ::= SEQUENCE
    {
     mpsEncryptInsertAcpSlotNumber  INTEGER,
     mpsEncryptInsertAcpIndex       INTEGER,
     mpsEncryptInsertAcpEncryptType INTEGER,
     mpsEncryptInsertAcpUnitIndex   INTEGER,
     mpsEncryptInsertAcpGroup       INTEGER
    }

mpsEncryptInsertAcpSlotNumber OBJECT-TYPE
    SYNTAX INTEGER (1..8) 
    ACCESS not-accessible
    STATUS mandatory
    DESCRIPTION  
        "The slot number of the EI card"
    REFERENCE " -- "
::= { mpsEncryptInsertAcpEntry 1}

mpsEncryptInsertAcpIndex OBJECT-TYPE
    SYNTAX INTEGER
    ACCESS not-accessible
    STATUS mandatory
    DESCRIPTION  
        "The index of the ACP"
    REFERENCE " -- "
::= { mpsEncryptInsertAcpEntry 2}

mpsEncryptInsertAcpEncryptType OBJECT-TYPE
    SYNTAX INTEGER (1..16) 
    ACCESS read-only
    STATUS mandatory
    DESCRIPTION  
        "The type of acp (encrypt, decrypt)"
    REFERENCE " -- "
::= { mpsEncryptInsertAcpEntry 3}

mpsEncryptInsertAcpUnitIndex OBJECT-TYPE
    SYNTAX INTEGER  
    ACCESS read-only
    STATUS mandatory
    DESCRIPTION  
        "The Unit Index of the ACP in the ACP MIB"
    REFERENCE " -- "
::= { mpsEncryptInsertAcpEntry 4}

mpsEncryptInsertAcpGroup OBJECT-TYPE
    SYNTAX INTEGER  
    ACCESS read-only
    STATUS mandatory
    DESCRIPTION  
        "The grouping of the ACP. ACPs in same
         path have same group."
    REFERENCE " -- "
::= { mpsEncryptInsertAcpEntry 5}

mpsEncryptInsertStatusTable OBJECT-TYPE
    SYNTAX SEQUENCE OF MpsEncryptInsertStatusEntry
    ACCESS not-accessible
    STATUS mandatory
    DESCRIPTION  
       "A table of status for EI cards.
       This table is indexed by slot number.  Only slots
       that contain E/I Modules as reported in the 
       mpsSysStatusSlotTable contain valid data."
::= { mpsEncryptInsertStatus 3}

mpsEncryptInsertStatusEntry OBJECT-TYPE
    SYNTAX MpsEncryptInsertStatusEntry
    ACCESS not-accessible
    STATUS mandatory
    DESCRIPTION  
        "A row in the table"
    INDEX {mpsEncryptInsertStatusSlotNumber}
::= { mpsEncryptInsertStatusTable 1}

MpsEncryptInsertStatusEntry ::= SEQUENCE
    {
     mpsEncryptInsertStatusSlotNumber      INTEGER,
     mpsEncryptInsertStatusAuthorized      INTEGER
    }

mpsEncryptInsertStatusSlotNumber OBJECT-TYPE
    SYNTAX INTEGER (1..8) 
    ACCESS not-accessible
    STATUS mandatory
    DESCRIPTION  
        "The slot number of the EI card"
    REFERENCE " -- "
::= { mpsEncryptInsertStatusEntry 1}

mpsEncryptInsertStatusAuthorized OBJECT-TYPE
    SYNTAX INTEGER
       { 
        notAuthorized (1),
        authorized (2)
       }
    ACCESS read-only
    STATUS mandatory
    DESCRIPTION  
        "This status indicates whether the E/I module has proper encryption 
         authorization.  If the module has not been commanded to encrypt then 
         the status is not authorized.  If the module has been commanded to 
         encrypt but does not have proper authorization for every service 
         programmed then the status is not authorized.  If the module has been 
         commanded to encrypt and does have authorization for all services 
         programmed then the status reported is authorized.  This object 
         mirrors the authorized LED on the front of the E/I module."
    REFERENCE " -- "
::= { mpsEncryptInsertStatusEntry 2}

mpsDecryptExtractConfIOInfobusTable OBJECT-TYPE
    SYNTAX SEQUENCE OF MpsDecryptExtractConfIOInfobusEntry
    ACCESS not-accessible
    STATUS mandatory
    DESCRIPTION  
       "A table of configuration parameters for DE cards.
       This table is indexed by slot number and Infobus path
       through the DE module (there are four Infobus Inputs and
       four Infobus outputs so there are four Infobus paths).
       Only slots that contain DE Modules as reported in the
       mpsSysStatusSlotTable contain valid data.
       Once written, a save must be performed via the mpsSysConfSaveConfig
       parameter and the MPS must be rebooted for the change to take effect."
::= { mpsDecryptExtractConf 1}

mpsDecryptExtractConfIOInfobusEntry OBJECT-TYPE
    SYNTAX MpsDecryptExtractConfIOInfobusEntry
    ACCESS not-accessible
    STATUS mandatory
    DESCRIPTION  
        "A row in the table"
    INDEX {mpsDecryptExtractConfIOIBslotNumber, mpsDecryptExtractConfIOIBpath}
::= { mpsDecryptExtractConfIOInfobusTable 1}

MpsDecryptExtractConfIOInfobusEntry ::= SEQUENCE
    {
     mpsDecryptExtractConfIOIBslotNumber         INTEGER,
     mpsDecryptExtractConfIOIBpath               INTEGER,
     mpsDecryptExtractConfIOIBacpBankCount       INTEGER,
     mpsDecryptExtractConfIOIBinfobusInput       INTEGER
    }

mpsDecryptExtractConfIOIBslotNumber OBJECT-TYPE
    SYNTAX INTEGER (1..8) 
    ACCESS not-accessible
    STATUS mandatory
    DESCRIPTION  
        "The slot number of the DE card."
    REFERENCE " -- "
::= { mpsDecryptExtractConfIOInfobusEntry 1}

mpsDecryptExtractConfIOIBpath OBJECT-TYPE
    SYNTAX INTEGER (1..4)
    ACCESS not-accessible
    STATUS mandatory
    DESCRIPTION  
        "The Infobus path with which the setting is associated.  This
         can represent an index for the Infobus Input or the Infobus
         Output as noted under the individual parameters of this table."
    REFERENCE " -- "
::= { mpsDecryptExtractConfIOInfobusEntry 2}

mpsDecryptExtractConfIOIBacpBankCount OBJECT-TYPE
    SYNTAX INTEGER (0..8)
    ACCESS read-write
    STATUS mandatory
    DESCRIPTION  
      "Number of ACP Banks (two ACPs per bank) assigned to the Infobus
       input.  The mpsDecryptExtractConfIOIBpath index represents an
       index of the Infobus Input (1 through 4 representing IB In 1
       through 4 respectively).
       Once written, a save must be performed via the mpsSysConfSaveConfig
       parameter and the MPS must be rebooted for the change to take effect."
    REFERENCE " -- "
::= { mpsDecryptExtractConfIOInfobusEntry 3}

mpsDecryptExtractConfIOIBinfobusInput OBJECT-TYPE
    SYNTAX INTEGER (0..4)
    ACCESS read-write
    STATUS mandatory
    DESCRIPTION  
      "Selects which Infobus Input, if any, is routed to the Infobus Output.
       The mpsDecryptExtractConfIOIBpath index represents an index of the
       Infobus Output (1 through 4 representing IB Out 5 through 8 respectively).
       Once written, a save must be performed via the mpsSysConfSaveConfig
       parameter and the MPS must be rebooted for the change to take effect."
    REFERENCE " -- "
::= { mpsDecryptExtractConfIOInfobusEntry 4}

mpsDecryptExtractConfIODheiTable OBJECT-TYPE
    SYNTAX SEQUENCE OF MpsDecryptExtractConfIODheiEntry
    ACCESS not-accessible
    STATUS mandatory
    DESCRIPTION  
       "A table of configuration parameters for DE cards.
       This table is indexed by slot number and Dhei output.
       Only slots that contain DE Modules as reported in the
       mpsSysStatusSlotTable contain valid data.
       Once written, a save must be performed via the mpsSysConfSaveConfig
       parameter and the MPS must be rebooted for the change to take effect."
::= { mpsDecryptExtractConf 2}

mpsDecryptExtractConfIODheiEntry OBJECT-TYPE
    SYNTAX MpsDecryptExtractConfIODheiEntry
    ACCESS not-accessible
    STATUS mandatory
    DESCRIPTION  
        "A row in the table"
    INDEX {mpsDecryptExtractConfIODHEIslotNumber, mpsDecryptExtractConfIODHEIdheiOutput}
::= { mpsDecryptExtractConfIODheiTable 1}

MpsDecryptExtractConfIODheiEntry ::= SEQUENCE
    {
     mpsDecryptExtractConfIODHEIslotNumber         INTEGER,
     mpsDecryptExtractConfIODHEIdheiOutput         INTEGER,
     mpsDecryptExtractConfIODHEIinfobusInput       INTEGER
    }

mpsDecryptExtractConfIODHEIslotNumber OBJECT-TYPE
    SYNTAX INTEGER (1..8) 
    ACCESS not-accessible
    STATUS mandatory
    DESCRIPTION  
        "The slot number of the DE card."
    REFERENCE " -- "
::= { mpsDecryptExtractConfIODheiEntry 1}

mpsDecryptExtractConfIODHEIdheiOutput OBJECT-TYPE
    SYNTAX INTEGER (1..2)
    ACCESS not-accessible
    STATUS mandatory
    DESCRIPTION  
        "The Dhei output with which the setting is associated."
    REFERENCE " -- "
::= { mpsDecryptExtractConfIODheiEntry 2}

mpsDecryptExtractConfIODHEIinfobusInput OBJECT-TYPE
    SYNTAX INTEGER (0..4)
    ACCESS read-write
    STATUS mandatory
    DESCRIPTION  
      "Selects which Infobus Input, if any, is routed to the DHEI Output.
       Once written, a save must be performed via the mpsSysConfSaveConfig
       parameter and the MPS must be rebooted for the change to take effect."
    REFERENCE " -- "
::= { mpsDecryptExtractConfIODheiEntry 3}

mpsDecryptExtractStatusIOTable OBJECT-TYPE
    SYNTAX SEQUENCE OF MpsDecryptExtractStatusIOEntry
    ACCESS not-accessible
    STATUS mandatory
    DESCRIPTION  
       "A table of status parameters for DE cards.
       This table is indexed by slot number and Infobus input.
       Only slots that contain DE Modules as reported in the
       mpsSysStatusSlotTable contain valid data."
::= { mpsDecryptExtractStatus 1}

mpsDecryptExtractStatusIOEntry OBJECT-TYPE
    SYNTAX MpsDecryptExtractStatusIOEntry
    ACCESS not-accessible
    STATUS mandatory
    DESCRIPTION  
        "A row in the table"
    INDEX {mpsDecryptExtractStatusIOslotNumber, mpsDecryptExtractStatusIOinfobusInput}
::= { mpsDecryptExtractStatusIOTable 1}

MpsDecryptExtractStatusIOEntry ::= SEQUENCE
    {
     mpsDecryptExtractStatusIOslotNumber      INTEGER,
     mpsDecryptExtractStatusIOinfobusInput    INTEGER,
     mpsDecryptExtractStatusIOinputActive     INTEGER
    }

mpsDecryptExtractStatusIOslotNumber OBJECT-TYPE
    SYNTAX INTEGER (1..8) 
    ACCESS not-accessible
    STATUS mandatory
    DESCRIPTION  
        "The slot number of the DE card"
    REFERENCE " -- "
::= { mpsDecryptExtractStatusIOEntry 1}

mpsDecryptExtractStatusIOinfobusInput OBJECT-TYPE
    SYNTAX INTEGER (1..4) 
    ACCESS not-accessible
    STATUS mandatory
    DESCRIPTION  
        "The Infobus input with which the status is associated"
    REFERENCE " -- "
::= { mpsDecryptExtractStatusIOEntry 2}

mpsDecryptExtractStatusIOinputActive OBJECT-TYPE
    SYNTAX INTEGER  
       { 
        notActive (1),
        active (2)
       }
    ACCESS read-only
    STATUS mandatory
    DESCRIPTION  
        "This object reports whether the input for the path
         is currently active. This object only applies if the
         connected."
    REFERENCE " -- "
::= { mpsDecryptExtractStatusIOEntry 3}

mpsDecryptExtractAcpTable OBJECT-TYPE
    SYNTAX SEQUENCE OF MpsDecryptExtractAcpEntry
    ACCESS not-accessible
    STATUS mandatory
    DESCRIPTION  
        "This table contains a table of references to the acpStatus
         MIB.  The references can be used to identify which ACPs in
         the acpStatus MIB are located on which modules and in which
         paths.  The table is indexed by slot and by acpIndex.  If 
         an DE module is not located in the specified slot in the
         mpsSysStatusSlotTable then the corresponding row in this
         table is not valid and should not be used.  acpIndex is a
         number between 1 and 16.  For each acp in this table, the
         AcpUnitIndex is given.  This index is the index in the 
         acpStatus MIB at which status for this ACP can be found.
         Each acp also has a group identification.  ACPs that are in
         the same group can be used together to encrypt the same
         service.  
         To obtain meaningful information about the status of ACPs
         the acpStatus MIB must be read."
::= { mpsDecryptExtractStatus 2}

mpsDecryptExtractAcpEntry OBJECT-TYPE
    SYNTAX MpsDecryptExtractAcpEntry
    ACCESS not-accessible
    STATUS mandatory
    DESCRIPTION
        "A row in the table"
    INDEX {mpsDecryptExtractAcpSlotNumber, mpsDecryptExtractAcpIndex}
::= { mpsDecryptExtractAcpTable 1}

MpsDecryptExtractAcpEntry ::= SEQUENCE
    {
     mpsDecryptExtractAcpSlotNumber  INTEGER,
     mpsDecryptExtractAcpIndex       INTEGER,
     mpsDecryptExtractAcpEncryptType INTEGER,
     mpsDecryptExtractAcpUnitIndex   INTEGER
    }

mpsDecryptExtractAcpSlotNumber OBJECT-TYPE
    SYNTAX INTEGER (1..8) 
    ACCESS not-accessible
    STATUS mandatory
    DESCRIPTION  
        "The slot number of the DE card"
    REFERENCE " -- "
::= { mpsDecryptExtractAcpEntry 1}

mpsDecryptExtractAcpIndex OBJECT-TYPE
    SYNTAX INTEGER
    ACCESS not-accessible
    STATUS mandatory
    DESCRIPTION  
        "The index of the ACP"
    REFERENCE " -- "
::= { mpsDecryptExtractAcpEntry 2}

mpsDecryptExtractAcpEncryptType OBJECT-TYPE
    SYNTAX INTEGER (1..16) 
    ACCESS read-only
    STATUS mandatory
    DESCRIPTION  
        "The type of acp (encrypt, decrypt)"
    REFERENCE " -- "
::= { mpsDecryptExtractAcpEntry 3}

mpsDecryptExtractAcpUnitIndex OBJECT-TYPE
    SYNTAX INTEGER  
    ACCESS read-only
    STATUS mandatory
    DESCRIPTION  
        "The Unit Index of the ACP in the ACP mib"
    REFERENCE " -- "
::= { mpsDecryptExtractAcpEntry 4}

mpsDecryptExtractStatusTable OBJECT-TYPE
    SYNTAX SEQUENCE OF MpsDecryptExtractStatusEntry
    ACCESS not-accessible
    STATUS mandatory
    DESCRIPTION  
       "A table of status for DE cards.
       This table is indexed by slot number.  Only slots
       that contain DE Modules as reported in the 
       mpsSysStatusSlotTable contain valid data."
::= { mpsDecryptExtractStatus 3}

mpsDecryptExtractStatusEntry OBJECT-TYPE
    SYNTAX MpsDecryptExtractStatusEntry
    ACCESS not-accessible
    STATUS mandatory
    DESCRIPTION  
        "A row in the table"
    INDEX {mpsDecryptExtractStatusSlotNumber}
::= { mpsDecryptExtractStatusTable 1}

MpsDecryptExtractStatusEntry ::= SEQUENCE
    {
     mpsDecryptExtractStatusSlotNumber      INTEGER,
     mpsDecryptExtractStatusAuthorized      INTEGER,
     mpsDecryptExtractStatusMtcInputActive  INTEGER
    }

mpsDecryptExtractStatusSlotNumber OBJECT-TYPE
    SYNTAX INTEGER (1..8) 
    ACCESS not-accessible
    STATUS mandatory
    DESCRIPTION  
        "The slot number of the DE card"
    REFERENCE " -- "
::= { mpsDecryptExtractStatusEntry 1}

mpsDecryptExtractStatusAuthorized OBJECT-TYPE
    SYNTAX INTEGER
       { 
        notAuthorized (1),
        authorized (2)
       }
    ACCESS read-only
    STATUS mandatory
    DESCRIPTION  
        "This status indicates whether the DE module has proper decryption 
         authorization.  If the module has not been commanded to decrypt then 
         the status is not authorized.  If the module has been commanded to 
         decrypt but does not have proper authorization for every service 
         programmed then the status is not authorized.  If the module has been 
         commanded to decrypt and does have authorization for all services 
         programmed then the status reported is authorized.  This object 
         mirrors the authorized LED on the front of the DE module."
    REFERENCE " -- "
::= { mpsDecryptExtractStatusEntry 2}

mpsDecryptExtractStatusMtcInputActive OBJECT-TYPE
    SYNTAX INTEGER
       { 
        notActive (1),
        active (2)
       }
    ACCESS read-only
    STATUS mandatory
    DESCRIPTION  
        "Indicates whether the MPEG deTunneling Controller has a stream present."
    REFERENCE " -- "
::= { mpsDecryptExtractStatusEntry 3}

mpsEieConfCascadeTable OBJECT-TYPE
    SYNTAX SEQUENCE OF MpsEieConfCascadeEntry
    ACCESS not-accessible
    STATUS mandatory
    DESCRIPTION  
        "A table of cascade settings for EIE cards.
         This table is indexed by slot number.  Only slots
         that contain E/I/E Modules as reported in the 
         mpsSysStatusSlotTable contain valid data.   
         The cascade setting controls how input streams are 
         passed through the ACP devices on the module.  
         When not cascaded the first input is
         passed through the first 8 ACPs and the second input
         is passed through the second group of 8 ACPs.
         When cascaded one input stream is passed through all 16
         ACPs (MC1s) originating at IB1 and outputting on IB5.
         When inverse cascaded one input stream is passed through all 16
         ACPs (MC1s) originating at IB2 and outputting on IB6.
         Once written, a save must be performed via the mpsSysConfSaveConfig
         parameter and the MPS must be rebooted for the change to take effect."
::= { mpsEieConf 1}

mpsEieConfCascadeEntry OBJECT-TYPE
    SYNTAX MpsEieConfCascadeEntry
    ACCESS not-accessible
    STATUS mandatory
    DESCRIPTION  
        "A row in the table"
    INDEX {mpsEieConfCascadeSlotNumber}
::= { mpsEieConfCascadeTable 1}

MpsEieConfCascadeEntry ::= SEQUENCE
    {
     mpsEieConfCascadeSlotNumber   INTEGER,
     mpsEieConfCascadeSetting      INTEGER
    }

mpsEieConfCascadeSlotNumber OBJECT-TYPE
    SYNTAX INTEGER (1..8) 
    ACCESS not-accessible
    STATUS mandatory
    DESCRIPTION  
        "The slot number index of the EIE card"
    REFERENCE " -- "
::= { mpsEieConfCascadeEntry 1}

mpsEieConfCascadeSetting OBJECT-TYPE
    SYNTAX INTEGER 
       {
        notCascaded (1),
        cascaded (2),
        inverseCascaded (3)
       }
    ACCESS read-write
    STATUS mandatory
    DESCRIPTION  
       "The cascade setting controls how input streams are 
       passed through the ACP devices on the module.  
       When not cascaded the first input is
       passed through the first 8 ACPs and the second input
       is passed through the second group of 8 ACPs.
       When cascaded the first input is passed through all
       16 ACPs originating on IB1 and outputting on IB5.
       When inverse cascaded the second input is passed through
       all 16 ACPs originating on IB2 and outputting on IB6.
       Once written, a save must be performed via the mpsSysConfSaveConfig
       parameter and the MPS must be rebooted for the change to take effect."
    REFERENCE " -- "
::= { mpsEieConfCascadeEntry 2}

mpsEieConfIOTable OBJECT-TYPE
    SYNTAX SEQUENCE OF MpsEieConfIOEntry
    ACCESS not-accessible
    STATUS mandatory
    DESCRIPTION  
       "A table of configuration parameters for EIE cards
       This table is indexed by slot number.  Only slots
       that contain E/I/E Modules as reported in the 
       mpsSysStatusSlotTable contain valid data.   
       The table is also indexed by path.  Depending upon
       the cascade setting for this module the first or
       both paths will contain valid data.  When cascaded
       only the first path index will reference valid data
       When not cascaded both paths will have valid data.
       When inverse cascaded only the second path will have
       valid data.
       For each E/I/E and each valid path, Input, ASI Enabled, 
       Output Port, Input Packet Size, Pid Remap are configurable.
       
       Once written, a save must be performed via the mpsSysConfSaveConfig
       parameter and the MPS must be rebooted for the change to take effect."
::= { mpsEieConf 2}

mpsEieConfIOEntry OBJECT-TYPE
    SYNTAX MpsEieConfIOEntry
    ACCESS not-accessible
    STATUS mandatory
    DESCRIPTION  
        "A row in the table"
    INDEX {mpsEieConfIOslotNumber, mpsEieConfIOpath}
::= { mpsEieConfIOTable 1}

MpsEieConfIOEntry ::= SEQUENCE
    {
     mpsEieConfIOslotNumber       INTEGER,
     mpsEieConfIOpath             INTEGER,
     mpsEieConfIOinput            INTEGER,
     mpsEieConfIOasiEnabled       INTEGER,
     mpsEieConfIOoutput           INTEGER,
     mpsEieConfIOinputPacketSize  INTEGER,
     mpsEieConfIOpidRemapEnabled  INTEGER,
     mpsEieConfIOnullOverwrite    INTEGER
    }

mpsEieConfIOslotNumber OBJECT-TYPE
    SYNTAX INTEGER (1..8) 
    ACCESS not-accessible
    STATUS mandatory
    DESCRIPTION  
        "The slot number of the EIE card"
    REFERENCE " -- "
::= { mpsEieConfIOEntry 1}

mpsEieConfIOpath OBJECT-TYPE
    SYNTAX INTEGER (1..2)
    ACCESS not-accessible
    STATUS mandatory
    DESCRIPTION  
        "The path for which the setting is associated"
    REFERENCE " -- "
::= { mpsEieConfIOEntry 2}

mpsEieConfIOinput OBJECT-TYPE
    SYNTAX INTEGER 
        {
         ib   (1),
         asi  (2)
        } 
    ACCESS read-write
    STATUS mandatory
    DESCRIPTION  
      "Controls whether the input for the path comes from
       InfoBus (IB) or from a ASI connector (asi).  When
       from IB path index 1 will always come from ib1 on the
       backplane. IB path index 2 will always come from ib2.
       When from ASI path index 1 will come from the first 
       ASI connector and path 2 will come from the second.
       Once written, a save must be performed via the mpsSysConfSaveConfig
       parameter and the MPS must be rebooted for the change to take effect."
    REFERENCE " -- "
::= { mpsEieConfIOEntry 3}

mpsEieConfIOasiEnabled OBJECT-TYPE
    SYNTAX INTEGER
       {
        asiDisabled (1),
        asiEnabled  (2)
       }
    ACCESS read-write
    STATUS mandatory
    DESCRIPTION  
      "This object controls whether the ASI input is enabled or not.
       When an ASI input is enabled the module will generate input
       failures if data is not being received at the ASI input.  If
       the ASI input is disabled the module will not generate input
       failures for the ASI input.  This setting has no effect on 
       input when the backplane infobus inputs are being used.
       Once written, a save must be performed via the mpsSysConfSaveConfig
       parameter and the MPS must be rebooted for the change to take effect."
    REFERENCE " -- "
::= { mpsEieConfIOEntry 4}

mpsEieConfIOoutput OBJECT-TYPE
    SYNTAX INTEGER 
        {
         ib5 (1),
         ib6 (2)
        } 
    ACCESS read-write
    STATUS mandatory
    DESCRIPTION  
      "Reports which InfoBus output the path is going to"
    REFERENCE " -- "
::= { mpsEieConfIOEntry 5}

mpsEieConfIOinputPacketSize OBJECT-TYPE
    SYNTAX INTEGER 
        {
         byte188 (1),
         byte204 (2)
        } 
    ACCESS read-write
    STATUS mandatory
    DESCRIPTION  
      "Configures the input packet size for each ASI input.  Valid
       packet sizes are 188 and 204.  If the ASI input is not selected
       or is not enabled then this parameter has no affect.  
       Once written, the change to this parameter will take immediate
       affect.  However, in order for the change to persist through 
       subsequent reboots or power cycles, the change must be saved via
       the mpsSysConfSaveConfig parameter."
    REFERENCE " -- "
::= { mpsEieConfIOEntry 6}

mpsEieConfIOpidRemapEnabled OBJECT-TYPE
    SYNTAX INTEGER 
        {
         remapDisabled (1),
         remapEnabled (2)
        } 
    ACCESS read-write
    STATUS mandatory
    DESCRIPTION  
      "Configures whether Pid Remapping is enabled.  Only the first
       Pid Remap enabled parameter in a chain of E/I/E modules and
       paths has affect.  Subsequent parameters in a chain are ignored.
       For example, if this module is in cascade mode, only the Pid 
       Remap parameter for the first path has affect.  In inverse cascade
       mode, only the second parameter is used.  The first is ignored.
       Similarly, if a second EIE module was connected in series with 
       this module, then both of its pid remap parameters would be ignored
       because they represent a continuation of the chain.
       Also, when the EIE module is connected in series following a Remux 
       module, then the Remux module automatically handles the remapping of
       PIDs.  Therefore, this parameter is ignored in that case.
       The PID Remap parameter specifies whether PID Remapping is enabled.
       When enabled, the MPS will instruct the EIE module to remap PIDs
       to ranges that will support PID remapping.  When disabled, the MPS
       will not change the PID numbers of incoming component PIDs.
       }
    REFERENCE " -- "
::= { mpsEieConfIOEntry 7}


mpsEieConfIOnullOverwrite OBJECT-TYPE
    SYNTAX INTEGER
       {
        disabled (1),
        enabled  (2)
       }
    ACCESS read-write
    STATUS mandatory
    DESCRIPTION  
      "This object controls whether the EIE module will overwrite NULL
       packets with inserted data.  By default the module will not overwrite
       NULL packets.  Input PSI will be overwritten by the EIE.  However,
       in some cases it is necessary to use more bandwidth in the output 
       multiplex then the bandwidth used for PSI and other data on the input.
       In these cases, NULL overwrite can be enabled.  When enabling NULL
       overwrite, the user must use care to ensure that the insertion does
       not overflow the output.  Sum the expected insertion rate and the
       data rate of component PIDs being mapped through the EIE to make
       sure that the sum is less than the output data rate.
       Once written, a save must be performed via the mpsSysConfSaveConfig
       parameter and the MPS must be rebooted for the change to take effect."
    REFERENCE " -- "
::= { mpsEieConfIOEntry 8}

mpsEieStatusIOTable OBJECT-TYPE
    SYNTAX SEQUENCE OF MpsEieStatusIOEntry
    ACCESS not-accessible
    STATUS mandatory
    DESCRIPTION  
       "A table of status for EIE cards.
       This table is indexed by slot number.  Only slots
       that contain E/I/E Modules as reported in the 
       mpsSysStatusSlotTable contain valid data.   
       The table is also indexed by path.  Depending upon
       the cascade setting for this module the first or
       both paths will contain valid data.  When cascaded
       only the first path index will reference valid data
       When not cascaded both paths will have valid data.
       Input Active and Packets Inserted is reported for 
       each path."
::= { mpsEieStatus 1}

mpsEieStatusIOEntry OBJECT-TYPE
    SYNTAX MpsEieStatusIOEntry
    ACCESS not-accessible
    STATUS mandatory
    DESCRIPTION  
        "A row in the table"
    INDEX {mpsEieStatusIOslotNumber, mpsEieStatusIOpath}
::= { mpsEieStatusIOTable 1}

MpsEieStatusIOEntry ::= SEQUENCE
    {
     mpsEieStatusIOslotNumber      INTEGER,
     mpsEieStatusIOpath            INTEGER,
     mpsEieStatusIOinputActive     INTEGER,
     mpsEieStatusIOpacketsInserted INTEGER,
     mpsEieStatusIOauthorized      INTEGER,
     mpsEieStatusIOmtcActive       INTEGER,
     mpsEieStatusIOremapVisible    INTEGER,
     mpsEieStatusIOasiMpegProc     INTEGER,
     mpsEieStatusIOasiChanBuff     INTEGER
    }

mpsEieStatusIOslotNumber OBJECT-TYPE
    SYNTAX INTEGER (1..8) 
    ACCESS not-accessible
    STATUS mandatory
    DESCRIPTION  
        "The slot number of the EI card"
    REFERENCE " -- "
::= { mpsEieStatusIOEntry 1}

mpsEieStatusIOpath OBJECT-TYPE
    SYNTAX INTEGER (1..2) 
    ACCESS not-accessible
    STATUS mandatory
    DESCRIPTION  
        "The path"
    REFERENCE " -- "
::= { mpsEieStatusIOEntry 2}

mpsEieStatusIOinputActive OBJECT-TYPE
    SYNTAX INTEGER  
       { 
        notActive (1),
        active (2)
       }
    ACCESS read-only
    STATUS mandatory
    DESCRIPTION  
        "This object reports whether the input for the path
         is currently active. This object only applies if the
         path is enabled (for ASI) or connected (for backplane
         infobus)." 
    REFERENCE " -- "
::= { mpsEieStatusIOEntry 3}

mpsEieStatusIOpacketsInserted OBJECT-TYPE
    SYNTAX INTEGER  
    ACCESS read-only
    STATUS mandatory
    DESCRIPTION  
        "This object stores the number of packets inserted 
         from the message queue for the path specified.  This
         object will increment and eventually wrap."
    REFERENCE " -- "
::= { mpsEieStatusIOEntry 4}

mpsEieStatusIOauthorized OBJECT-TYPE
    SYNTAX INTEGER  
       { 
        notAuthorized (1),
        authorized    (2)
       }
    ACCESS read-only
    STATUS mandatory
    DESCRIPTION  
        ""
    REFERENCE " -- "
::= { mpsEieStatusIOEntry 5}

mpsEieStatusIOmtcActive OBJECT-TYPE
    SYNTAX INTEGER  
       { 
        notActive (1),
        active    (2)
       }
    ACCESS read-only
    STATUS mandatory
    DESCRIPTION  
       ""
    REFERENCE " -- "
::= { mpsEieStatusIOEntry 6}

mpsEieStatusIOremapVisible OBJECT-TYPE
    SYNTAX INTEGER  
       { 
        visible    (1),
        notVisible (2)
       }
    ACCESS read-only
    STATUS mandatory
    DESCRIPTION  
       ""
    REFERENCE " -- "
::= { mpsEieStatusIOEntry 7}

mpsEieStatusIOasiMpegProc OBJECT-TYPE
    SYNTAX INTEGER  
       { 
        noError    (1),
        error      (2)
       }
    ACCESS read-only
    STATUS mandatory
    DESCRIPTION  
       ""
    REFERENCE " -- "
::= { mpsEieStatusIOEntry 8}

mpsEieStatusIOasiChanBuff OBJECT-TYPE
    SYNTAX INTEGER  
       {
        empty    (1),
        active   (2),
        overflow (3)
       }
    ACCESS read-only
    STATUS mandatory
    DESCRIPTION  
       ""
    REFERENCE " -- "
::= { mpsEieStatusIOEntry 9}

mpsEieAcpTable OBJECT-TYPE
    SYNTAX SEQUENCE OF MpsEieAcpEntry
    ACCESS not-accessible
    STATUS mandatory
    DESCRIPTION  
        "This table contains a table of references to the acpStatus
         MIB.  The references can be used to identify which ACPs in
         the acpStatus MIB are located on which modules and in which
         paths.  The table is indexed by slot and by acpIndex.  If 
         an EI module is not located in the specified slot in the
         mpsSysStatusSlotTable then the corresponding row in this
         table is not valid and should not be used.  acpIndex is a
         number between 1 and 16.  For each acp in this table, the
         AcpUnitIndex is given.  This index is the index in the 
         acpStatus MIB at which status for this ACP can be found.
         Each acp also has a group identification.  ACPs that are in
         the same group can be used together to encrypt the same
         service.  
         To obtain meaningful information about the status of ACPs
         the acpStatus MIB must be read."
::= { mpsEieStatus 2}

mpsEieAcpEntry OBJECT-TYPE
    SYNTAX MpsEieAcpEntry
    ACCESS not-accessible
    STATUS mandatory
    DESCRIPTION
        "A row in the table"
    INDEX {mpsEieAcpSlotNumber, mpsEieAcpIndex}
::= { mpsEieAcpTable 1}

MpsEieAcpEntry ::= SEQUENCE
    {
     mpsEieAcpSlotNumber  INTEGER,
     mpsEieAcpIndex       INTEGER,
     mpsEieAcpEncryptType INTEGER,
     mpsEieAcpUnitIndex   INTEGER,
     mpsEieAcpGroup       INTEGER
    }

mpsEieAcpSlotNumber OBJECT-TYPE
    SYNTAX INTEGER (1..8) 
    ACCESS not-accessible
    STATUS mandatory
    DESCRIPTION  
        "The slot number of the EI card"
    REFERENCE " -- "
::= { mpsEieAcpEntry 1}

mpsEieAcpIndex OBJECT-TYPE
    SYNTAX INTEGER
    ACCESS not-accessible
    STATUS mandatory
    DESCRIPTION  
        "The index of the ACP"
    REFERENCE " -- "
::= { mpsEieAcpEntry 2}

mpsEieAcpEncryptType OBJECT-TYPE
    SYNTAX INTEGER (1..16) 
    ACCESS read-only
    STATUS mandatory
    DESCRIPTION  
        "The type of acp (encrypt, decrypt)"
    REFERENCE " -- "
::= { mpsEieAcpEntry 3}

mpsEieAcpUnitIndex OBJECT-TYPE
    SYNTAX INTEGER  
    ACCESS read-only
    STATUS mandatory
    DESCRIPTION  
        "The Unit Index of the ACP in the ACP MIB"
    REFERENCE " -- "
::= { mpsEieAcpEntry 4}

mpsEieAcpGroup OBJECT-TYPE
    SYNTAX INTEGER  
    ACCESS read-only
    STATUS mandatory
    DESCRIPTION  
        "The grouping of the ACP. ACPs in same
         path have same group."
    REFERENCE " -- "
::= { mpsEieAcpEntry 5}

mpsQamConfTable OBJECT-TYPE
    SYNTAX SEQUENCE OF MpsQamConfEntry
    ACCESS not-accessible
    STATUS mandatory
    DESCRIPTION  
        "Whether the input is enabled to be used.  When disabled, for this input,
         all errors are suppressed from causing alarms.  Typically, a user will 
         set an input that has nothing connected to it to disabled to eliminate
         errors on the path.
         Once written, a save must be performed via the mpsSysConfSaveConfig
         parameter and the MPS must be rebooted for the change to take effect."
::= { mpsQamConf 1}

mpsQamConfEntry OBJECT-TYPE
    SYNTAX MpsQamConfEntry
    ACCESS not-accessible
    STATUS mandatory
    DESCRIPTION  
        "A row in the Qam Configuration table"
    INDEX {mpsQamConfSlotNumber}
::= { mpsQamConfTable 1}

MpsQamConfEntry ::= SEQUENCE
    {
     mpsQamConfSlotNumber           INTEGER,
     mpsQamConfMode                 INTEGER,
     mpsQamConfMute                 INTEGER,
     mpsQamConfInterleaver          INTEGER,
     mpsQam2ConfGainLevel           INTEGER
    }

mpsQamConfSlotNumber OBJECT-TYPE
    SYNTAX INTEGER (1..8) 
    ACCESS not-accessible
    STATUS mandatory
    DESCRIPTION  
        "The slot number of the Qam card"
    REFERENCE " -- "
::= { mpsQamConfEntry 1}

mpsQamConfMode OBJECT-TYPE
    SYNTAX INTEGER
        {  
         qam64 (1),
         qam256 (2)
        } 
    ACCESS read-write
    STATUS mandatory
    DESCRIPTION  
        "The Qam mode for the Qam Card.  Note that the input data rate and
         clock configured elsewhere in the MPS must match the QAM setting above
         for the QAM module to operate properly.
         Once written, a save must be performed via the mpsSysConfSaveConfig
         parameter and the MPS must be rebooted for the change to take effect."
    REFERENCE " -- "
::= { mpsQamConfEntry 2}

mpsQamConfMute OBJECT-TYPE
    SYNTAX INTEGER
        {  
         off (1),
         on  (2)
        } 
    ACCESS read-write
    STATUS mandatory
    DESCRIPTION  
        "The Mute control for the Qam Card.
         Once written, the change to this parameter will take immediate
         affect.  However, in order for the change to persist through 
         subsequent reboots or power cycles, the change must be saved via
         the mpsSysConfSaveConfig parameter."
    REFERENCE " -- "
::= { mpsQamConfEntry 3}

mpsQamConfInterleaver OBJECT-TYPE
    SYNTAX INTEGER (1..8) 
    ACCESS read-write
    STATUS mandatory
    DESCRIPTION  
        "The Interleaver Setting for the Qam card
         Once written, a save must be performed via the mpsSysConfSaveConfig
         parameter and the MPS must be rebooted for the change to take effect."
    REFERENCE " -- "
::= { mpsQamConfEntry 4}

mpsQam2ConfGainLevel OBJECT-TYPE
    SYNTAX INTEGER
        {
         level24-5dBmV (1),
         level25-0dBmV (2),
         level25-5dBmV (3),
         level26-0dBmV (4),
         level26-5dBmV (5),
         level27-0dBmV (6),
         level27-5dBmV (7),
         level28-0dBmV (8),
         level28-5dBmV (9),
         level29-0dBmV (10),
         level29-5dBmV (11),
         level30-0dBmV (12),
         level30-5dBmV (13),
         level31-0dBmV (14),
         level31-5dBmV (15),
         level32-0dBmV (16),
         level32-5dBmV (17),
         level33-0dBmV (18),
         level33-5dBmV (19),
         level34-0dBmV (20),
         level34-5dBmV (21),
         level35-0dBmV (22),
         level35-5dBmV (23),
         level36-0dBmV (24),
         level36-5dBmV (25),
         level37-0dBmV (26),
         level37-5dBmV (27),
         level38-0dBmV (28),
         level38-5dBmV (29),
         level39-0dBmV (30),
         level39-5dBmV (31),
         level40-0dBmV (32)
        }
    ACCESS read-write
    STATUS mandatory
    DESCRIPTION
        "The Gain Control Level Setting for the Qam 2 card.  Value is
         index to half dBmV steps in the 25 to 40 dBmV range).
         Once written, a save must be performed via the mpsSysConfSaveConfig
         parameter."
    REFERENCE " -- "
::= { mpsQamConfEntry 5}

mpsQamStatusTable OBJECT-TYPE
    SYNTAX SEQUENCE OF MpsQamStatusEntry
    ACCESS not-accessible
    STATUS mandatory
    DESCRIPTION  
        "A table of status parameters for QAM cards"
::= { mpsQamStatus 1}

mpsQamStatusEntry OBJECT-TYPE
    SYNTAX MpsQamStatusEntry
    ACCESS not-accessible
    STATUS mandatory
    DESCRIPTION  
        "A row in the Qam Status table"
    INDEX {mpsQamStatusSlotNumber}
::= { mpsQamStatusTable 1}

MpsQamStatusEntry ::= SEQUENCE
    {
     mpsQamStatusSlotNumber   INTEGER,
     mpsQamStatusInputActive  INTEGER,
     mpsQamStatusPllLock      INTEGER
    }

mpsQamStatusSlotNumber OBJECT-TYPE
    SYNTAX INTEGER (1..8) 
    ACCESS not-accessible
    STATUS mandatory
    DESCRIPTION  
        "The slot number of the Qam card"
    REFERENCE " -- "
::= { mpsQamStatusEntry 1}

mpsQamStatusInputActive OBJECT-TYPE
    SYNTAX INTEGER
       { 
        notActive (1),
        active (2)
       }
    ACCESS read-only
    STATUS mandatory
    DESCRIPTION  
        "The Input Transport Stream Activity indicator for the Qam Card"
    REFERENCE " -- "
::= { mpsQamStatusEntry 2}

mpsQamStatusPllLock OBJECT-TYPE
    SYNTAX INTEGER
        {
         notLocked (1),
         locked (2)
        }
    ACCESS read-only
    STATUS mandatory
    DESCRIPTION  
        "The QAM Data Rate PLL Lock indicator for the Qam Card"
    REFERENCE " -- "
::= { mpsQamStatusEntry 3}

mpsQam3ConfBoardTable OBJECT-TYPE
    SYNTAX SEQUENCE OF MpsQam3ConfBoardEntry
    ACCESS not-accessible
    STATUS mandatory
    DESCRIPTION  
        "A table of board level configuration parameters for the QAM3."
::= { mpsQam3Conf 1}

mpsQam3ConfBoardEntry OBJECT-TYPE
    SYNTAX MpsQam3ConfBoardEntry
    ACCESS not-accessible
    STATUS mandatory
    DESCRIPTION  
        "A row in the table"
    INDEX {mpsQam3ConfBoardSlotNumber}
::= { mpsQam3ConfBoardTable 1}

MpsQam3ConfBoardEntry ::= SEQUENCE
    {
     mpsQam3ConfBoardSlotNumber   INTEGER,
     mpsQam3ConfFecMode           INTEGER,
     mpsQam3ConfIbPort            INTEGER,
     mpsQam3ConfTuningMode        INTEGER,
     mpsQam3ConfChannelSpacing    INTEGER
    }

mpsQam3ConfBoardSlotNumber OBJECT-TYPE
    SYNTAX INTEGER (1..8) 
    ACCESS not-accessible
    STATUS mandatory
    DESCRIPTION  
        "The slot number index of the QAM3 card"
    REFERENCE " -- "
::= { mpsQam3ConfBoardEntry 1}

mpsQam3ConfFecMode OBJECT-TYPE
    SYNTAX INTEGER 
       {
        dcii   (1),
        dvb    (2),
        annexC (3)
       }
    ACCESS read-write
    STATUS mandatory
    DESCRIPTION  
       "Specifies the FEC Mode for the board.
       Once written, a save must be performed via the mpsSysConfSaveConfig
       parameter and the MPS must be rebooted for the change to take effect."
    REFERENCE " -- "
::= { mpsQam3ConfBoardEntry 2}

mpsQam3ConfIbPort OBJECT-TYPE
    SYNTAX INTEGER 
       {
        ib2   (1),
        ib4   (2)
       }
    ACCESS read-write
    STATUS mandatory
    DESCRIPTION  
       "Specifies which input Infobus port the second path receives data from.  Typically 
       this is set to ib2.  In slot 4 ib4 should be used.
       Once written, a save must be performed via the mpsSysConfSaveConfig
       parameter and the MPS must be rebooted for the change to take effect."
    REFERENCE " -- "
::= { mpsQam3ConfBoardEntry 3}

mpsQam3ConfTuningMode OBJECT-TYPE
    SYNTAX INTEGER 
       {
        frequency     (1),
        stdChannel    (2),
        hrcChannel    (3)
       }
    ACCESS read-write
    STATUS mandatory
    DESCRIPTION  
       "Specifies the tuning mode for the Qam3.  In STD Channel tuning mode the SEM uses EIA 
       channels for tuning.  In Frequency mode, the QAM3 uses a specified frequency to tune the 
       channel.
       Once written, a save must be performed via the mpsSysConfSaveConfig
       parameter and the MPS."
    REFERENCE " -- "
::= { mpsQam3ConfBoardEntry 4}

mpsQam3ConfChannelSpacing OBJECT-TYPE
    SYNTAX INTEGER (1000..8000)
    ACCESS read-write
    STATUS mandatory
    DESCRIPTION  
       "Indicates the spacing between the first and second RF channels for the QAM3.
       Once written, a save must be performed via the mpsSysConfSaveConfig
       parameter and the MPS."
    REFERENCE " -- "
::= { mpsQam3ConfBoardEntry 5}

mpsQam3ConfOutTable OBJECT-TYPE
    SYNTAX SEQUENCE OF MpsQam3ConfOutEntry
    ACCESS not-accessible
    STATUS mandatory
    DESCRIPTION  
        "A table of board level configuration parameters for the QAM3.  
         Once written, a save must be performed via the mpsSysConfSaveConfig
         parameter and the MPS must be rebooted for the change to take effect."
::= { mpsQam3Conf 2}

mpsQam3ConfOutEntry OBJECT-TYPE
    SYNTAX MpsQam3ConfOutEntry
    ACCESS not-accessible
    STATUS mandatory
    DESCRIPTION  
        "A row in the table"
    INDEX {mpsQam3ConfOutSlotNumber, mpsQam3ConfOutPortNumber}
::= { mpsQam3ConfOutTable 1}

MpsQam3ConfOutEntry ::= SEQUENCE
    {
     mpsQam3ConfOutSlotNumber   INTEGER,
     mpsQam3ConfOutPortNumber   INTEGER,
     mpsQam3ConfModulationMode    INTEGER,
     mpsQam3ConfSymbolRate        INTEGER,
     mpsQam3ConfInformationRate   INTEGER,
     mpsQam3ConfOutputMode        INTEGER,
     mpsQam3ConfInterleaveDepth   INTEGER,
     mpsQam3ConfSpectralInversion INTEGER,
     mpsQam3ConfTestMode          INTEGER,
     mpsQam3ConfIfFrequency       INTEGER,
     mpsQam3ConfIfOutputLevel     INTEGER,
     mpsQam3ConfRfFrequency       INTEGER,
     mpsQam3ConfRfOutputLevel     INTEGER,
     mpsQam3ConfChannelNumber     INTEGER,
     mpsQam3ConfAsiPacketSize     INTEGER,
     mpsQam3ConfAsiInputEnable    INTEGER,
     mpsQam3ConfApply             INTEGER
    }

mpsQam3ConfOutSlotNumber OBJECT-TYPE
    SYNTAX INTEGER (1..8) 
    ACCESS not-accessible
    STATUS mandatory
    DESCRIPTION  
        "The slot number index of the QAM3 card"
    REFERENCE " -- "
::= { mpsQam3ConfOutEntry 1}

mpsQam3ConfOutPortNumber OBJECT-TYPE
    SYNTAX INTEGER (1..2) 
    ACCESS not-accessible
    STATUS mandatory
    DESCRIPTION  
        "The port number index of the QAM3 card"
    REFERENCE " -- "
::= { mpsQam3ConfOutEntry 2}

mpsQam3ConfModulationMode OBJECT-TYPE
    SYNTAX INTEGER 
       {
        qam64   (1),
        qam256  (2)
       }
    ACCESS read-write
    STATUS mandatory
    DESCRIPTION  
       "Specifies whether the Qam3 is modulated in QAM 64 or QAM 256 mode.
       Once written, a save must be performed via the mpsSysConfSaveConfig
       parameter and the MPS must be rebooted for the change to take effect."
    REFERENCE " -- "
::= { mpsQam3ConfOutEntry 3}

mpsQam3ConfSymbolRate OBJECT-TYPE
    SYNTAX INTEGER (100000..7000000)
    ACCESS read-write
    STATUS mandatory
    DESCRIPTION  
       "Specifies the Symbol Rate to use for output.  Note that in Annex B, this symbol rate is
       fixed and will not be used by the device.
       Once this and all other desired changes to parameters for the Qam3 module are
       made, an apply must be performed via the mpsQam3ConfApply parameter.
       To save this change through reboots, a save must be performed via the
       mpsSysConfSaveConfig parameter."
    REFERENCE " -- "
::= { mpsQam3ConfOutEntry 4}

mpsQam3ConfInformationRate OBJECT-TYPE
    SYNTAX INTEGER 
    ACCESS read-only
    STATUS mandatory
    DESCRIPTION  
        "Read only parameter that provides the Information Rate of the output."
    REFERENCE " -- "
::= { mpsQam3ConfOutEntry 5}

mpsQam3ConfOutputMode OBJECT-TYPE
    SYNTAX INTEGER 
       {
        unmute  (1),
        mute    (2)
       }
    ACCESS read-write
    STATUS mandatory
    DESCRIPTION  
       "Specifies whether the output is muted or not.
       Once this and all other desired changes to parameters for the Qam3 module are
       made, an apply must be performed via the mpsQam3ConfApply parameter.
       To save this change through reboots, a save must be performed via the
       mpsSysConfSaveConfig parameter."
    REFERENCE " -- "
::= { mpsQam3ConfOutEntry 6}

mpsQam3ConfInterleaveDepth OBJECT-TYPE
    SYNTAX INTEGER 
    ACCESS read-write
    STATUS mandatory
    DESCRIPTION  
       "Specifies the Interleave Depth for the Qam3 output.
       Once this and all other desired changes to parameters for the Qam3 module are
       made, an apply must be performed via the mpsQam3ConfApply parameter.
       To save this change through reboots, a save must be performed via the
       mpsSysConfSaveConfig parameter."
    REFERENCE " -- "
::= { mpsQam3ConfOutEntry 7}

mpsQam3ConfSpectralInversion OBJECT-TYPE
    SYNTAX INTEGER 
       {
        invert  (1),
        normal  (2)
       }
    ACCESS read-write
    STATUS mandatory
    DESCRIPTION  
       "Specifies the spectral inversion setting for the QAM3 output.
       Once this and all other desired changes to parameters for the Qam3 module are
       made, an apply must be performed via the mpsQam3ConfApply parameter.
       To save this change through reboots, a save must be performed via the
       mpsSysConfSaveConfig parameter."
    REFERENCE " -- "
::= { mpsQam3ConfOutEntry 8}

mpsQam3ConfTestMode OBJECT-TYPE
    SYNTAX INTEGER 
       {
        off     (1),
        cwtest  (2),
        prbs15  (3),
        prbs15m (4),
        prbs23  (5),
        prbs23m (6)
       }
    ACCESS read-write
    STATUS mandatory
    DESCRIPTION  
       "Enables test modes for the Qam3 output.
       Once this and all other desired changes to parameters for the Qam3 module are
       made, an apply must be performed via the mpsQam3ConfApply parameter.
       To save this change through reboots, a save must be performed via the
       mpsSysConfSaveConfig parameter."
    REFERENCE " -- "
::= { mpsQam3ConfOutEntry 9}

mpsQam3ConfIfFrequency OBJECT-TYPE
    SYNTAX INTEGER (32000..44000)
    ACCESS read-write
    STATUS mandatory
    DESCRIPTION  
       "Specifies the IF frequency of the output for IF output versions of this module.
       Once this and all other desired changes to parameters for the Qam3 module are
       made, an apply must be performed via the mpsQam3ConfApply parameter.
       To save this change through reboots, a save must be performed via the
       mpsSysConfSaveConfig parameter."
    REFERENCE " -- "
::= { mpsQam3ConfOutEntry 10}

mpsQam3ConfIfOutputLevel OBJECT-TYPE
    SYNTAX INTEGER 
    ACCESS read-write
    STATUS mandatory
    DESCRIPTION  
       "Specifies the IF Output Level for IF output versions of this module.
       Once this and all other desired changes to parameters for the Qam3 module are
       made, an apply must be performed via the mpsQam3ConfApply parameter.
       To save this change through reboots, a save must be performed via the
       mpsSysConfSaveConfig parameter."
    REFERENCE " -- "
::= { mpsQam3ConfOutEntry 11}

mpsQam3ConfRfFrequency OBJECT-TYPE
    SYNTAX INTEGER (57000..867000)
    ACCESS read-write
    STATUS mandatory
    DESCRIPTION  
       "Specifies the RF Frequency to use for RF output versions of this module.
       Once this and all other desired changes to parameters for the Qam3 module are
       made, an apply must be performed via the mpsQam3ConfApply parameter.
       To save this change through reboots, a save must be performed via the
       mpsSysConfSaveConfig parameter."
    REFERENCE " -- "
::= { mpsQam3ConfOutEntry 12}

mpsQam3ConfRfOutputLevel OBJECT-TYPE
    SYNTAX INTEGER (40..56)
    ACCESS read-write
    STATUS mandatory
    DESCRIPTION  
       "Specifies the RF Output Level for RF output versions of this module.
       Once this and all other desired changes to parameters for the Qam3 module are
       made, an apply must be performed via the mpsQam3ConfApply parameter.
       To save this change through reboots, a save must be performed via the
       mpsSysConfSaveConfig parameter."
    REFERENCE " -- "
::= { mpsQam3ConfOutEntry 13}

mpsQam3ConfChannelNumber OBJECT-TYPE
    SYNTAX INTEGER (0..138)
    ACCESS read-write
    STATUS mandatory
    DESCRIPTION  
       "Specifies the Output Channel Number.  Used when the mpsQam3ConfTuningMode parameter
       is specified to tune by channel.  
       Once this and all other desired changes to parameters for the Qam3 module are
       made, an apply must be performed via the mpsQam3ConfApply parameter.
       To save this change through reboots, a save must be performed via the
       mpsSysConfSaveConfig parameter."
    REFERENCE " -- "
::= { mpsQam3ConfOutEntry 14}

mpsQam3ConfAsiPacketSize OBJECT-TYPE
    SYNTAX INTEGER 
       {
        byte188 (1),
        byte204 (2)
       }
    ACCESS read-write
    STATUS mandatory
    DESCRIPTION  
       "Specifies the ASI packet size.  
       Once this and all other desired changes to parameters for the Qam3 module are
       made, an apply must be performed via the mpsQam3ConfApply parameter.
       To save this change through reboots, a save must be performed via the
       mpsSysConfSaveConfig parameter."
    REFERENCE " -- "
::= { mpsQam3ConfOutEntry 15}

mpsQam3ConfAsiInputEnable OBJECT-TYPE
    SYNTAX INTEGER 
       {
        disabled (1),
        enabled  (2)
       }
    ACCESS read-write
    STATUS mandatory
    DESCRIPTION  
       "Specifies whether the ASI input is enabled.  
       Once this and all other desired changes to parameters for the Qam3 module are
       made, an apply must be performed via the mpsQam3ConfApply parameter.
       To save this change through reboots, a save must be performed via the
       mpsSysConfSaveConfig parameter."
    REFERENCE " -- "
::= { mpsQam3ConfOutEntry 16}

mpsQam3ConfApply OBJECT-TYPE
    SYNTAX INTEGER 
       {
        applyNotInProgress   (1),
        apply                (2)
       }
    ACCESS read-write
    STATUS mandatory
    DESCRIPTION  
       "Used to apply changes to any of the dynamic tuning parameters.  Set this to apply after
       making desired changes.  Note that a save must also be performed via the 
       mpsSysConfSaveConfig  if changes are desired to persist through reboot."
    REFERENCE " -- "
::= { mpsQam3ConfOutEntry 17}

mpsQam3StatusTable OBJECT-TYPE
    SYNTAX SEQUENCE OF MpsQam3StatusEntry
    ACCESS not-accessible
    STATUS mandatory
    DESCRIPTION  
        "A table of board level configuration parameters for the QAM3."
::= { mpsQam3Status 1}

mpsQam3StatusEntry OBJECT-TYPE
    SYNTAX MpsQam3StatusEntry
    ACCESS not-accessible
    STATUS mandatory
    DESCRIPTION  
        "A row in the table"
    INDEX {mpsQam3StatusSlotNumber, mpsQam3StatusPortNumber}
::= { mpsQam3StatusTable 1}

MpsQam3StatusEntry ::= SEQUENCE
    {
     mpsQam3StatusSlotNumber   INTEGER,
     mpsQam3StatusPortNumber   INTEGER,
     mpsQam3StatusInputActive            INTEGER,
     mpsQam3StatusMpegProcessing        INTEGER,
     mpsQam3StatusAlpha     INTEGER
    }

mpsQam3StatusSlotNumber OBJECT-TYPE
    SYNTAX INTEGER (1..8) 
    ACCESS not-accessible
    STATUS mandatory
    DESCRIPTION  
        "The slot number index of the QAM3 card"
    REFERENCE " -- "
::= { mpsQam3StatusEntry 1}

mpsQam3StatusPortNumber OBJECT-TYPE
    SYNTAX INTEGER (1..8) 
    ACCESS not-accessible
    STATUS mandatory
    DESCRIPTION  
        "The port number index of the QAM3 card"
    REFERENCE " -- "
::= { mpsQam3StatusEntry 2}

mpsQam3StatusInputActive OBJECT-TYPE
    SYNTAX INTEGER 
      {
        notActive (1),
        active(2)
      }
    ACCESS read-only
    STATUS mandatory
    DESCRIPTION  
       "Indicates whether the input is active"
    REFERENCE " -- "
::= { mpsQam3StatusEntry 3}

mpsQam3StatusMpegProcessing OBJECT-TYPE
    SYNTAX INTEGER 
       {
        noError  (1),
        overflow (2),
        sncError (3)
       }
    ACCESS read-only
    STATUS mandatory
    DESCRIPTION  
       "Indicates an error in MPEG processing.  Overflow and sync errors are reported."
    REFERENCE " -- "
::= { mpsQam3StatusEntry 4}

mpsQam3StatusAlpha OBJECT-TYPE
    SYNTAX INTEGER 
       {
        twelvePercent        (1),
        fifteenPercent       (2),
        eighteenPercent      (3)
       }
    ACCESS read-only
    STATUS mandatory
    DESCRIPTION  
       "Indicates the current read-only Alpha setting."
    REFERENCE " -- "
::= { mpsQam3StatusEntry 5}

mpsQam3DcmStatusTable OBJECT-TYPE
    SYNTAX SEQUENCE OF MpsQam3DcmStatusEntry
    ACCESS not-accessible
    STATUS mandatory
    DESCRIPTION  
        "A table of board level status parameters for the QAM3.  "
::= { mpsQam3Status 2}

mpsQam3DcmStatusEntry OBJECT-TYPE
    SYNTAX MpsQam3DcmStatusEntry
    ACCESS not-accessible
    STATUS mandatory
    DESCRIPTION  
        "A row in the table"
    INDEX {mpsQam3DcmStatusSlotNumber, mpsQam3DcmStatusPortNumber}
::= { mpsQam3DcmStatusTable 1}

MpsQam3DcmStatusEntry ::= SEQUENCE
    {
     mpsQam3DcmStatusSlotNumber   INTEGER,
     mpsQam3DcmStatusPortNumber   INTEGER,
     mpsQam3StatusRfOutputLevel     INTEGER,
     mpsQam3StatusDcmStatus     INTEGER,
     mpsQam3StatusTemperature    INTEGER
    }

mpsQam3DcmStatusSlotNumber OBJECT-TYPE
    SYNTAX INTEGER (1..8) 
    ACCESS not-accessible
    STATUS mandatory
    DESCRIPTION  
        "The slot number index of the QAM3 card"
    REFERENCE " -- "
::= { mpsQam3DcmStatusEntry 1}

mpsQam3DcmStatusPortNumber OBJECT-TYPE
    SYNTAX INTEGER (1..8) 
    ACCESS not-accessible
    STATUS mandatory
    DESCRIPTION  
        "The port number index of the QAM3 card"
    REFERENCE " -- "
::= { mpsQam3DcmStatusEntry 2}

mpsQam3StatusRfOutputLevel OBJECT-TYPE
    SYNTAX INTEGER 
       {
        highError (1),
        lowError  (2),
        ok        (3)
       }
    ACCESS read-only
    STATUS mandatory
    DESCRIPTION  
       "Indicates errors in the RF level of the output."
    REFERENCE " -- "
::= { mpsQam3DcmStatusEntry 3}

mpsQam3StatusDcmStatus OBJECT-TYPE
    SYNTAX INTEGER 
       {
        ok          (1),
        commError   (2),
        vccError    (3),
        synthError  (4),
        tuningError (5)
       }
    ACCESS read-only
    STATUS mandatory
    DESCRIPTION  
       "Indicates error status from the DCM."
    REFERENCE " -- "
::= { mpsQam3DcmStatusEntry 4}

mpsQam3StatusTemperature OBJECT-TYPE
    SYNTAX INTEGER 
    ACCESS read-only
    STATUS mandatory
    DESCRIPTION  
       "Indicates the temperature."
    REFERENCE " -- "
::= { mpsQam3DcmStatusEntry 5}

mpsDheiInputConfTable OBJECT-TYPE
    SYNTAX SEQUENCE OF MpsDheiInputConfEntry
    ACCESS not-accessible
    STATUS mandatory
    DESCRIPTION  
        "A table of config parameters for DheiInput cards.
         Once written, a save must be performed via the mpsSysConfSaveConfig
         parameter and the MPS must be rebooted for the change to take effect."
::= { mpsDheiInputConf 1}

mpsDheiInputConfEntry OBJECT-TYPE
    SYNTAX MpsDheiInputConfEntry
    ACCESS not-accessible
    STATUS mandatory
    DESCRIPTION  
        "A row in the Dhei Input Conf table"
    INDEX {mpsDheiInputConfSlotNumber}
::= { mpsDheiInputConfTable 1}

MpsDheiInputConfEntry ::= SEQUENCE
    {
     mpsDheiInputConfSlotNumber    INTEGER,
     mpsDheiInputConfInput1Enabled INTEGER,
     mpsDheiInputConfInput2Enabled INTEGER
    }

mpsDheiInputConfSlotNumber OBJECT-TYPE
    SYNTAX INTEGER (1..8) 
    ACCESS not-accessible
    STATUS mandatory
    DESCRIPTION  
        "The slot number of the Dhei Input card"
    REFERENCE " -- "
::= { mpsDheiInputConfEntry 1}

mpsDheiInputConfInput1Enabled OBJECT-TYPE
    SYNTAX INTEGER
       {  
        disabled (1),
        enabled  (2)
       }
    ACCESS read-write
    STATUS mandatory
    DESCRIPTION  
        "Whether the input is enabled to be used.  When disabled, for this input,
         all errors are suppressed from causing alarms.  Typically, a user will 
         set an input that has nothing connected to it to disabled to eliminate
         errors on the path.
         Once written, a save must be performed via the mpsSysConfSaveConfig
         parameter and the MPS must be rebooted for the change to take effect."
    REFERENCE " -- "
::= { mpsDheiInputConfEntry 2}

mpsDheiInputConfInput2Enabled OBJECT-TYPE
    SYNTAX INTEGER
       {  
        disabled (1),
        enabled  (2)
       }
    ACCESS read-write
    STATUS mandatory
    DESCRIPTION  
        "Whether the input is enabled to be used.  When disabled, for this input,
         all errors are suppressed from causing alarms.  Typically, a user will 
         set an input that has nothing connected to it to disabled to eliminate
         errors on the path.
         Once written, a save must be performed via the mpsSysConfSaveConfig
         parameter and the MPS must be rebooted for the change to take effect."
    REFERENCE " -- "
::= { mpsDheiInputConfEntry 3}

mpsDheiInputStatusTable OBJECT-TYPE
    SYNTAX SEQUENCE OF MpsDheiInputStatusEntry
    ACCESS not-accessible
    STATUS mandatory
    DESCRIPTION  
        "A table of status parameters for DheiInput cards"
::= { mpsDheiInputStatus 1}

mpsDheiInputStatusEntry OBJECT-TYPE
    SYNTAX MpsDheiInputStatusEntry
    ACCESS not-accessible
    STATUS mandatory
    DESCRIPTION  
        "A row in the Dhei Input Status table"
    INDEX {mpsDheiInputStatusSlotNumber}
::= { mpsDheiInputStatusTable 1}

MpsDheiInputStatusEntry ::= SEQUENCE
    {
     mpsDheiInputStatusSlotNumber      INTEGER,
     mpsDheiInputStatusInput1Active    INTEGER,
     mpsDheiInputStatusInput2Active    INTEGER
    }

mpsDheiInputStatusSlotNumber OBJECT-TYPE
    SYNTAX INTEGER (1..8) 
    ACCESS not-accessible
    STATUS mandatory
    DESCRIPTION  
        "The slot number of the Dhei Input card"
    REFERENCE " -- "
::= { mpsDheiInputStatusEntry 1}

mpsDheiInputStatusInput1Active OBJECT-TYPE
    SYNTAX INTEGER
       { 
        notActive (1),
        active    (2)
       }
    ACCESS read-only
    STATUS mandatory
    DESCRIPTION  
        "The Input Transport Stream Activity indicator for the Dhei Input Card"
    REFERENCE " -- "
::= { mpsDheiInputStatusEntry 2}

mpsDheiInputStatusInput2Active OBJECT-TYPE
    SYNTAX INTEGER
        {
         notActive (1),
         active    (2)
        }
    ACCESS read-only
    STATUS mandatory
    DESCRIPTION  
        "The Input Transport Stream Activity indicator for the Dhei Input Card"
    REFERENCE " -- "
::= { mpsDheiInputStatusEntry 3}

mpsDS3ConfTable OBJECT-TYPE
    SYNTAX SEQUENCE OF MpsDS3ConfEntry
    ACCESS not-accessible
    STATUS mandatory
    DESCRIPTION  
        "A table of configuration parameters for DS3 cards"
::= { mpsDS3Conf 1}

mpsDS3ConfEntry OBJECT-TYPE
    SYNTAX MpsDS3ConfEntry
    ACCESS not-accessible
    STATUS mandatory
    DESCRIPTION  
        "A row in the DS3 Configuration table"
    INDEX {mpsDS3ConfSlotNumber}
::= { mpsDS3ConfTable 1}

MpsDS3ConfEntry ::= SEQUENCE
    {
     mpsDS3ConfSlotNumber               INTEGER,
     mpsDS3ConfDataRate                 INTEGER,
     mpsDS3ConfMute                     INTEGER,
     mpsDS3ConfLBOsetting               INTEGER,
     mpsDS3ConfInput1Enabled            INTEGER,
     mpsDS3ConfInput2Enabled            INTEGER,
     mpsDS3ConfRecOut1Combined          INTEGER,
     mpsDS3ConfRecOut1I                 INTEGER,
     mpsDS3ConfRecOut1Q                 INTEGER,
     mpsDS3ConfRecOut1PacketRateMode    INTEGER,
     mpsDS3ConfRecOut2DataRate          INTEGER,
     mpsDS3ConfRecOut2Combined          INTEGER,
     mpsDS3ConfRecOut2I                 INTEGER,
     mpsDS3ConfRecOut2Q                 INTEGER,
     mpsDS3ConfRecOut2PacketRateMode    INTEGER,
     mpsDS3ConfTransmitIn1DataRate      INTEGER,
     mpsDS3ConfTransmitIn2DataRate      INTEGER,
     mpsDS3ConfTransmitIn1Mode          INTEGER,
     mpsDS3ConfTransmitIn2Mode          INTEGER,
     mpsDS3ConfTransmitAmplitude        INTEGER,
     mpsDS3ConfPassThrough1             INTEGER,
     mpsDS3ConfPassThrough2             INTEGER,
     mpsDS3ConfRepeater                 INTEGER
    }

mpsDS3ConfSlotNumber OBJECT-TYPE
    SYNTAX INTEGER (1..8) 
    ACCESS not-accessible
    STATUS mandatory
    DESCRIPTION  
        "The slot number of the DS3 card"
    REFERENCE " -- "
::= { mpsDS3ConfEntry 1}

mpsDS3ConfDataRate OBJECT-TYPE
    SYNTAX INTEGER
        {
         dataRate2360 (1),
         dataRate2697 (2),
         dataRate3881 (3),
         dataRate1438 (4),
         dataRate1498 (5),
         dataRate1573 (6),
         dataRate1618 (7),
         dataRate1635 (8),
         dataRate1798 (9),
         dataRate2023 (10),
         dataRate2158 (11),
         dataRate2248 (12),
         dataRate2397 (13),
         dataRate2452 (14)
        } 
    ACCESS read-write
    STATUS mandatory
    DESCRIPTION  
        "The Receive Output 1 Data Rate selection."
    REFERENCE " -- "
::= { mpsDS3ConfEntry 2}

mpsDS3ConfMute OBJECT-TYPE
    SYNTAX INTEGER
        {
         off (1),
         on  (2)
        } 
    ACCESS read-write
    STATUS mandatory
    DESCRIPTION  
        "The Transmit Mute control for the DS3 Card"
    REFERENCE " -- "
::= { mpsDS3ConfEntry 3}

mpsDS3ConfLBOsetting OBJECT-TYPE
    SYNTAX INTEGER
       {  
        short (1),
        long  (2)
       }
    ACCESS read-write
    STATUS mandatory
    DESCRIPTION  
        "The Transmit Line Build Out Setting for the DS3 card"
    REFERENCE " -- "
::= { mpsDS3ConfEntry 4}

mpsDS3ConfInput1Enabled OBJECT-TYPE
    SYNTAX INTEGER
       {  
        disabled (1),
        enabled  (2)
       }
    ACCESS read-write
    STATUS mandatory
    DESCRIPTION  
        "Whether the Receive Physical input is enabled to be used"
    REFERENCE " -- "
::= { mpsDS3ConfEntry 5}

mpsDS3ConfInput2Enabled OBJECT-TYPE
    SYNTAX INTEGER
       {  
        disabled (1),
        enabled  (2)
       }
    ACCESS not-accessible
    STATUS mandatory
    DESCRIPTION  
        "This is no longer used."
    REFERENCE " -- "
::= { mpsDS3ConfEntry 6}

mpsDS3ConfRecOut1Combined OBJECT-TYPE
    SYNTAX INTEGER
       {  
        disabled (1),
        enabled  (2)
       }
    ACCESS read-write
    STATUS mandatory
    DESCRIPTION  
        "The Receive Output channel 1 Combined enable.
         The DS3 Receive processing consists of a Physical input connector at the
         back of the board feeding one or two backplane infobus outputs.  The SW/HW
         allows any of Combined, I, and Q to be enabled or disabled for either of the
         outputs in any combination."
    REFERENCE " -- "
::= { mpsDS3ConfEntry 7}

mpsDS3ConfRecOut1I OBJECT-TYPE
    SYNTAX INTEGER
       {  
        disabled (1),
        enabled  (2)
       }
    ACCESS read-write
    STATUS mandatory
    DESCRIPTION  
        "The Receive Output channel 1 I enable.
         The DS3 Receive processing consists of a Physical input connector at the
         back of the board feeding one or two backplane infobus outputs.  The SW/HW
         allows any of Combined, I, and Q to be enabled or disabled for either of the
         outputs in any combination."
    REFERENCE " -- "
::= { mpsDS3ConfEntry 8}

mpsDS3ConfRecOut1Q OBJECT-TYPE
    SYNTAX INTEGER
       {  
        disabled (1),
        enabled  (2)
       }
    ACCESS read-write
    STATUS mandatory
    DESCRIPTION  
        "The Receive Output channel 1 Q enable.
         The DS3 Receive processing consists of a Physical input connector at the
         back of the board feeding one or two backplane infobus outputs.  The SW/HW
         allows any of Combined, I, and Q to be enabled or disabled for either of the
         outputs in any combination."
    REFERENCE " -- "
::= { mpsDS3ConfEntry 9}

mpsDS3ConfRecOut1PacketRateMode OBJECT-TYPE
    SYNTAX INTEGER
       {  
         variable (1),
         fixed (2)
       }
    ACCESS read-write
    STATUS mandatory
    DESCRIPTION  
        "The Receive Output channel 1 Packet Rate Mode [fixed or variable]"
    REFERENCE " -- "
::= { mpsDS3ConfEntry 10}

mpsDS3ConfRecOut2DataRate OBJECT-TYPE
    SYNTAX INTEGER
        {
         dataRate2360 (1),
         dataRate2697 (2),
         dataRate3881 (3),
         dataRate1438 (4),
         dataRate1498 (5),
         dataRate1573 (6),
         dataRate1618 (7),
         dataRate1635 (8),
         dataRate1798 (9),
         dataRate2023 (10),
         dataRate2158 (11),
         dataRate2248 (12),
         dataRate2397 (13),
         dataRate2452 (14)
        } 
    ACCESS read-write
    STATUS mandatory
    DESCRIPTION  
        "The Receive Output 2 Data Rate selection."
    REFERENCE " -- "
::= { mpsDS3ConfEntry 11}

mpsDS3ConfRecOut2Combined OBJECT-TYPE
    SYNTAX INTEGER
       {  
        disabled (1),
        enabled  (2)
       }
    ACCESS read-write
    STATUS mandatory
    DESCRIPTION  
        "The Receive Output channel 2 Combined enable.
         The DS3 Receive processing consists of a Physical input connector at the
         back of the board feeding one or two backplane infobus outputs.  The SW/HW
         allows any of Combined, I, and Q to be enabled or disabled for either of the
         outputs in any combination."
    REFERENCE " -- "
::= { mpsDS3ConfEntry 12}

mpsDS3ConfRecOut2I OBJECT-TYPE
    SYNTAX INTEGER
       {  
        disabled (1),
        enabled  (2)
       }
    ACCESS read-write
    STATUS mandatory
    DESCRIPTION  
        "The Receive Output channel 2 I enable.
         The DS3 Receive processing consists of a Physical input connector at the
         back of the board feeding one or two backplane infobus outputs.  The SW/HW
         allows any of Combined, I, and Q to be enabled or disabled for either of the
         outputs in any combination."
    REFERENCE " -- "
::= { mpsDS3ConfEntry 13}

mpsDS3ConfRecOut2Q OBJECT-TYPE
    SYNTAX INTEGER
       {  
        disabled (1),
        enabled  (2)
       }
    ACCESS read-write
    STATUS mandatory
    DESCRIPTION  
        "The Receive Output channel 2 Q enable.
         The DS3 Receive processing consists of a Physical input connector at the
         back of the board feeding one or two backplane infobus outputs.  The SW/HW
         allows any of Combined, I, and Q to be enabled or disabled for either of the
         outputs in any combination."
    REFERENCE " -- "
::= { mpsDS3ConfEntry 14}

mpsDS3ConfRecOut2PacketRateMode OBJECT-TYPE
    SYNTAX INTEGER
       {  
         variable (1),
         fixed (2)
       }
    ACCESS read-write
    STATUS mandatory
    DESCRIPTION  
        "The Receive Output channel 2 Packet Rate Mode [fixed or variable]"
    REFERENCE " -- "
::= { mpsDS3ConfEntry 15}

mpsDS3ConfTransmitIn1DataRate OBJECT-TYPE
    SYNTAX INTEGER
       {  
         dataRate2360 (1),
         dataRate2697 (2),
         dataRate3881 (3)
       }
    ACCESS read-write
    STATUS mandatory
    DESCRIPTION  
        "The Transmit Data Rate selection."
    REFERENCE " -- "
::= { mpsDS3ConfEntry 16}

mpsDS3ConfTransmitIn2DataRate OBJECT-TYPE
    SYNTAX INTEGER
       {  
         dataRate2360 (1),
         dataRate2697 (2),
         dataRate3881 (3),
         dataRate1438 (4),
         dataRate1498 (5),
         dataRate1573 (6),
         dataRate1618 (7),
         dataRate1635 (8),
         dataRate1798 (9),
         dataRate2023 (10),
         dataRate2158 (11),
         dataRate2248 (12),
         dataRate2397 (13),
         dataRate2452 (14)
       }
    ACCESS not-accessible
    STATUS mandatory
    DESCRIPTION  
        "This is not currently used."
    REFERENCE " -- "
::= { mpsDS3ConfEntry 17}

mpsDS3ConfTransmitIn1Mode OBJECT-TYPE
    SYNTAX INTEGER
       {  
        disabled (1),
        combined (2),
        i (3),
        q (4)
       }
    ACCESS read-write
    STATUS mandatory
    DESCRIPTION  
        "Enables and selects the mode of transmit input channel 1.
         The DS3 Transmit processing consists of one or two backplane infobus inputs
         feeding a Physical output connector on at the back of the board feeding.
         This requires Channel Input Mode settings for each channel.
         The SW/HW will only allow the following combinations:
              Channel 1      Channel 2
              ---------      ---------
               DISABL           any
                COMB           DISABL
                 I            DISABL, Q
                 Q            DISABL, I
                any            DISABL
               DISABL           COMB
              DISABL, Q          I
              DISABL, I          Q
        
         If there is a conflict channel one settings will be used and channel two
         changed to correct the conflict.  A warning will be generated when an
         incorrect configuration is encountered."
    REFERENCE " -- "
::= { mpsDS3ConfEntry 18}

mpsDS3ConfTransmitIn2Mode OBJECT-TYPE
    SYNTAX INTEGER
       {  
        disabled (1),
        combined (2),
        i (3),
        q (4)
       }
    ACCESS read-write
    STATUS mandatory
    DESCRIPTION  
        "Enables and selects the mode of transmit input channel 2.
         The DS3 Transmit processing consists of one or two backplane infobus inputs
         feeding a Physical output connector on at the back of the board feeding.
         This requires Channel Input Mode settings for each channel.
         The SW/HW will only allow the following combinations:
              Channel 1      Channel 2
              ---------      ---------
               DISABL           any
                COMB           DISABL
                 I            DISABL, Q
                 Q            DISABL, I
                any            DISABL
               DISABL           COMB
              DISABL, Q          I
              DISABL, I          Q
        
         If there is a conflict channel one settings will be used and channel two
         changed to correct the conflict.  A warning will be generated when an
         incorrect configuration is encountered."
    REFERENCE " -- "
::= { mpsDS3ConfEntry 19}

mpsDS3ConfTransmitAmplitude OBJECT-TYPE
    SYNTAX INTEGER
       {  
        high (1),
        low (2)
       }
    ACCESS read-write
    STATUS mandatory
    DESCRIPTION  
        "Selects a faster output with a higher amplitude or a slower output with a lower amplitude"
    REFERENCE " -- "
::= { mpsDS3ConfEntry 20}

mpsDS3ConfPassThrough1 OBJECT-TYPE
    SYNTAX INTEGER
       {  
        disabled (1),
        enabled  (2)
       }
    ACCESS read-write
    STATUS mandatory
    DESCRIPTION  
        "Whether the Pass Through for channel 1 is enabled to be used.  If Receive Channel
         1 is enabled and Pass Through is enabled, the Receive channel takes precedence over
         Pass Through and Pass Through is ignored."
    REFERENCE " -- "
::= { mpsDS3ConfEntry 21}

mpsDS3ConfPassThrough2 OBJECT-TYPE
    SYNTAX INTEGER
       {  
        disabled (1),
        enabled  (2)
       }
    ACCESS read-write
    STATUS mandatory
    DESCRIPTION  
        "Whether the Pass Through for channel 2 is enabled to be used.  If Receive Channel
         2 is enabled and Pass Through is enabled, the Receive channel takes precedence over
         Pass Through and Pass Through is ignored."
    REFERENCE " -- "
::= { mpsDS3ConfEntry 22}

mpsDS3ConfRepeater OBJECT-TYPE
    SYNTAX INTEGER
       {  
        disabled (1),
        enabled  (2)
       }
    ACCESS read-write
    STATUS mandatory
    DESCRIPTION  
        "Whether the Repeater mode is enabled to be used.
         Repeater (loop-back) mode is enabled as necessary.  By default, the
         RX input routes to the RX processing section, and the TX processing
         section output routes to the TX output.  When Repeater mode is enabled,
         the RX input is passed unprocessed to the TX output, and the TX
         processing section output routes to the RX processing section.
         Because of this routing the Repeater mode can only be used if it is set to
         enabled AND: the Physical receive input is enabled OR: one of the Transmit
         section inputs is enabled (and is not set for pass through) AND one of
         the Receive section outputs is enabled (and is not set for pass through).
         The above requirements dictate that the Repeater mode, when enabled, will
         take precedence over the individual Transmit and Receive sides.  The
         Transmit and Receive sections must also be configured appropriately if
         the Repeater mode across the backplane is to be utilized."
    REFERENCE " -- "
::= { mpsDS3ConfEntry 23}

mpsDS3StatusTable OBJECT-TYPE
    SYNTAX SEQUENCE OF MpsDS3StatusEntry
    ACCESS not-accessible
    STATUS mandatory
    DESCRIPTION  
        "A table of status parameters for DS3 cards"
::= { mpsDS3Status 1}

mpsDS3StatusEntry OBJECT-TYPE
    SYNTAX MpsDS3StatusEntry
    ACCESS not-accessible
    STATUS mandatory
    DESCRIPTION  
        "A row in the DS3 Status table"
    INDEX {mpsDS3StatusSlotNumber}
::= { mpsDS3StatusTable 1}

MpsDS3StatusEntry ::= SEQUENCE
    {
     mpsDS3StatusSlotNumber          INTEGER,
     mpsDS3StatusInputActive         INTEGER,
     mpsDS3StatusPllLock             INTEGER,
     mpsDS3StatusReceiveError        INTEGER,
     mpsDS3StatusInfobusInput1Active INTEGER,
     mpsDS3StatusInfobusInput2Active INTEGER,
     mpsDS3StatusTransmitPllLock     INTEGER,
     mpsDS3StatusTransmitFifo1Error  INTEGER,
     mpsDS3StatusTransmitFifo2Error  INTEGER,
     mpsDS3StatusReceiveFifo1Error   INTEGER,
     mpsDS3StatusReceiveFifo2Error   INTEGER
    }

mpsDS3StatusSlotNumber OBJECT-TYPE
    SYNTAX INTEGER (1..8) 
    ACCESS not-accessible
    STATUS mandatory
    DESCRIPTION  
        "The slot number of the DS3 card"
    REFERENCE " -- "
::= { mpsDS3StatusEntry 1}

mpsDS3StatusInputActive OBJECT-TYPE
    SYNTAX INTEGER
       {
        notActive (1),
        active    (2)
       }
    ACCESS read-only
    STATUS mandatory
    DESCRIPTION  
        "The Receive Input Transport Stream Activity indicator for the DS3 Card"
    REFERENCE " -- "
::= { mpsDS3StatusEntry 2}

mpsDS3StatusPllLock OBJECT-TYPE
    SYNTAX INTEGER
       {
        notLocked (1),
        locked    (2)
       }
    ACCESS read-only
    STATUS mandatory
    DESCRIPTION  
        "The Receive Data Rate PLL Lock indicator for the DS3 Card"
    REFERENCE " -- "
::= { mpsDS3StatusEntry 3}

mpsDS3StatusReceiveError OBJECT-TYPE
    SYNTAX INTEGER
       {
        noError (1),
        error   (2)
       }
    ACCESS read-only
    STATUS mandatory
    DESCRIPTION  
        "The Receive Input Error indicator for the DS3 Card"
    REFERENCE " -- "
::= { mpsDS3StatusEntry 4}

mpsDS3StatusInfobusInput1Active OBJECT-TYPE
    SYNTAX INTEGER
       {
        notActive (1),
        active    (2)
       }
    ACCESS read-only
    STATUS mandatory
    DESCRIPTION  
        "The Infobus Input 1 Transport Stream Activity indicator for the DS3 Card"
    REFERENCE " -- "
::= { mpsDS3StatusEntry 5}

mpsDS3StatusInfobusInput2Active OBJECT-TYPE
    SYNTAX INTEGER
       {
        notActive (1),
        active    (2)
       }
    ACCESS read-only
    STATUS mandatory
    DESCRIPTION  
        "The Infobus Input 2 Transport Stream Activity indicator for the DS3 Card"
    REFERENCE " -- "
::= { mpsDS3StatusEntry 6}
 
mpsDS3StatusTransmitPllLock OBJECT-TYPE
    SYNTAX INTEGER
       {
        notLocked (1),
        locked    (2)
       }
    ACCESS read-only
    STATUS mandatory
    DESCRIPTION
        "The Transmit Data Rate PLL Lock indicator for the DS3 Card"
    REFERENCE " -- "
::= { mpsDS3StatusEntry 7}

mpsDS3StatusTransmitFifo1Error OBJECT-TYPE
    SYNTAX INTEGER
       {
        noError (1),
        error   (2)
       }
    ACCESS read-only
    STATUS mandatory
    DESCRIPTION  
        "The Transmit FIFO 1 Error indicator for the DS3 Card"
    REFERENCE " -- "
::= { mpsDS3StatusEntry 8}

mpsDS3StatusTransmitFifo2Error OBJECT-TYPE
    SYNTAX INTEGER
       {
        noError (1),
        error   (2)
       }
    ACCESS read-only
    STATUS mandatory
    DESCRIPTION  
        "The Transmit FIFO 2 Error indicator for the DS3 Card"
    REFERENCE " -- "
::= { mpsDS3StatusEntry 9}

mpsDS3StatusReceiveFifo1Error OBJECT-TYPE
    SYNTAX INTEGER
       {
        noError (1),
        error   (2)
       }
    ACCESS read-only
    STATUS mandatory
    DESCRIPTION  
        "The Receive FIFO 1 Error indicator for the DS3 Card"
    REFERENCE " -- "
::= { mpsDS3StatusEntry 10}

mpsDS3StatusReceiveFifo2Error OBJECT-TYPE
    SYNTAX INTEGER
       {
        noError (1),
        error   (2)
       }
    ACCESS read-only
    STATUS mandatory
    DESCRIPTION  
        "The Receive FIFO 2 Error indicator for the DS3 Card"
    REFERENCE " -- "
::= { mpsDS3StatusEntry 11}

mpsDheiOutputStatusTable OBJECT-TYPE
    SYNTAX SEQUENCE OF MpsDheiOutputStatusEntry
    ACCESS not-accessible
    STATUS mandatory
    DESCRIPTION  
        "A table of status parameters for DheiOutput cards"
::= { mpsDheiOutputStatus 1}

mpsDheiOutputStatusEntry OBJECT-TYPE
    SYNTAX MpsDheiOutputStatusEntry
    ACCESS not-accessible
    STATUS mandatory
    DESCRIPTION  
        "A row in the Dhei Output Status table"
    INDEX {mpsDheiOutputStatusSlotNumber}
::= { mpsDheiOutputStatusTable 1}

MpsDheiOutputStatusEntry ::= SEQUENCE
    {
     mpsDheiOutputStatusSlotNumber      INTEGER,
     mpsDheiOutputStatusInput1Active    INTEGER,
     mpsDheiOutputStatusInput2Active    INTEGER
    }

mpsDheiOutputStatusSlotNumber OBJECT-TYPE
    SYNTAX INTEGER (1..8) 
    ACCESS not-accessible
    STATUS mandatory
    DESCRIPTION  
        "The slot number of the Dhei Output card"
    REFERENCE " -- "
::= { mpsDheiOutputStatusEntry 1}

mpsDheiOutputStatusInput1Active OBJECT-TYPE
    SYNTAX INTEGER
       { 
        notActive (1),
        active    (2)
       }
    ACCESS read-only
    STATUS mandatory
    DESCRIPTION  
        "The Input Transport Stream Activity indicator for the Dhei Output Card"
    REFERENCE " -- "
::= { mpsDheiOutputStatusEntry 2}

mpsDheiOutputStatusInput2Active OBJECT-TYPE
    SYNTAX INTEGER
        {
         notActive (1),
         active    (2)
        }
    ACCESS read-only
    STATUS mandatory
    DESCRIPTION  
        "The Input Transport Stream Activity indicator for the Dhei Output Card"
    REFERENCE " -- "
::= { mpsDheiOutputStatusEntry 3}

mpsRemuxConfTable OBJECT-TYPE
    SYNTAX SEQUENCE OF MpsRemuxConfEntry
    ACCESS not-accessible
    STATUS mandatory
    DESCRIPTION  
        "A table of config parameters for Remux cards.  The remux module allows
         the configuration of the output clock through the parameters in this table.
         The user can configure the output clock source and the gapping to use.
         The gap is configured in one of two ways.  If the Override Packet Size
         parameter is set to false, the gap is configured by setting the Packet Size
         parameter to one of two common values, 188 or 204.  If the Overrid Packet
         Size parameter is set to true, then the gap is specified by setting the
         Gapped Clock Constant directly.  The Gapped Clock Enabled parameter is no
         longer used.
         Once written, a save must be performed via the mpsSysConfSaveConfig
         parameter and the MPS must be rebooted for the change to take effect."
::= { mpsRemuxConf 1}

mpsRemuxConfEntry OBJECT-TYPE
    SYNTAX MpsRemuxConfEntry
    ACCESS not-accessible
    STATUS mandatory
    DESCRIPTION  
        "A row in the Remux Conf table"
    INDEX {mpsRemuxConfSlotNumber, mpsRemuxConfOutput}
::= { mpsRemuxConfTable 1}

MpsRemuxConfEntry ::= SEQUENCE
    {
     mpsRemuxConfSlotNumber                 INTEGER,
     mpsRemuxConfOutput                     INTEGER,
     mpsRemuxConfDheiOutputEnabled          INTEGER,
     mpsRemuxConfClockSource                INTEGER,
     mpsRemuxConfGappedClockEnabled         INTEGER,
     mpsRemuxConfGappedClockConstant        INTEGER,
     mpsRemuxConfPacketSize                 INTEGER,
     mpsRemuxConfOverridePacketSize         INTEGER
    }

mpsRemuxConfSlotNumber OBJECT-TYPE
    SYNTAX INTEGER (1..8) 
    ACCESS not-accessible
    STATUS mandatory
    DESCRIPTION  
        "The slot number index for the Remux card"
    REFERENCE " -- "
::= { mpsRemuxConfEntry 1}

mpsRemuxConfOutput OBJECT-TYPE
    SYNTAX INTEGER (1..2) 
    ACCESS not-accessible
    STATUS mandatory
    DESCRIPTION  
        "The output index"
    REFERENCE " -- "
::= { mpsRemuxConfEntry 2}

mpsRemuxConfDheiOutputEnabled OBJECT-TYPE
    SYNTAX INTEGER
       {  
        disabled (1),
        enabled  (2)
       }
    ACCESS read-write
    STATUS mandatory
    DESCRIPTION  
        "Whether the DHEI output is enabled to be used.  This parameter is
         not currently supported.
         Once written, a save must be performed via the mpsSysConfSaveConfig
         parameter and the MPS must be rebooted for the change to take effect."
    REFERENCE " -- "
::= { mpsRemuxConfEntry 3}

mpsRemuxConfClockSource OBJECT-TYPE
    SYNTAX INTEGER
       {  
        vcxo1 (1),
        vcxo2 (2),
        vcxo3 (3),
        reserved (4),
        sysclk (5),
        input1 (6),
        input2 (7),
        input3 (8),
        input4 (9),
        input5 (10),
        input6 (11)
       }
    ACCESS read-write
    STATUS mandatory
    DESCRIPTION  
        "Source of clock for the output.
         Once written, a save must be performed via the mpsSysConfSaveConfig
         parameter and the MPS must be rebooted for the change to take effect."
    REFERENCE " -- "
::= { mpsRemuxConfEntry 4}

mpsRemuxConfGappedClockEnabled OBJECT-TYPE
    SYNTAX INTEGER
       {  
        disabled (1),
        enabled  (2)
       }
    ACCESS read-write
    STATUS mandatory
    DESCRIPTION  
        "This parameter is no longer used.
         Once written, a save must be performed via the mpsSysConfSaveConfig
         parameter and the MPS must be rebooted for the change to take effect."
    REFERENCE " -- "
::= { mpsRemuxConfEntry 5}

mpsRemuxConfGappedClockConstant OBJECT-TYPE
    SYNTAX INTEGER
    ACCESS read-write
    STATUS mandatory
    DESCRIPTION  
        "When mpsRemuxConfOverridePacketSize is set to true, this parameter
         is set to specify the Gapped Clock Constant that is desired.  When
         mpsRemuxConfOverridePacketSize is set to false, this parameter is
         written by the MPS to specify the Gapped Clock Constant equivelent
         to the setting specified by mpsRemuxConfPacketSize.
         Once written, a save must be performed via the mpsSysConfSaveConfig
         parameter and the MPS must be rebooted for the change to take effect."
    REFERENCE " -- "
::= { mpsRemuxConfEntry 6}

mpsRemuxConfPacketSize OBJECT-TYPE
    SYNTAX INTEGER
       {
         byte188 (1),
         byte204 (2)
       }
    ACCESS read-write
    STATUS mandatory
    DESCRIPTION  
        "When mpsRemuxConfOverridePacketSize is set to false, this parameter
         is specifies the gapping to be used, either 188 or 188+16(204). When
         mpsRemuxConfOverridePacketSize is set to false, this parameter is
         not used.
         Once written, a save must be performed via the mpsSysConfSaveConfig
         parameter and the MPS must be rebooted for the change to take effect."
    REFERENCE " -- "
::= { mpsRemuxConfEntry 7}

mpsRemuxConfOverridePacketSize OBJECT-TYPE
    SYNTAX INTEGER
       {
         true  (1),
         false (2)
       }
    ACCESS read-write
    STATUS mandatory
    DESCRIPTION  
        "This parameter is used to specify whether the gapping is set via the
         mpsRemuxConfPacketSize parameter or by mpsRemuxConfGappedClockConstant.
         Once written, a save must be performed via the mpsSysConfSaveConfig
         parameter and the MPS must be rebooted for the change to take effect."
    REFERENCE " -- "
::= { mpsRemuxConfEntry 8}

mpsRemuxStatusTable OBJECT-TYPE
    SYNTAX SEQUENCE OF MpsRemuxStatusEntry
    ACCESS not-accessible
    STATUS mandatory
    DESCRIPTION  
        "A table of status parameters for Remux cards"
::= { mpsRemuxStatus 1}

mpsRemuxStatusEntry OBJECT-TYPE
    SYNTAX MpsRemuxStatusEntry
    ACCESS not-accessible
    STATUS mandatory
    DESCRIPTION  
        "A row in the Remux Status table"
    INDEX {mpsRemuxStatusSlotNumber}
::= { mpsRemuxStatusTable 1}

MpsRemuxStatusEntry ::= SEQUENCE
    {
     mpsRemuxStatusSlotNumber        INTEGER,
     mpsRemuxStatusInput1Active      INTEGER,
     mpsRemuxStatusInput2Active      INTEGER,
     mpsRemuxStatusInput3Active      INTEGER,
     mpsRemuxStatusInput4Active      INTEGER,
     mpsRemuxStatusInput5Active      INTEGER,
     mpsRemuxStatusInput6Active      INTEGER,
     mpsRemuxStatusOutput1Active     INTEGER,
     mpsRemuxStatusOutput2Active     INTEGER,
     mpsRemuxStatusModuleError       INTEGER
    }

mpsRemuxStatusSlotNumber OBJECT-TYPE
    SYNTAX INTEGER (1..8) 
    ACCESS not-accessible
    STATUS mandatory
    DESCRIPTION  
        "The slot number of the Remux card"
    REFERENCE " -- "
::= { mpsRemuxStatusEntry 1}

mpsRemuxStatusInput1Active OBJECT-TYPE
    SYNTAX INTEGER
       {  
        notActive (1),
        active  (2)
       }
    ACCESS read-only
    STATUS mandatory
    DESCRIPTION  
        "Whether the input is active"
    REFERENCE " -- "
::= { mpsRemuxStatusEntry 2}


mpsRemuxStatusInput2Active OBJECT-TYPE
    SYNTAX INTEGER
       {  
        notActive (1),
        active  (2)
       }
    ACCESS read-only
    STATUS mandatory
    DESCRIPTION  
        "Whether the input is active"
    REFERENCE " -- "
::= { mpsRemuxStatusEntry 3}

mpsRemuxStatusInput3Active OBJECT-TYPE
    SYNTAX INTEGER
       {  
        notActive (1),
        active  (2)
       }
    ACCESS read-only
    STATUS mandatory
    DESCRIPTION  
        "Whether the input is active"
    REFERENCE " -- "
::= { mpsRemuxStatusEntry 4}

mpsRemuxStatusInput4Active OBJECT-TYPE
    SYNTAX INTEGER
       {  
        notActive (1),
        active  (2)
       }
    ACCESS read-only
    STATUS mandatory
    DESCRIPTION  
        "Whether the input is active"
    REFERENCE " -- "
::= { mpsRemuxStatusEntry 5}

mpsRemuxStatusInput5Active OBJECT-TYPE
    SYNTAX INTEGER
       {  
        notActive (1),
        active  (2)
       }
    ACCESS read-only
    STATUS mandatory
    DESCRIPTION  
        "Whether the input is active"
    REFERENCE " -- "
::= { mpsRemuxStatusEntry 6}

mpsRemuxStatusInput6Active OBJECT-TYPE
    SYNTAX INTEGER
       {  
        notActive (1),
        active  (2)
       }
    ACCESS read-only
    STATUS mandatory
    DESCRIPTION  
        "Whether the input is active"
    REFERENCE " -- "
::= { mpsRemuxStatusEntry 7}


mpsRemuxStatusOutput1Active OBJECT-TYPE
    SYNTAX INTEGER
       {  
        notActive (1),
        active  (2)
       }
    ACCESS read-only
    STATUS mandatory
    DESCRIPTION  
        "Whether the output is active.  An active output has packets being multiplexed"
    REFERENCE " -- "
::= { mpsRemuxStatusEntry 8}


mpsRemuxStatusOutput2Active OBJECT-TYPE
    SYNTAX INTEGER
       {  
        notActive (1),
        active  (2)
       }
    ACCESS read-only
    STATUS mandatory
    DESCRIPTION  
        "Whether the output is active.  An active output has packets being multiplexed"
    REFERENCE " -- "
::= { mpsRemuxStatusEntry 9}

mpsRemuxStatusModuleError OBJECT-TYPE
    SYNTAX INTEGER
       {  
        noError (1),
        error  (2)
       }
    ACCESS read-only
    STATUS mandatory
    DESCRIPTION  
        "Whether the module has an error"
    REFERENCE " -- "
::= { mpsRemuxStatusEntry 10}

-- Definition for Remux statistics  JQL001

mpsRemuxStatisticsLogFrozen OBJECT-TYPE
    SYNTAX INTEGER
    {
        false (1),
        true (2)
    }
    ACCESS read-write
    STATUS mandatory
    DESCRIPTION
        "This parameter is used to suspend gathering of remux statistics.
           By suspending the gathering of statistics, the user can read 
           a snapshot of the table where statistics are all frozen at the same
           moment in time.  Without freezing the gathering of statistics, each
           read from the table will be at a slightly later moment in time, 
           possibly producing inconsistent results.
           true -   suspend remux statistics log 
         false -  resume remux statistics log
           Writing this parameter has immediate effect.  The parameter is not
           saved between reboots and is initialized to false."
::= {mpsRemuxStatistics 1}

mpsRemuxStatisticsDataType OBJECT-TYPE
    SYNTAX INTEGER
    {
        oneSecData (1),
        avgData (2)
    }
    ACCESS read-write
    STATUS mandatory
    DESCRIPTION
        "This parameter is set to change the contents of this table
         to either average statistics or one second statistics.  When
         set to avgData, the statistics supplied are the average of
         the data gathered since the last time the mpsRemuxStatisticsDataReset
         parameter was set.  When set to oneSecData, the data gathered is 
         the statistics over the last one second interval of remux statistics
         gathered.  
         Once written, the change to this parameter will take immediate
         effect.  However, in order for the change to persist through 
         subsequent reboots or power cycles, the change must be saved via
         the mpsSysConfSaveConfig parameter."
::= {mpsRemuxStatistics 2}

mpsRemuxStatisticsDataReset OBJECT-TYPE
    SYNTAX INTEGER
    {
        reset(1)    
    }
    ACCESS read-write
    STATUS mandatory
    DESCRIPTION
          "This parameter is set to reset the avgData statistics in the log.
           Writing this parameter has immediate effect.  The parameter is not
           saved between reboots and is initialized to false."
::= {mpsRemuxStatistics 3}

mpsRemuxStatisticsTime OBJECT-TYPE
    SYNTAX INTEGER
    ACCESS read-only
    STATUS mandatory
    DESCRIPTION
         "This parameter reports the time since the last time when 
            mpsRemuxStatisticsDataReset was written in seconds."
::= {mpsRemuxStatistics 4}

mpsRemuxStatisticsDataTable OBJECT-TYPE
        SYNTAX  SEQUENCE OF MpsRemuxStatisticsDataEntry
        ACCESS  not-accessible
        STATUS  mandatory
        DESCRIPTION
                "A table of statistics data Remux cards.
                The table is indexed by slot number, remux input number
                and output number. The following shows an example of the
                statistics data.

                        Average Bandwidth Utilization
                       --------------------------------
                Input           Output1         Output2
                  1               10%             10%
                  2               20%             30%
                 ...              ...             ...

                Total
                -----             70%              60%

                Info Rate       27,000,000      38,800,000

                This table contains:
                  * Average bandwidth usage for each output of the given input
                  * Total bandwidth usage for each ouput of the total inputs
                  * Info rate for each output.
                  * Peak buffer usage for each input and ouput buffer
                  * Input overflow for each input. "
::={ mpsRemuxStatistics 5 }

mpsRemuxStatisticsDataEntry OBJECT-TYPE
        SYNTAX  MpsRemuxStatisticsDataEntry
        ACCESS  not-accessible
        STATUS  mandatory
        DESCRIPTION
                "A row in remux statistics table"
        INDEX { mpsRemuxStatisticsSlotNum,
                mpsRemuxStatisticsInputNum,
                mpsRemuxStatisticsOutputNum}
::={ mpsRemuxStatisticsDataTable 1}

MpsRemuxStatisticsDataEntry ::= SEQUENCE
{
        mpsRemuxStatisticsSlotNum          INTEGER,
        mpsRemuxStatisticsInputNum         INTEGER,
        mpsRemuxStatisticsOutputNum        INTEGER,
        mpsRemuxStatisticsOutBwUsage       INTEGER,
        mpsRemuxStatisticsTotalOutBwUsage  INTEGER,
        mpsRemuxStatisticsOutInfoRate      INTEGER,
        mpsRemuxStatisticsOutPeakBuffUsage INTEGER,
        mpsRemuxStatisticsInPeakBuffUsage  INTEGER,
        mpsRemuxStatisticsInputOverflow    INTEGER
}

mpsRemuxStatisticsSlotNum OBJECT-TYPE
        SYNTAX INTEGER (1..8)
        ACCESS          not-accessible
        STATUS          mandatory
        DESCRIPTION
                "The slot number index of Remux Card"
        REFERENCE "--"
::= {mpsRemuxStatisticsDataEntry 1}

mpsRemuxStatisticsInputNum OBJECT-TYPE
        SYNTAX INTEGER (1..6)
        ACCESS          not-accessible
        STATUS          mandatory
        DESCRIPTION
                "The Input number index of Remux Card"
        REFERENCE "--"
::= {mpsRemuxStatisticsDataEntry 2}

mpsRemuxStatisticsOutputNum OBJECT-TYPE
        SYNTAX INTEGER (1..2)
        ACCESS          not-accessible
        STATUS          mandatory
        DESCRIPTION
                "The Output number index of Remux Card"
        REFERENCE "--"
::= {mpsRemuxStatisticsDataEntry 3}

mpsRemuxStatisticsOutBwUsage OBJECT-TYPE
        SYNTAX  INTEGER
        ACCESS  read-only
        STATUS  mandatory
        DESCRIPTION
                "The value of average output bandwidth for
                a given input.  Specified as an integer value from 0 to 10000.
                Dividing this number by 100 gives the percentage bandwidth used."
        REFERENCE "--"
::={mpsRemuxStatisticsDataEntry 4}

mpsRemuxStatisticsTotalOutBwUsage OBJECT-TYPE
        SYNTAX  INTEGER
        ACCESS  read-only
        STATUS  mandatory
        DESCRIPTION
                "This hold the value of average output Bandwidth
                for all inputs.  Dividing this number by 100 gives the 
                percentage bandwidth used."
        REFERENCE "--"
::={mpsRemuxStatisticsDataEntry 5}

mpsRemuxStatisticsOutInfoRate OBJECT-TYPE
        SYNTAX  INTEGER
        ACCESS  read-only
        STATUS  mandatory
        DESCRIPTION
                "This hold the value of the remux output info rate in MBps"
        REFERENCE "--"
::={mpsRemuxStatisticsDataEntry 6}


mpsRemuxStatisticsOutPeakBuffUsage OBJECT-TYPE
        SYNTAX  INTEGER
        ACCESS  read-only
        STATUS  mandatory
        DESCRIPTION
                "This holds the value of the remux Peak Buffer Usage
                for an given output.  Peak Buffer usage indicates the
                maximum number of packets stored in the buffer during the
                interval measured."
        REFERENCE "--"
::={mpsRemuxStatisticsDataEntry 7}

mpsRemuxStatisticsInPeakBuffUsage OBJECT-TYPE
        SYNTAX  INTEGER
        ACCESS  read-only
        STATUS  mandatory
        DESCRIPTION
                "This holds the value of the remux Peak Buffer Usage
                for an given output.  Peak Buffer usage indicates the
                maximum number of packets stored in the buffer during the
                interval measured."
        REFERENCE "--"
::={mpsRemuxStatisticsDataEntry 8}

mpsRemuxStatisticsInputOverflow OBJECT-TYPE
        SYNTAX  INTEGER
        ACCESS  read-only
        STATUS  mandatory
        DESCRIPTION
                "This holds a count of Overflow events for the buffer
                for an given output during the interval measured."
        REFERENCE "--"
::={mpsRemuxStatisticsDataEntry 9}


mpsDvbQamConfTable OBJECT-TYPE
    SYNTAX SEQUENCE OF MpsDvbQamConfEntry
    ACCESS not-accessible
    STATUS mandatory
    DESCRIPTION  
        "A table of configuration parameters for DVB QAM cards.
         Once written, a save must be performed via the mpsSysConfSaveConfig
         parameter and the MPS must be rebooted for the change to take effect."
::= { mpsDvbQamConf 1}

mpsDvbQamConfEntry OBJECT-TYPE
    SYNTAX MpsDvbQamConfEntry
    ACCESS not-accessible
    STATUS mandatory
    DESCRIPTION  
        "A row in the DVB Qam Configuration table"
    INDEX {mpsDvbQamConfSlotNumber}
::= { mpsDvbQamConfTable 1}

MpsDvbQamConfEntry ::= SEQUENCE
    {
     mpsDvbQamConfSlotNumber           INTEGER,
     mpsDvbQamConfMode                 INTEGER,
     mpsDvbQamConfGainLevel            INTEGER,
     mpsDvbQamConfFrequency            INTEGER,
     mpsDvbQamConfDataRate             INTEGER,
     mpsDvbQamConfSpectrumInversion    INTEGER,
     mpsDvbQamConfRollOff              INTEGER
    }

mpsDvbQamConfSlotNumber OBJECT-TYPE
    SYNTAX INTEGER (1..8) 
    ACCESS not-accessible
    STATUS mandatory
    DESCRIPTION  
        "The slot number of the DVB Qam card"
    REFERENCE " -- "
::= { mpsDvbQamConfEntry 1}

mpsDvbQamConfMode OBJECT-TYPE
    SYNTAX INTEGER
        {  
         qam64 (1),
         qam256 (2)
        } 
    ACCESS read-write
    STATUS mandatory
    DESCRIPTION  
        "The Qam mode for the DVB Qam Card.
         Once written, a save must be performed via the mpsSysConfSaveConfig
         parameter and the MPS must be rebooted for the change to take effect."
    REFERENCE " -- "
::= { mpsDvbQamConfEntry 2}

mpsDvbQamConfGainLevel OBJECT-TYPE
    SYNTAX INTEGER (30..48)
    ACCESS read-write
    STATUS mandatory
    DESCRIPTION  
        "The Gain Control Level Setting for the DVB Qam card in dBmV.
         Once written, a save must be performed via the mpsSysConfSaveConfig
         parameter and the MPS must be rebooted for the change to take effect."
    REFERENCE " -- "
::= { mpsDvbQamConfEntry 3}

mpsDvbQamConfFrequency OBJECT-TYPE
    SYNTAX INTEGER (31000..41000)
    ACCESS read-write
    STATUS mandatory
    DESCRIPTION  
        "The IF Frequency control for the DVB Qam Card - range is 31,000 kHz to 
         41,000 kHz.
         Once written, a save must be performed via the mpsSysConfSaveConfig
         parameter and the MPS must be rebooted for the change to take effect."
    REFERENCE " -- "
::= { mpsDvbQamConfEntry 4}

mpsDvbQamConfDataRate OBJECT-TYPE
    SYNTAX INTEGER (860..9999) 
    ACCESS read-write
    STATUS mandatory
    DESCRIPTION  
        "The Symbol Data Rate Setting for the DVB Qam card - range is 860 ksps to 
         9,999 ksps.
         Once written, a save must be performed via the mpsSysConfSaveConfig
         parameter and the MPS must be rebooted for the change to take effect."
    REFERENCE " -- "
::= { mpsDvbQamConfEntry 5}

mpsDvbQamConfSpectrumInversion OBJECT-TYPE
    SYNTAX INTEGER
        {
         off (1),
         on (2)
        }
    ACCESS read-write
    STATUS mandatory
    DESCRIPTION  
        "The Spectrum Inversion Setting for the DVB Qam card.
         Once written, a save must be performed via the mpsSysConfSaveConfig
         parameter and the MPS must be rebooted for the change to take effect."
    REFERENCE " -- "
::= { mpsDvbQamConfEntry 6}

mpsDvbQamConfRollOff OBJECT-TYPE
    SYNTAX INTEGER
        {
         percent13 (13),
         percent15 (15)
        }
    ACCESS read-write
    STATUS mandatory
    DESCRIPTION  
        "The Roll-Off factor Setting for the DVB Qam card in percent.
         Once written, a save must be performed via the mpsSysConfSaveConfig
         parameter and the MPS must be rebooted for the change to take effect."
    REFERENCE " -- "
::= { mpsDvbQamConfEntry 7}

mpsDvbQamStatusTable OBJECT-TYPE
    SYNTAX SEQUENCE OF MpsDvbQamStatusEntry
    ACCESS not-accessible
    STATUS mandatory
    DESCRIPTION  
        "A table of status parameters for QAM cards"
::= { mpsDvbQamStatus 1}

mpsDvbQamStatusEntry OBJECT-TYPE
    SYNTAX MpsDvbQamStatusEntry
    ACCESS not-accessible
    STATUS mandatory
    DESCRIPTION  
        "A row in the Qam Status table"
    INDEX {mpsDvbQamStatusSlotNumber}
::= { mpsDvbQamStatusTable 1}

MpsDvbQamStatusEntry ::= SEQUENCE
    {
     mpsDvbQamStatusSlotNumber   INTEGER,
     mpsDvbQamStatusInputActive  INTEGER,
     mpsDvbQamStatusMpegLock     INTEGER,
     mpsDvbQamStatusFifoError    INTEGER
    }

mpsDvbQamStatusSlotNumber OBJECT-TYPE
    SYNTAX INTEGER (1..8) 
    ACCESS not-accessible
    STATUS mandatory
    DESCRIPTION  
        "The slot number of the Qam card"
    REFERENCE " -- "
::= { mpsDvbQamStatusEntry 1}

mpsDvbQamStatusInputActive OBJECT-TYPE
    SYNTAX INTEGER
       { 
        notActive (1),
        active (2)
       }
    ACCESS read-only
    STATUS mandatory
    DESCRIPTION  
        "The Input Transport Stream Activity indicator for the DVB Qam Card"
    REFERENCE " -- "
::= { mpsDvbQamStatusEntry 2}

mpsDvbQamStatusMpegLock OBJECT-TYPE
    SYNTAX INTEGER
        {
         notLocked (1),
         locked (2)
        }
    ACCESS read-only
    STATUS mandatory
    DESCRIPTION  
        "The MPEG Lock indicator for the DVB Qam Card.  Indicates that the module 
         receives a valid MPEG datastream and the internal sync stage is locked 
         to the MPEG syncbytes."
    REFERENCE " -- "
::= { mpsDvbQamStatusEntry 3}

mpsDvbQamStatusFifoError OBJECT-TYPE
    SYNTAX INTEGER
        {
         noError (1),
         error (2)
        }
    ACCESS read-only
    STATUS mandatory
    DESCRIPTION  
        "The FIFO Error indicator for the DVB Qam Card.  Indicates that a FIFO overflow has occurred."
    REFERENCE " -- "
::= { mpsDvbQamStatusEntry 4}

mpsDvbAsiConfTable OBJECT-TYPE
    SYNTAX SEQUENCE OF MpsDvbAsiConfEntry
    ACCESS not-accessible
    STATUS mandatory
    DESCRIPTION  
        "A table of configuration parameters for DVB ASI cards.
         Once written, a save must be performed via the mpsSysConfSaveConfig
         parameter and the MPS must be rebooted for the change to take effect."
::= { mpsDvbAsiConf 1}

mpsDvbAsiConfEntry OBJECT-TYPE
    SYNTAX MpsDvbAsiConfEntry
    ACCESS not-accessible
    STATUS mandatory
    DESCRIPTION  
        "A row in the DVB Asi Configuration table"
    INDEX {mpsDvbAsiConfSlotNumber}
::= { mpsDvbAsiConfTable 1}

MpsDvbAsiConfEntry ::= SEQUENCE
    {
     mpsDvbAsiConfSlotNumber           INTEGER,
     mpsDvbAsiConfInputEnabled         INTEGER,
     mpsDvbAsiConfPacketSize           INTEGER
    }

mpsDvbAsiConfSlotNumber OBJECT-TYPE
    SYNTAX INTEGER (1..8) 
    ACCESS not-accessible
    STATUS mandatory
    DESCRIPTION  
        "The slot number of the DVB Asi card"
    REFERENCE " -- "
::= { mpsDvbAsiConfEntry 1}

mpsDvbAsiConfInputEnabled OBJECT-TYPE
    SYNTAX INTEGER
        {
         disabled (1),
         enabled (2)
        }
    ACCESS read-write
    STATUS mandatory
    DESCRIPTION  
        "Whether the input is enabled to be used.  When disabled, for this input,
         all errors are suppressed from causing alarms.  Typically, a user will 
         set an input that has nothing connected to it to disabled to eliminate
         errors on the path.
         Once written, a save must be performed via the mpsSysConfSaveConfig
         parameter and the MPS must be rebooted for the change to take effect."
    REFERENCE " -- "
::= { mpsDvbAsiConfEntry 2}

mpsDvbAsiConfPacketSize OBJECT-TYPE
    SYNTAX INTEGER
        { 
         byte188 (1),
         byte204 (2)
        }
    ACCESS read-write
    STATUS mandatory
    DESCRIPTION  
        "The packet size for the DVB Asi Input Card.
         Once written, a save must be performed via the mpsSysConfSaveConfig
         parameter and the MPS must be rebooted for the change to take effect."
    REFERENCE " -- "
::= { mpsDvbAsiConfEntry 3}

mpsDvbAsiStatusTable OBJECT-TYPE
    SYNTAX SEQUENCE OF MpsDvbAsiStatusEntry
    ACCESS not-accessible
    STATUS mandatory
    DESCRIPTION  
        "A table of status parameters for Dvb Asi cards"
::= { mpsDvbAsiStatus 1}

mpsDvbAsiStatusEntry OBJECT-TYPE
    SYNTAX MpsDvbAsiStatusEntry
    ACCESS not-accessible
    STATUS mandatory
    DESCRIPTION  
        "A row in the Dvb Asi Status table"
    INDEX {mpsDvbAsiStatusSlotNumber}
::= { mpsDvbAsiStatusTable 1}

MpsDvbAsiStatusEntry ::= SEQUENCE
    {
     mpsDvbAsiStatusSlotNumber   INTEGER,
     mpsDvbAsiStatusInputActive  INTEGER,
     mpsDvbAsiStatusMpegLock     INTEGER,
     mpsDvbAsiStatusFifoError    INTEGER
    }

mpsDvbAsiStatusSlotNumber OBJECT-TYPE
    SYNTAX INTEGER (1..8) 
    ACCESS not-accessible
    STATUS mandatory
    DESCRIPTION  
        "The slot number of the Dvb Asi card"
    REFERENCE " -- "
::= { mpsDvbAsiStatusEntry 1}

mpsDvbAsiStatusInputActive OBJECT-TYPE
    SYNTAX INTEGER
       { 
        notActive (1),
        active (2)
       }
    ACCESS read-only
    STATUS mandatory
    DESCRIPTION  
        "The Input Transport Stream Activity indicator for the DVB Asi Card"
    REFERENCE " -- "
::= { mpsDvbAsiStatusEntry 2}

mpsDvbAsiStatusMpegLock OBJECT-TYPE
    SYNTAX INTEGER
        {
         notLocked (1),
         locked (2)
        }
    ACCESS read-only
    STATUS mandatory
    DESCRIPTION  
        "The MPEG Lock indicator for the DVB Asi Card.  Indicates that the module 
         receives a valid MPEG datastream and the internal sync stage is locked 
         to the MPEG syncbytes."
    REFERENCE " -- "
::= { mpsDvbAsiStatusEntry 3}

mpsDvbAsiStatusFifoError OBJECT-TYPE
    SYNTAX INTEGER
        {
         noError (1),
         error (2)
        }
    ACCESS read-only
    STATUS mandatory
    DESCRIPTION  
        "The FIFO Error indicator for the DVB Asi Card.  Indicates that a FIFO overflow has occurred."
    REFERENCE " -- "
::= { mpsDvbAsiStatusEntry 4}

mpsLbandInConfControlTable OBJECT-TYPE
    SYNTAX SEQUENCE OF MpsLbandInConfControlEntry
    ACCESS not-accessible
    STATUS mandatory
    DESCRIPTION  
        "A table of configuration control parameters for LbandIn cards"
::= { mpsLbandInConf 1}

mpsLbandInConfControlEntry OBJECT-TYPE
    SYNTAX MpsLbandInConfControlEntry
    ACCESS not-accessible
    STATUS mandatory
    DESCRIPTION  
        "A row in the LbandIn Conf table"
    INDEX {mpsLbandInConfControlSlotNumber, mpsLbandInConfControlPath}
::= { mpsLbandInConfControlTable 1}

MpsLbandInConfControlEntry ::= SEQUENCE
    {
     mpsLbandInConfControlSlotNumber     INTEGER,
     mpsLbandInConfControlPath           INTEGER,
     mpsLbandInConfDebugEnable           INTEGER,
     mpsLbandInConfRetuneInput           INTEGER,
     mpsLbandInConfResetRsErrors         INTEGER
    }

mpsLbandInConfControlSlotNumber OBJECT-TYPE
    SYNTAX INTEGER (1..8) 
    ACCESS not-accessible
    STATUS mandatory
    DESCRIPTION  
        "The slot number of the LbandIn card"
    REFERENCE " -- "
::= { mpsLbandInConfControlEntry 1}

mpsLbandInConfControlPath OBJECT-TYPE
    SYNTAX INTEGER (1..2) 
    ACCESS not-accessible
    STATUS mandatory
    DESCRIPTION  
        "Which path the configuration parameters are applied to."
    REFERENCE " -- "
::= { mpsLbandInConfControlEntry 2}

mpsLbandInConfDebugEnable OBJECT-TYPE
    SYNTAX INTEGER
       {  
        disabled (1),
        enabled  (2)
       }
    ACCESS read-write
    STATUS mandatory
    DESCRIPTION  
        "This parameter is available for internal debug only.  This parameter
         should not be written"
    REFERENCE " -- "
::= { mpsLbandInConfControlEntry 3}

mpsLbandInConfRetuneInput OBJECT-TYPE
    SYNTAX INTEGER
       {  
         retuneNotInProgress (1),
         retuneNow           (2)
       }
    ACCESS read-write
    STATUS mandatory
    DESCRIPTION  
        "When modifying L-Band configuration parameters in the 
         mpsLbandInConfPathTable this parameter must always be written, as
         a final step, to cause the changes to take affect.  By waiting to
         retune the input until this parameter has been set, multiple updates
         can be made to the mpsLbandInConfPathTable and applied for the same
         retune event."
    REFERENCE " -- "
::= { mpsLbandInConfControlEntry 4}

mpsLbandInConfResetRsErrors OBJECT-TYPE
    SYNTAX INTEGER
       {  
         waitingToReset (1),
         resetNow       (2)
       }
    ACCESS read-write
    STATUS mandatory
    DESCRIPTION  
        "Causes the Lband Status parameters for Reed-Solomon errors
         (uncorrectable/correctable) to be reset."
    REFERENCE " -- "
::= { mpsLbandInConfControlEntry 5}

mpsLbandInConfPathTable OBJECT-TYPE
    SYNTAX SEQUENCE OF MpsLbandInConfPathEntry
    ACCESS not-accessible
    STATUS mandatory
    DESCRIPTION  
        "A table of config parameters for LbandIn cards.  This table
         allows the user to specify the tuning parameters of the input.
         Input paths may be inabled or disabled.  Frequency, Mode, Symbol
         Rate, Viterbi Rate, Output Clock Mode, and Gapping may be specified.
         The Frequency is set by setting the mpsLbandInConfInputFrequency
         parameter.
         Other tuning parameters are specified in one of two ways.  If the 
         mpsLbandInConfOverrideCommonConfig parameter is set to false, then
         tuning parameters are selected from a single enumeration of common
         configurations specified by mpsLbandInConfCommonConfig.  If the 
         mpsLbandInConfOverrideCommonConfig parameter is set to true, then
         tuning parameters are by specifying the Mode,Frequency,Symbol Rate,
         Viterbi Rate, and Clock Mode seperately. This is termed advanced mode.
         When operating in advanced mode, the gapping is specified in one of
         two ways.  If the Override Packet Size parameter is set to false, then
         the gapping is specified by setting the Packet Size parameter to one
         of two common gaps: 188 or 188+16 (204 mode).  When the Override Packet
         Size parameter is set to true, then the gapping is specified by setting
         the Gapped Clock Constant.
         The Gapped Clock Enabled parameter is no longer used.
         Writes to any of these fields do not take effect until the 
         mpsLbandInConfRetuneInput from the previous table is written.
         Additionally, in order for the change to persist through 
         subsequent reboots or power cycles, the change must be saved via
         the mpsSysConfSaveConfig parameter."
::= { mpsLbandInConf 2}

mpsLbandInConfPathEntry OBJECT-TYPE
    SYNTAX MpsLbandInConfPathEntry
    ACCESS not-accessible
    STATUS mandatory
    DESCRIPTION  
        "A row in the LbandIn Conf table"
    INDEX {mpsLbandInConfPathSlotNumber, mpsLbandInConfPath}
::= { mpsLbandInConfPathTable 1}

MpsLbandInConfPathEntry ::= SEQUENCE
    {
     mpsLbandInConfPathSlotNumber        INTEGER,
     mpsLbandInConfPath                  INTEGER,
     mpsLbandInConfInputEnabled          INTEGER,
     mpsLbandInConfInputMode             INTEGER,
     mpsLbandInConfInputFrequency        INTEGER,
     mpsLbandInConfInputSymbolRate       INTEGER,
     mpsLbandInConfInputViterbiRate      INTEGER,
     mpsLbandInConfOutputClockMode       INTEGER,
     mpsLbandInConfGappedClockEnabled    INTEGER,
     mpsLbandInConfGappedClockConstant   INTEGER,
     mpsLbandInConfCommonConfig          INTEGER,
     mpsLbandInConfOverrideCommonConfig  INTEGER,
     mpsLbandInConfPacketSize            INTEGER,
     mpsLbandInConfOverridePacketSize    INTEGER
    }

mpsLbandInConfPathSlotNumber OBJECT-TYPE
    SYNTAX INTEGER (1..8) 
    ACCESS not-accessible
    STATUS mandatory
    DESCRIPTION  
        "The slot number index of the LbandIn card"
    REFERENCE " -- "
::= { mpsLbandInConfPathEntry 1}

mpsLbandInConfPath OBJECT-TYPE
    SYNTAX INTEGER (1..2)
    ACCESS not-accessible
    STATUS mandatory
    DESCRIPTION  
        "The path index for the path to be tuned."
    REFERENCE " -- "
::= { mpsLbandInConfPathEntry 2}

mpsLbandInConfInputEnabled OBJECT-TYPE
    SYNTAX INTEGER
       {  
        disabled (1),
        enabled  (2)
       }
    ACCESS read-write
    STATUS mandatory
    DESCRIPTION  
        "Whether the input is enabled to be used.  When disabled, for this input,
         all errors are suppressed from causing alarms.  Typically, a user will 
         set an input that has nothing connected to it to disabled to eliminate
         errors on the path.
         Once written, a save must be performed via the mpsSysConfSaveConfig
         parameter and the MPS must be rebooted for the change to take effect."
    REFERENCE " -- "
::= { mpsLbandInConfPathEntry 3}

mpsLbandInConfInputMode OBJECT-TYPE
    SYNTAX INTEGER
       {  
        dcIIcombined   (1),
        dcIIsplitI     (2),
        dcIIsplitQ     (3),
        dvb            (4),
        dss            (5)
       }
    ACCESS read-write
    STATUS mandatory
    DESCRIPTION  
        "Input mode selection.  This specifies the input mode that the Lband is 
         to tune.  
         When the mpsLbandInConfOverrideCommonConfig parameter is set to true,
         the value set here is used in tuning the input.  When the 
         mpsLbandInConfOverrideCommonConfig is set to false, the MPS will
         overwrite this value when tuning the input to coorespond to the appropriate
         setting as compared to the selection in the mpsLbandInConfCommonConfig 
         parameter.
         Writes to this field do not take effect until the 
         mpsLbandInConfRetuneInput from the previous table is written.
         Additionally, in order for the change to persist through 
         subsequent reboots or power cycles, the change must be saved via
         the mpsSysConfSaveConfig parameter."
    REFERENCE " -- "
::= { mpsLbandInConfPathEntry 4}

mpsLbandInConfInputFrequency OBJECT-TYPE
    SYNTAX INTEGER (950000..2150000)
    ACCESS read-write
    STATUS mandatory
    DESCRIPTION  
        "The IF Frequency setting for the input - range is 950,000 kHz to 2,150,000 kHz.
         When the mpsLbandInConfOverrideCommonConfig parameter is set to true,
         the value set here is used in tuning the input.  When the 
         mpsLbandInConfOverrideCommonConfig is set to false, the MPS will
         overwrite this value when tuning the input to coorespond to the appropriate
         setting as compared to the selection in the mpsLbandInConfCommonConfig 
         parameter.
         Writes to this field do not take effect until the 
         mpsLbandInConfRetuneInput from the previous table is written.
         Additionally, in order for the change to persist through 
         subsequent reboots or power cycles, the change must be saved via
         the mpsSysConfSaveConfig parameter."
    REFERENCE " -- "
::= { mpsLbandInConfPathEntry 5}

mpsLbandInConfInputSymbolRate OBJECT-TYPE
    SYNTAX INTEGER (1000..45000)
    ACCESS read-write
    STATUS mandatory
    DESCRIPTION  
        "The Symbol Data Rate setting for the input - range is 1,000 ksps to 45,000 ksps.
         When the mpsLbandInConfOverrideCommonConfig parameter is set to true,
         the value set here is used in tuning the input.  When the 
         mpsLbandInConfOverrideCommonConfig is set to false, the MPS will
         overwrite this value when tuning the input to coorespond to the appropriate
         setting as compared to the selection in the mpsLbandInConfCommonConfig 
         parameter.
         Writes to this field do not take effect until the 
         mpsLbandInConfRetuneInput from the previous table is written.
         Additionally, in order for the change to persist through 
         subsequent reboots or power cycles, the change must be saved via
         the mpsSysConfSaveConfig parameter."
    REFERENCE " -- "
::= { mpsLbandInConfPathEntry 6}

mpsLbandInConfInputViterbiRate OBJECT-TYPE
    SYNTAX INTEGER
       {  
        dvbDirectTvOneHalf         (1),
        dvbDirectTvTwoThirds       (2),
        dvbDirectTvThreeFourths    (3),
        dvbDirectTvFiveSixths      (4),
        dvbDirectTvSixthSevenths   (5),
        dvbDirectTvSevenEighths    (6),
        dcIIFiveElevenths          (9),
        dcIIOneHalf                (10),
        dcIIThreeFifths            (11),
        dcIITwoThirds              (12),
        dcIIThreeFourths           (13),
        dcIIFourFifths             (14),
        dcIIFiveSixths             (15),
        dcIISevenEighths           (16),
        dvbScan                    (17),
        directTvScan               (18),
        dcIIScan                   (19)
       }
    ACCESS read-write
    STATUS mandatory
    DESCRIPTION  
        "The Viterbi Rate setting for the input.
         When the mpsLbandInConfOverrideCommonConfig parameter is set to true,
         the value set here is used in tuning the input.  When the 
         mpsLbandInConfOverrideCommonConfig is set to false, the MPS will
         overwrite this value when tuning the input to coorespond to the appropriate
         setting as compared to the selection in the mpsLbandInConfCommonConfig 
         parameter.
         Writes to this field do not take effect until the 
         mpsLbandInConfRetuneInput from the previous table is written.
         Additionally, in order for the change to persist through 
         subsequent reboots or power cycles, the change must be saved via
         the mpsSysConfSaveConfig parameter."
    REFERENCE " -- "
::= { mpsLbandInConfPathEntry 7}

mpsLbandInConfOutputClockMode OBJECT-TYPE
    SYNTAX INTEGER
       {  
        lockedToInputSymbolRate29260KHz  (1),
        localFreeRun29260KHz             (2),
        localFreeRun38810KHz             (3),
        localFreeRun54000KHz             (4), 
        direct                            (5)
       }
    ACCESS read-write
    STATUS mandatory
    DESCRIPTION  
        "The output clock mode.
         When the mpsLbandInConfOverrideCommonConfig parameter is set to true,
         the value set here is used in tuning the input.  When the 
         mpsLbandInConfOverrideCommonConfig is set to false, the MPS will
         overwrite this value when tuning the input to coorespond to the appropriate
         setting as compared to the selection in the mpsLbandInConfCommonConfig 
         parameter.
         Writes to this field do not take effect until the 
         mpsLbandInConfRetuneInput from the previous table is written.
         Additionally, in order for the change to persist through 
         subsequent reboots or power cycles, the change must be saved via
         the mpsSysConfSaveConfig parameter."
    REFERENCE " -- "
::= { mpsLbandInConfPathEntry 8}

mpsLbandInConfGappedClockEnabled OBJECT-TYPE
    SYNTAX INTEGER
       {  
        disabled (1),
        enabled  (2)
       }
    ACCESS read-write
    STATUS mandatory
    DESCRIPTION  
        "This parameter is no longer used."
    REFERENCE " -- "
::= { mpsLbandInConfPathEntry 9}

mpsLbandInConfGappedClockConstant OBJECT-TYPE
    SYNTAX INTEGER
    ACCESS read-write
    STATUS mandatory
    DESCRIPTION  
        "When the mpsLbandInConfOverrideCommonConfig parameter is set to true,
         the value set here may be used in setting the gapping.  When the 
         mpsLbandInConfOverrideCommonConfig is set to false, the MPS will
         overwrite this value when tuning the input to coorespond to the appropriate
         setting as compared to the selection in the mpsLbandInConfCommonConfig 
         parameter.
         If used, the following additional checking is performed.
         When mpsLbandConfOverridePacketSize is set to true, this parameter
         is set to specify the Gapped Clock Constant that is desired.  When
         mpsLbandConfOverridePacketSize is set to false, this parameter is
         written by the MPS to specify the Gapped Clock Constant equivalent
         to the setting specified by mpsRemuxConfPacketSize.
         Writes to this field do not take effect until the 
         mpsLbandInConfRetuneInput from the previous table is written.
         Additionally, in order for the change to persist through 
         subsequent reboots or power cycles, the change must be saved via
         the mpsSysConfSaveConfig parameter."
    REFERENCE " -- "
::= { mpsLbandInConfPathEntry 10}

mpsLbandInConfCommonConfig OBJECT-TYPE
    SYNTAX INTEGER
       { 
         comb975threeFourthsFEC    (1),
         comb1951threeFourthsFEC   (2),
         comb2927oneHalfFEC        (3),
         comb2927threeFourthsFEC   (4),
         splitI2927sevenEighthsFEC (5),
         splitQ2927sevenEighthsFEC (6)
       }
    ACCESS read-write
    STATUS mandatory
    DESCRIPTION  
        "When the mpsLbandInConfOverrideCommonConfig parameter is set to false,
         the value set here is used when tuning the input.  Parameters above
         are defaulted to values cooresponding the selected common config setting.
         For most applications this parameter and the frequency are the only 
         parameters that are required to be set.
         Writes to this field do not take effect until the 
         mpsLbandInConfRetuneInput from the previous table is written.
         Additionally, in order for the change to persist through 
         subsequent reboots or power cycles, the change must be saved via
         the mpsSysConfSaveConfig parameter."
    REFERENCE " -- "
::= { mpsLbandInConfPathEntry 11}

mpsLbandInConfOverrideCommonConfig OBJECT-TYPE
    SYNTAX INTEGER
       {
         true  (1),
         false (2)
       }
    ACCESS read-write
    STATUS mandatory
    DESCRIPTION  
        "This parameter is set to specify whether to use the Common Config
         parameter when tuning the input.  If set to false, then the Common
         Config parameter is used to tune the input and the other tuning
         parameters are defaulted to cooresponding values.  When set to true,
         the Common Config Setting is ignored and the other tuning parameters
         are used directly.
         Writes to this field do not take effect until the 
         mpsLbandInConfRetuneInput from the previous table is written.
         Additionally, in order for the change to persist through 
         subsequent reboots or power cycles, the change must be saved via
         the mpsSysConfSaveConfig parameter."
    REFERENCE " -- "
::= { mpsLbandInConfPathEntry 12}

mpsLbandInConfPacketSize OBJECT-TYPE
    SYNTAX INTEGER
       {
         byte188 (1),
         byte204 (2)
       }
    ACCESS read-write
    STATUS mandatory
    DESCRIPTION  
        "When mpsLbandConfOverridePacketSize is set to true, this parameter
         is set to specify the Gapped Clock Constant that is desired.  When
         mpsLbandConfOverridePacketSize is set to false, this parameter is
         written by the MPS to specify the Gapped Clock Constant equivelent
         to the setting specified by mpsRemuxConfPacketSize.
         Writes to this field do not take effect until the 
         mpsLbandInConfRetuneInput from the previous table is written.
         Additionally, in order for the change to persist through 
         subsequent reboots or power cycles, the change must be saved via
         the mpsSysConfSaveConfig parameter."
    REFERENCE " -- "
::= { mpsLbandInConfPathEntry 13}

mpsLbandInConfOverridePacketSize OBJECT-TYPE
    SYNTAX INTEGER
       {
         true  (1),
         false (2)
       }
    ACCESS read-write
    STATUS mandatory
    DESCRIPTION  
        "This parameter is set to specify whether to use the Packet Size
         parameter when setting the output gap.  If set to false, then the 
         Packet Size parameter is used to set the gap.  When set to true,
         the Gapped Clock Constant is used.
         Writes to this field do not take effect until the 
         mpsLbandInConfRetuneInput from the previous table is written.
         Additionally, in order for the change to persist through 
         subsequent reboots or power cycles, the change must be saved via
         the mpsSysConfSaveConfig parameter."
    REFERENCE " -- "
::= { mpsLbandInConfPathEntry 14}


mpsLbandInStatusTable OBJECT-TYPE
    SYNTAX SEQUENCE OF MpsLbandInStatusEntry
    ACCESS not-accessible
    STATUS mandatory
    DESCRIPTION  
        "A table of status parameters for LbandIn cards"
::= { mpsLbandInStatus 1}

mpsLbandInStatusEntry OBJECT-TYPE
    SYNTAX MpsLbandInStatusEntry
    ACCESS not-accessible
    STATUS mandatory
    DESCRIPTION  
        "A row in the LbandIn Status table"
    INDEX {mpsLbandInStatusSlotNumber}
::= { mpsLbandInStatusTable 1}

MpsLbandInStatusEntry ::= SEQUENCE
    {
     mpsLbandInStatusSlotNumber                   INTEGER,
     mpsLbandInStatusAuxDataBuffer                INTEGER
    }

mpsLbandInStatusSlotNumber OBJECT-TYPE
    SYNTAX INTEGER (1..8) 
    ACCESS not-accessible
    STATUS mandatory
    DESCRIPTION  
        "The slot number of the LbandIn card"
    REFERENCE " -- "
::= { mpsLbandInStatusEntry 1}

mpsLbandInStatusAuxDataBuffer OBJECT-TYPE
    SYNTAX INTEGER
       {
        empty    (1),
        active   (2),
        overflow (3)
       }
    ACCESS read-only
    STATUS mandatory
    DESCRIPTION  
        "The status of the Auxilliary Data Buffer."
    REFERENCE " -- "
::= { mpsLbandInStatusEntry 2}

mpsLbandInStatusPathTable OBJECT-TYPE
    SYNTAX SEQUENCE OF MpsLbandInStatusPathEntry
    ACCESS not-accessible
    STATUS mandatory
    DESCRIPTION  
        "A table of status parameters for a path in the LbandIn cards"
::= { mpsLbandInStatus 2}

mpsLbandInStatusPathEntry OBJECT-TYPE
    SYNTAX MpsLbandInStatusPathEntry
    ACCESS not-accessible
    STATUS mandatory
    DESCRIPTION  
        "A row in the LbandIn Status Path table"
    INDEX {mpsLbandInStatusPathSlotNumber, mpsLbandInStatusPath}
::= { mpsLbandInStatusPathTable 1}

MpsLbandInStatusPathEntry ::= SEQUENCE
    {
     mpsLbandInStatusPathSlotNumber          INTEGER,
     mpsLbandInStatusPath                    INTEGER,
     mpsLbandInStatusLnbPower                INTEGER,
     mpsLbandInStatusFrequencyLock           INTEGER,
     mpsLbandInStatusSnrLock                 INTEGER,
     mpsLbandInStatusReceiverLock            INTEGER,
     mpsLbandInStatusViterbiLock             INTEGER,
     mpsLbandInStatusReedSolomonLock         INTEGER,
     mpsLbandInStatusFrequencyError          INTEGER,
     mpsLbandInStatusSignalLevel             INTEGER,
     mpsLbandInStatusSignalToNoiseRatio      INTEGER,
     mpsLbandInStatusUncorrectableRsErrors   INTEGER,
     mpsLbandInStatusCorrectableRsErrors     INTEGER,
     mpsLbandInStatusOutputMpegProcessing    INTEGER,
     mpsLbandInStatusOutputChannelBuffer     INTEGER,
     mpsLbandInStatusPllLock                 INTEGER,
     mpsLbandInStatusEbNo                    INTEGER
    }

mpsLbandInStatusPathSlotNumber OBJECT-TYPE
    SYNTAX INTEGER (1..8) 
    ACCESS not-accessible
    STATUS mandatory
    DESCRIPTION  
        "The slot number of the LbandIn card"
    REFERENCE " -- "
::= { mpsLbandInStatusPathEntry 1}

mpsLbandInStatusPath OBJECT-TYPE
    SYNTAX INTEGER (1..2)
    ACCESS not-accessible
    STATUS mandatory
    DESCRIPTION  
        "Which path the status parameters apply to."
    REFERENCE " -- "
::= { mpsLbandInStatusPathEntry 2}

mpsLbandInStatusLnbPower OBJECT-TYPE
    SYNTAX INTEGER
       {  
        off   (1),
        on    (2),
        fault (3)
       }
    ACCESS read-only
    STATUS mandatory
    DESCRIPTION  
        "Input LNB Power status.  LNB power is turned on and off via a jumper
         on the Lband module.  Please reference the Lband user manual for more
         information."
    REFERENCE " -- "
::= { mpsLbandInStatusPathEntry 3}

mpsLbandInStatusFrequencyLock OBJECT-TYPE
    SYNTAX INTEGER
       {  
         notLocked (1),
         locked    (2)
       }
    ACCESS read-only
    STATUS mandatory
    DESCRIPTION  
        "Frequency lock status."
    REFERENCE " -- "
::= { mpsLbandInStatusPathEntry 4}

mpsLbandInStatusSnrLock OBJECT-TYPE
    SYNTAX INTEGER
       {  
         notLocked (1),
         locked    (2)
       }
    ACCESS read-only
    STATUS mandatory
    DESCRIPTION  
        "Signal-to-Noise Ratio lock status."
    REFERENCE " -- "
::= { mpsLbandInStatusPathEntry 5}

mpsLbandInStatusReceiverLock OBJECT-TYPE
    SYNTAX INTEGER
       {  
         notLocked (1),
         locked    (2)
       }
    ACCESS read-only
    STATUS mandatory
    DESCRIPTION  
        "Receiver lock status."
    REFERENCE " -- "
::= { mpsLbandInStatusPathEntry 6}

mpsLbandInStatusViterbiLock OBJECT-TYPE
    SYNTAX INTEGER
       {  
         notLocked (1),
         locked    (2)
       }
    ACCESS read-only
    STATUS mandatory
    DESCRIPTION  
        "Viterbi lock status."
    REFERENCE " -- "
::= { mpsLbandInStatusPathEntry 7}

mpsLbandInStatusReedSolomonLock OBJECT-TYPE
    SYNTAX INTEGER
       {  
         notLocked (1),
         locked    (2)
       }
    ACCESS read-only
    STATUS mandatory
    DESCRIPTION  
        "Reed Solomon lock status."
    REFERENCE " -- "
::= { mpsLbandInStatusPathEntry 8}

mpsLbandInStatusFrequencyError OBJECT-TYPE
    SYNTAX INTEGER
    ACCESS read-only
    STATUS mandatory
    DESCRIPTION  
        "Frequency Error in kHz."
    REFERENCE " -- "
::= { mpsLbandInStatusPathEntry 9}

mpsLbandInStatusSignalLevel OBJECT-TYPE
    SYNTAX INTEGER
    ACCESS read-only
    STATUS mandatory
    DESCRIPTION  
        "Signal Level.  A value from 0 to 100% indicating the
         signal strength from -65 dBm to -25 dBm respectively"
    REFERENCE " -- "
::= { mpsLbandInStatusPathEntry 10}

mpsLbandInStatusSignalToNoiseRatio OBJECT-TYPE
    SYNTAX INTEGER
    ACCESS read-only
    STATUS mandatory
    DESCRIPTION  
        "Signal-to-Noise Ratio in dB."
    REFERENCE " -- "
::= { mpsLbandInStatusPathEntry 11}

mpsLbandInStatusUncorrectableRsErrors OBJECT-TYPE
    SYNTAX INTEGER
    ACCESS read-only
    STATUS mandatory
    DESCRIPTION  
        "Count of uncorrectable Reed-Solomon errors."
    REFERENCE " -- "
::= { mpsLbandInStatusPathEntry 12}

mpsLbandInStatusCorrectableRsErrors OBJECT-TYPE
    SYNTAX INTEGER
    ACCESS read-only
    STATUS mandatory
    DESCRIPTION  
        "Count of correctable Reed-Solomon errors."
    REFERENCE " -- "
::= { mpsLbandInStatusPathEntry 13}

mpsLbandInStatusOutputMpegProcessing OBJECT-TYPE
    SYNTAX INTEGER
        {
         noError (1),
         error (2)
        }
    ACCESS read-only
    STATUS mandatory
    DESCRIPTION  
        "Output MPEG Processing status."
    REFERENCE " -- "
::= { mpsLbandInStatusPathEntry 14}

mpsLbandInStatusOutputChannelBuffer OBJECT-TYPE
    SYNTAX INTEGER
       {
        empty    (1),
        active   (2),
        overflow (3)
       }
    ACCESS read-only
    STATUS mandatory
    DESCRIPTION  
        "Output Channel Buffer status."
    REFERENCE " -- "
::= { mpsLbandInStatusPathEntry 15}

mpsLbandInStatusPllLock OBJECT-TYPE
    SYNTAX INTEGER
       {  
         notLocked (1),
         locked    (2)
       }
    ACCESS read-only
    STATUS mandatory
    DESCRIPTION  
        "PLL lock status."
    REFERENCE " -- "
::= { mpsLbandInStatusPathEntry 16}

mpsLbandInStatusEbNo OBJECT-TYPE
    SYNTAX INTEGER
    ACCESS read-only
    STATUS mandatory
    DESCRIPTION  
        "The calculation of EbNo for the current input"
    REFERENCE " -- "
::= { mpsLbandInStatusPathEntry 17}

mpsDualDvbAsiOutConfTable OBJECT-TYPE
    SYNTAX SEQUENCE OF MpsDualDvbAsiOutConfEntry
    ACCESS not-accessible
    STATUS mandatory
    DESCRIPTION  
        "A table of configuration control parameters for DualDvbAsiOutcards"
::= { mpsDualDvbAsiOutConf 1}

mpsDualDvbAsiOutConfEntry OBJECT-TYPE
    SYNTAX MpsDualDvbAsiOutConfEntry
    ACCESS not-accessible
    STATUS mandatory
    DESCRIPTION  
        "A row in the DualDvbAsiOutput Conf table"
    INDEX {mpsDualDvbAsiOutConfSlotNumber, mpsDualDvbAsiOutConfPath}
::= { mpsDualDvbAsiOutConfTable 1}

MpsDualDvbAsiOutConfEntry ::= SEQUENCE
    {
     mpsDualDvbAsiOutConfSlotNumber    INTEGER,
     mpsDualDvbAsiOutConfPath          INTEGER,
     mpsDualDvbAsiOutConfInputSource   INTEGER,
     mpsDualDvbAsiOutConfMute          INTEGER
    }

mpsDualDvbAsiOutConfSlotNumber OBJECT-TYPE
    SYNTAX INTEGER (1..8) 
    ACCESS not-accessible
    STATUS mandatory
    DESCRIPTION  
        "The slot number of the DualDvbAsiOut card."
    REFERENCE " -- "
::= { mpsDualDvbAsiOutConfEntry 1}

mpsDualDvbAsiOutConfPath OBJECT-TYPE
    SYNTAX INTEGER (1..2) 
    ACCESS not-accessible
    STATUS mandatory
    DESCRIPTION  
        "Which path the configuration parameters are applied to."
    REFERENCE " -- "
::= { mpsDualDvbAsiOutConfEntry 2}

mpsDualDvbAsiOutConfInputSource OBJECT-TYPE
    SYNTAX INTEGER (1..4)
    ACCESS read-write
    STATUS mandatory
    DESCRIPTION  
      "Selects which Infobus Input, is routed to the Output.
       Once written, a save must be performed via the mpsSysConfSaveConfig
       parameter and the MPS must be rebooted for the change to take effect."
    REFERENCE " -- "
::= { mpsDualDvbAsiOutConfEntry 3}

mpsDualDvbAsiOutConfMute OBJECT-TYPE
    SYNTAX INTEGER
        {
         off (1),
         on  (2)
        } 
    ACCESS read-write
    STATUS mandatory
    DESCRIPTION  
        "Mute control for the output.
         Once written, the change to this parameter will take immediate
         affect.  However, in order for the change to persist through 
         subsequent reboots or power cycles, the change must be saved via
         the mpsSysConfSaveConfig parameter."
    REFERENCE " -- "
::= { mpsDualDvbAsiOutConfEntry 4}

mpsDualDvbAsiOutStatusTable OBJECT-TYPE
    SYNTAX SEQUENCE OF MpsDualDvbAsiOutStatusEntry
    ACCESS not-accessible
    STATUS mandatory
    DESCRIPTION  
        "A table of status parameters for DualDvbAsiOut cards"
::= { mpsDualDvbAsiOutStatus 1}

mpsDualDvbAsiOutStatusEntry OBJECT-TYPE
    SYNTAX MpsDualDvbAsiOutStatusEntry
    ACCESS not-accessible
    STATUS mandatory
    DESCRIPTION  
        "A row in the DualDvbAsiOut Status Path table"
    INDEX {mpsDualDvbAsiOutStatusSlotNumber, mpsDualDvbAsiOutStatusPath }
::= { mpsDualDvbAsiOutStatusTable 1}

MpsDualDvbAsiOutStatusEntry ::= SEQUENCE
    {
     mpsDualDvbAsiOutStatusSlotNumber       INTEGER,
     mpsDualDvbAsiOutStatusPath             INTEGER,
     mpsDualDvbAsiOutStatusInputActive      INTEGER
    }

mpsDualDvbAsiOutStatusSlotNumber OBJECT-TYPE
    SYNTAX INTEGER (1..8) 
    ACCESS not-accessible
    STATUS mandatory
    DESCRIPTION  
        "The slot number of the DualDvbAsiOut card"
    REFERENCE " -- "
::= { mpsDualDvbAsiOutStatusEntry 1}

mpsDualDvbAsiOutStatusPath OBJECT-TYPE
    SYNTAX INTEGER (1..2)
    ACCESS not-accessible
    STATUS mandatory
    DESCRIPTION  
        "Which path the status parameters apply to."
    REFERENCE " -- "
::= { mpsDualDvbAsiOutStatusEntry 2}

mpsDualDvbAsiOutStatusInputActive OBJECT-TYPE
    SYNTAX INTEGER
       {
        notActive (1),
        active (2)
       }
    ACCESS read-only
    STATUS mandatory
    DESCRIPTION
        "The Input Transport Stream Activity indicator for the Dual DVB Asi Out Card"
    REFERENCE " -- "
::= { mpsDualDvbAsiOutStatusEntry 3}





mpsDualDvbAsiInConfTable OBJECT-TYPE
    SYNTAX SEQUENCE OF MpsDualDvbAsiInConfEntry
    ACCESS not-accessible
    STATUS mandatory
    DESCRIPTION  
        "A table of configuration control parameters for Dual Dvb Asi Input cards.
         Writes to any of these fields do not take effect until the 
         last parameter, mpsDualDvbAsiInConfApply, is written.
         Additionally, in order for the change to persist through 
         subsequent reboots or power cycles, the change must be saved via
         the mpsSysConfSaveConfig parameter."
::= { mpsDualDvbAsiInConf 1}

mpsDualDvbAsiInConfEntry OBJECT-TYPE
    SYNTAX MpsDualDvbAsiInConfEntry
    ACCESS not-accessible
    STATUS mandatory
    DESCRIPTION  
        "A row in the DualDvbAsiInput Conf table"
    INDEX {mpsDualDvbAsiInConfSlotNumber, mpsDualDvbAsiInConfPath}
::= { mpsDualDvbAsiInConfTable 1}

MpsDualDvbAsiInConfEntry ::= SEQUENCE
    {
     mpsDualDvbAsiInConfSlotNumber    INTEGER,
     mpsDualDvbAsiInConfPath          INTEGER,
     mpsDualDvbAsiInConfInputEnabled  INTEGER,
     mpsDualDvbAsiInConfPacketSize    INTEGER,
     mpsDualDvbAsiInConfRefClock      INTEGER,
     mpsDualDvbAsiInConfClockPuncture INTEGER,
     mpsDualDvbAsiInConfSizeOverride  INTEGER,
     mpsDualDvbAsiInConfClockConstant INTEGER,
     mpsDualDvbAsiInConfApply         INTEGER
    }

mpsDualDvbAsiInConfSlotNumber OBJECT-TYPE
    SYNTAX INTEGER (1..8) 
    ACCESS not-accessible
    STATUS mandatory
    DESCRIPTION  
        "The slot number of the DualDvbAsiIn card."
    REFERENCE " -- "
::= { mpsDualDvbAsiInConfEntry 1}

mpsDualDvbAsiInConfPath OBJECT-TYPE
    SYNTAX INTEGER (1..2) 
    ACCESS not-accessible
    STATUS mandatory
    DESCRIPTION  
        "Which path the configuration parameters are applied to."
    REFERENCE " -- "
::= { mpsDualDvbAsiInConfEntry 2}

mpsDualDvbAsiInConfInputEnabled OBJECT-TYPE
    SYNTAX INTEGER
       {
        disabled (1),
        enabled  (2)
       }
    ACCESS read-write
    STATUS mandatory
    DESCRIPTION
        "Whether the input is enabled to be used.  When disabled, for this input,
         all errors are suppressed from causing alarms.  Typically, a user will 
         set an input that has nothing connected to it to disabled to eliminate
         errors on the path.
         Once written, a save must be performed via the mpsSysConfSaveConfig
         parameter and the MPS must be rebooted for the change to take effect."
    REFERENCE " -- "
::= { mpsDualDvbAsiInConfEntry 3}

mpsDualDvbAsiInConfPacketSize OBJECT-TYPE
    SYNTAX INTEGER
       {
        byte188 (1),
        byte204 (2)
       }
    ACCESS read-write
    STATUS mandatory
    DESCRIPTION
        "Contains a value for what packet size the input is using.
         Writes to this field do not take effect until the 
         last parameter, mpsDualDvbAsiInConfApply, is written.
         Additionally, in order for the change to persist through 
         subsequent reboots or power cycles, the change must be saved via
         the mpsSysConfSaveConfig parameter."
    REFERENCE " -- "
::= { mpsDualDvbAsiInConfEntry 4}

mpsDualDvbAsiInConfRefClock OBJECT-TYPE
    SYNTAX INTEGER
       {
        locked (1),
        vcxo1 (2),
        vcxo2 (3),
        vcxo3 (4)
       }
    ACCESS read-write
    STATUS mandatory
    DESCRIPTION
        "Which clock is being used for infobus output to the backplane.
         Writes to this field do not take effect until the 
         last parameter, mpsDualDvbAsiInConfApply, is written.
         Additionally, in order for the change to persist through 
         subsequent reboots or power cycles, the change must be saved via
         the mpsSysConfSaveConfig parameter."
    REFERENCE " -- "
::= { mpsDualDvbAsiInConfEntry 5}

mpsDualDvbAsiInConfClockPuncture OBJECT-TYPE
    SYNTAX INTEGER
       {
        byte188 (1),
        byte204 (2)
       }
    ACCESS read-write
    STATUS mandatory
    DESCRIPTION
        "Contains a value for what clock puncture to use.  This field may
         be overridden by setting override below and setting a specified
         gapped clock setting.
         Writes to this field do not take effect until the 
         last parameter, mpsDualDvbAsiInConfApply, is written.
         Additionally, in order for the change to persist through 
         subsequent reboots or power cycles, the change must be saved via
         the mpsSysConfSaveConfig parameter."
    REFERENCE " -- "
::= { mpsDualDvbAsiInConfEntry 6}

mpsDualDvbAsiInConfSizeOverride OBJECT-TYPE
    SYNTAX INTEGER
       {
        yes (1),
        no  (2)
       }
    ACCESS read-write
    STATUS mandatory
    DESCRIPTION
        "Used to override the packet size setting above with a specified gapped
         clock setting below.  When set to true the MPS will used the specified
         gapped setting below.  Otherwise, the packet size above is used.
         Writes to this field do not take effect until the 
         last parameter, mpsDualDvbAsiInConfApply, is written.
         Additionally, in order for the change to persist through 
         subsequent reboots or power cycles, the change must be saved via
         the mpsSysConfSaveConfig parameter."
    REFERENCE " -- "
::= { mpsDualDvbAsiInConfEntry 7}

mpsDualDvbAsiInConfClockConstant OBJECT-TYPE
    SYNTAX INTEGER
    ACCESS read-write
    STATUS mandatory
    DESCRIPTION
        "The constant used to determine the gapping.  If override is set to false
         above, then this field is defaulted to the appropriate setting as specified
         by the Packet Size.   If override is true above, then this field is used
         to specify the gapping.
         Writes to this field do not take effect until the 
         last parameter, mpsDualDvbAsiInConfApply, is written.
         Additionally, in order for the change to persist through 
         subsequent reboots or power cycles, the change must be saved via
         the mpsSysConfSaveConfig parameter."
    REFERENCE " -- "
::= { mpsDualDvbAsiInConfEntry 8}

mpsDualDvbAsiInConfApply OBJECT-TYPE
    SYNTAX INTEGER
       {  
         applyNotInProgress (1),
         applyNow           (2)
       }
    ACCESS read-write
    STATUS mandatory
    DESCRIPTION  
        "Indicates that the input's configuration parameters have 
         changed and the module is to apply the changes.  Always written
         as the final step in applying changes to the ASI Input."
    REFERENCE " -- "
::= { mpsDualDvbAsiInConfEntry 9}

mpsDualDvbAsiInStatusTable OBJECT-TYPE
    SYNTAX SEQUENCE OF MpsDualDvbAsiInStatusEntry
    ACCESS not-accessible
    STATUS mandatory
    DESCRIPTION  
        "A table of status parameters for DualDvbAsiIn cards"
::= { mpsDualDvbAsiInStatus 1}

mpsDualDvbAsiInStatusEntry OBJECT-TYPE
    SYNTAX MpsDualDvbAsiInStatusEntry
    ACCESS not-accessible
    STATUS mandatory
    DESCRIPTION  
        "A row in the DualDvbAsiIn Status Path table"
    INDEX {mpsDualDvbAsiInStatusSlotNumber, mpsDualDvbAsiInStatusPath }
::= { mpsDualDvbAsiInStatusTable 1}

MpsDualDvbAsiInStatusEntry ::= SEQUENCE
    {
     mpsDualDvbAsiInStatusSlotNumber       INTEGER,
     mpsDualDvbAsiInStatusPath             INTEGER,
     mpsDualDvbAsiInStatusInputActive      INTEGER,
     mpsDualDvbAsiInStatusPllLock          INTEGER,
     mpsDualDvbAsiInStatusMpegProcessing   INTEGER,
     mpsDualDvbAsiInStatusChannelBuffer    INTEGER
    }

mpsDualDvbAsiInStatusSlotNumber OBJECT-TYPE
    SYNTAX INTEGER (1..8) 
    ACCESS not-accessible
    STATUS mandatory
    DESCRIPTION  
        "The slot number of the DualDvbAsiIn card"
    REFERENCE " -- "
::= { mpsDualDvbAsiInStatusEntry 1}

mpsDualDvbAsiInStatusPath OBJECT-TYPE
    SYNTAX INTEGER (1..2)
    ACCESS not-accessible
    STATUS mandatory
    DESCRIPTION  
        "Which path the status parameters apply to."
    REFERENCE " -- "
::= { mpsDualDvbAsiInStatusEntry 2}

mpsDualDvbAsiInStatusInputActive OBJECT-TYPE
    SYNTAX INTEGER
       {
        notActive (1),
        active (2)
       }
    ACCESS read-only
    STATUS mandatory
    DESCRIPTION
        "The Input Transport Stream Activity indicator for the Dual DVB Asi In Card"
    REFERENCE " -- "
::= { mpsDualDvbAsiInStatusEntry 3}

mpsDualDvbAsiInStatusPllLock OBJECT-TYPE
    SYNTAX INTEGER
       {
        notLocked (1),
        locked (2)
       }
    ACCESS read-only
    STATUS mandatory
    DESCRIPTION
        "Indicates whether the path is in Phase Lock Loop"
    REFERENCE " -- "
::= { mpsDualDvbAsiInStatusEntry 4}

mpsDualDvbAsiInStatusMpegProcessing OBJECT-TYPE
    SYNTAX INTEGER
       {
        noError (1),
        error (2)
       }
    ACCESS read-only
    STATUS mandatory
    DESCRIPTION
        "Indicates whether an MPEG Processing error has occurred."
    REFERENCE " -- "
::= { mpsDualDvbAsiInStatusEntry 5}

mpsDualDvbAsiInStatusChannelBuffer OBJECT-TYPE
    SYNTAX INTEGER
       {
        empty    (1),
        active   (2),
        overflow (3)
       }
    ACCESS read-only
    STATUS mandatory
    DESCRIPTION
        "The status for the Channel Buffer."
    REFERENCE " -- "
::= { mpsDualDvbAsiInStatusEntry 6}


mpsSysAlarmZeroSystemTime OBJECT-TYPE
    SYNTAX INTEGER
        { 
         ok(1),
         interdeterminate(2),
         warning(3),
         minor(4),
         major(5),
         critical(6)
        }
    ACCESS read-only
    STATUS mandatory
    DESCRIPTION  
      "Set to 'major' when the MPS System Time value is 0."
    REFERENCE " -- "
::= { mpsSysAlarms 1000}


mpsSysAlarmCommandTableNearFull OBJECT-TYPE
    SYNTAX INTEGER
        { 
         ok(1),
         interdeterminate(2),
         warning(3),
         minor(4),
         major(5),
         critical(6)
        }
    ACCESS read-only
    STATUS mandatory
    DESCRIPTION  
      "Set to 'warning' when the LOAD MPS Command Table is >= 90% full.
       Set to 'major' when the LOAD MPS Command Table >= 98% full.
       The Load MPS Command Table represents all commands stored in the
       MPSs non-volatile memory.  The actual number of command blocks used
       and available can be read from mpsSysStatusCommands. "
    REFERENCE " -- "
::= { mpsSysAlarms 1001}

mpsSysAlarmFatalSIFerror OBJECT-TYPE
    SYNTAX INTEGER
        { 
         ok(1),
         interdeterminate(2),
         warning(3),
         minor(4),
         major(5),
         critical(6)
        }
    ACCESS read-only
    STATUS mandatory
    DESCRIPTION  
       "Set to critical when an error occurs in SIF communications that prevents 
        further use of the SIF. " 
    REFERENCE " -- "
::= { mpsSysAlarms 1002}

mpsSysAlarmConfigurationFailure OBJECT-TYPE
    SYNTAX INTEGER
        { 
         ok(1),
         interdeterminate(2),
         warning(3),
         minor(4),
         major(5),
         critical(6)
        }
    ACCESS read-only
    STATUS mandatory
    DESCRIPTION  
      "Set when an error occurs in the configuration process.  
       Critical indicates that a fatal configuration error occurred that
       prevented the MPS from going to operation mode.
       Major indicates that an error occured that is serious but does not
       prevent the MPS from going to operation mode.
       Warning indicates a configuration warning that does not prevent the
       MPS from going to operational mode."
    REFERENCE " -- "
::= { mpsSysAlarms 1003}

mpsSysAlarmModuleStatusFailure OBJECT-TYPE
    SYNTAX INTEGER
        { 
         ok(1),
         interdeterminate(2),
         warning(3),
         minor(4),
         major(5),
         critical(6)
        }
    ACCESS read-only
    STATUS mandatory
    DESCRIPTION  
      "Set to critical when a module that has been configured fails to reply with status.
       If a module continues not to reply to status requests the module is 
       likely in a hung state due to hardware or software failure."
    REFERENCE " -- "
::= { mpsSysAlarms 1004}

mpsSysAlarmCommandsInError OBJECT-TYPE
    SYNTAX INTEGER
        { 
         ok(1),
         interdeterminate(2),
         warning(3),
         minor(4),
         major(5),
         critical(6)
        }
    ACCESS read-only
    STATUS mandatory
    DESCRIPTION  "Not Implemented"
    REFERENCE " -- "
::= { mpsSysAlarms 1005}

mpsSysAlarmServiceNotAuthorized OBJECT-TYPE
    SYNTAX INTEGER
        { 
         ok(1),
         interdeterminate(2),
         warning(3),
         minor(4),
         major(5),
         critical(6)
        }
    ACCESS read-only
    STATUS mandatory
    DESCRIPTION  
      "Set to 'major' when a Service is not authorized but should be.
       If no services are assigned to ACPs the value is ok.
       If services are assigned to ACPs and they are all authorized the value
       is ok.
       If services are assigned to ACPs and any one service is not authorized
       the value is 'Major' "
    REFERENCE " -- "
::= { mpsSysAlarms 1006}

mpsSysAlarmNoCommandsWaiting OBJECT-TYPE
    SYNTAX INTEGER
        { 
         ok(1),
         interdeterminate(2),
         warning(3),
         minor(4),
         major(5),
         critical(6)
        }
    ACCESS read-only
    STATUS mandatory
    DESCRIPTION  
      "Set to 'warning' when no LOAD MPS commands are waiting to execute"
    REFERENCE " -- "
::= { mpsSysAlarms 1007}

mpsSysAlarmDcVoltageFault OBJECT-TYPE
    SYNTAX INTEGER
        { 
         ok(1),
         interdeterminate(2),
         warning(3),
         minor(4),
         major(5),
         critical(6)
        }
    ACCESS read-only
    STATUS mandatory
    DESCRIPTION  
      "Set to critical when there is a Dc Voltage fault.  This alarm indicates 
       that the unit is not functioning properly."
    REFERENCE " -- "
::= { mpsSysAlarms 1008}

mpsSysAlarmTemperatureFault OBJECT-TYPE
    SYNTAX INTEGER
        { 
         ok(1),
         interdeterminate(2),
         warning(3),
         minor(4),
         major(5),
         critical(6)
        }
    ACCESS read-only
    STATUS mandatory
    DESCRIPTION  
      "Set to critical when the temperature of the unit is out of spec.  The temperature
       sensors can be read seperately in this mib.  Whether fans are on or
       not can also be determined."
    REFERENCE " -- "
::= { mpsSysAlarms 1009}

mpsSysAlarmFanFault OBJECT-TYPE
    SYNTAX INTEGER
        { 
         ok(1),
         interdeterminate(2),
         warning(3),
         minor(4),
         major(5),
         critical(6)
        }
    ACCESS read-only
    STATUS mandatory
    DESCRIPTION  
      "Set to major when a fan is not functioning properly."
    REFERENCE " -- "
::= { mpsSysAlarms 1010}

mpsSysAlarmInputFailure OBJECT-TYPE
    SYNTAX INTEGER
        { 
         ok(1),
         interdeterminate(2),
         warning(3),
         minor(4),
         major(5),
         critical(6)
        }
    ACCESS read-only
    STATUS mandatory
    DESCRIPTION  
      "Set to critical when any input (either physical input to the MPS
       or an input to a functional module from the backplane)
       that should be active (not disabled) has a failure.  Input modules
       can be disabled to prevent this alarm when no input is connected."
    REFERENCE " -- "
::= { mpsSysAlarms 1011}

mpsSysAlarmWatchdogReboot OBJECT-TYPE
    SYNTAX INTEGER
        { 
         ok(1),
         interdeterminate(2),
         warning(3),
         minor(4),
         major(5),
         critical(6)
        }
    ACCESS read-only
    STATUS mandatory
    DESCRIPTION  
      "Set to warning when the last reboot was caused by a watchdog timeout"
    REFERENCE " -- "
::= { mpsSysAlarms 1012}

mpsSysAlarmOutputOverflow OBJECT-TYPE
    SYNTAX INTEGER
        { 
         ok(1),
         interdeterminate(2),
         warning(3),
         minor(4),
         major(5),
         critical(6)
        }
    ACCESS read-only
    STATUS mandatory
    DESCRIPTION  
      "Set to critical when there is an overflow of the buffers
       used to output packets when multiplexing.  This condition indicates
       that there is more bandwidth allocated to multiplexed services
       than there is available.  After one minute of no overflows this
       condition is cleared."
    REFERENCE " -- "
::= { mpsSysAlarms 1013}

mpsSysAlarmWaitingForExtractedData OBJECT-TYPE
    SYNTAX INTEGER
        { 
         ok(1),
         interdeterminate(2),
         warning(3),
         minor(4),
         major(5),
         critical(6)
        }
    ACCESS read-only
    STATUS mandatory
    DESCRIPTION  
      "Set to major when there are active Load MPS Commands that
       are stuck waiting for valid extracted data for more than 
       one minute.  This condition is cleared once all commands
       have received valid extractions."
    REFERENCE " -- "
::= { mpsSysAlarms 1014}

mpsSysAlarmNationalControlFault OBJECT-TYPE
    SYNTAX INTEGER
        { 
         ok(1),
         interdeterminate(2),
         warning(3),
         minor(4),
         major(5),
         critical(6)
        }
    ACCESS read-only
    STATUS mandatory
    DESCRIPTION  
      "Set to major when there is not National Control Stream
       present in an MPS configured to utilize National Control.
       This condition is cleared when there is a National
       Control Stream present."
    REFERENCE " -- "
::= { mpsSysAlarms 1015}

mpsSysAlarmBaseAcpUnitAddressChange OBJECT-TYPE
    SYNTAX INTEGER
        { 
         ok(1),
         interdeterminate(2),
         warning(3),
         minor(4),
         major(5),
         critical(6)
        }
    ACCESS read-only
    STATUS mandatory
    DESCRIPTION  
      "Set to warning when a change in the MPS Base ACP Unit Address
       is detected at boot.  This condition is cleared when the MIB entry
       mpsSysConfBaseAcpUnitAddressChange is set to 'notChanged' via SNMP.
    REFERENCE " -- "
::= { mpsSysAlarms 1016}

mpsSysAlarmMissingSourceTime OBJECT-TYPE
    SYNTAX INTEGER
        { 
         ok(1),
         interdeterminate(2),
         warning(3),
         minor(4),
         major(5),
         critical(6)
        }
    ACCESS read-only
    STATUS mandatory
    DESCRIPTION  
      "Set to minor when the source of MPS system time is missing for more
       than 600 seconds.  The MPS can be configured to use either an input 
       stream, SNTP server, or Load MPS Command source for receiving system time.
       If the configured time source does not send time to the MPS for more than
       600 seconds this alarm will be set.  For transport series configurations
       of the MPS this alarm is not used and is set to OK by default. "
    REFERENCE " -- "
::= { mpsSysAlarms 1017}

mpsSysAlarmInsertionRate OBJECT-TYPE
    SYNTAX INTEGER
        { 
         ok(1),
         interdeterminate(2),
         warning(3),
         minor(4),
         major(5),
         critical(6)
        }
    ACCESS read-only
    STATUS mandatory
    DESCRIPTION  
      "Set to warning when the MPS cannot insert messages at specified insertion
       rates.  This alarm indicates that the MPS insertion capabilities are maxed out.
       The MPS detects this state when every visit to the insertion queue produces a 
       packet for insertion."
    REFERENCE " -- "
::= { mpsSysAlarms 1018}

mpsSysEventLoadMPSerror OBJECT-TYPE
    SYNTAX INTEGER
    ACCESS read-only
    STATUS mandatory
    DESCRIPTION  
        "Count of Load MPS errors. mpsSysStatus provides additional
         command status data."
    REFERENCE " -- "
::= { mpsSysEvent 1100}

mpsSysEventConfigurationError OBJECT-TYPE
    SYNTAX INTEGER
    ACCESS read-only
    STATUS mandatory
    DESCRIPTION  
        "Count of MPS Configuration errors.  mpsSysDebug provides 
         additional error information"
    REFERENCE " -- "
::= { mpsSysEvent 1101}

mpsSysEventModuleStatusError OBJECT-TYPE
    SYNTAX INTEGER
    ACCESS read-only
    STATUS mandatory
    DESCRIPTION  
        "MPS status errors.  mpsSysDebug provides additional error 
         information."
    REFERENCE " -- "
::= { mpsSysEvent 1102}

mpsSysEventUDPinterfaceError OBJECT-TYPE
    SYNTAX INTEGER
    ACCESS read-only
    STATUS mandatory
    DESCRIPTION  
        "Count of UDP Interface errors.  mpsSysDebug provides 
         additional error information."
    REFERENCE " -- "
::= { mpsSysEvent 1103}

mpsSysEventTimeProcessingError OBJECT-TYPE
    SYNTAX INTEGER
    ACCESS read-only
    STATUS mandatory
    DESCRIPTION  
        "Count of time processing errors."
    REFERENCE " -- "
::= { mpsSysEvent 1104}

mpsSysEventSIFinterfaceError OBJECT-TYPE
    SYNTAX INTEGER
    ACCESS read-only
    STATUS mandatory
    DESCRIPTION  
        "Count of SIF interface errors"
    REFERENCE " -- "
::= { mpsSysEvent 1105}

mpsSysEventInputError OBJECT-TYPE
    SYNTAX INTEGER
    ACCESS read-only
    STATUS mandatory
    DESCRIPTION  
        "MPS Input errors.  mpsSysDebug provides additional error 
         information."
    REFERENCE " -- "
::= { mpsSysEvent 1106}

-- *******************************************************************
--  The MPS Traps Group.
--
--  This group contains those objects which are specifically related
--  to trap and alarm processing by the MPS .  Trap IDs start at 1000.
-- *******************************************************************

trapZeroSystemTime TRAP-TYPE
    ENTERPRISE mps
    VARIABLES
    {       
     trapIdentifier,
     trapNetworkElemModelNumber,
     trapNetworkElemSerialNum,
     trapPerceivedSeverity,
     trapNetworkElemOperState,
     trapNetworkElemAlarmStatus,  
     trapNetworkElemAdminState,
     trapNetworkElemAvailStatus,
     trapText,
     trapNETrapLastTrapTimeStamp,
     trapChangedObjectId,
     trapChangedValueInteger,  
     trapAdditionalInfoInteger1, 
     trapAdditionalInfoInteger2, 
     trapAdditionalInfoInteger3     
    }
    DESCRIPTION
        "See corresponding alarm.  Additional Info is not used."
::= 1000

trapCommandTableNearFull TRAP-TYPE
    ENTERPRISE mps
    VARIABLES
    {       
     trapIdentifier,
     trapNetworkElemModelNumber,
     trapNetworkElemSerialNum,
     trapPerceivedSeverity,
     trapNetworkElemOperState,
     trapNetworkElemAlarmStatus,  
     trapNetworkElemAdminState,
     trapNetworkElemAvailStatus,
     trapText,
     trapNETrapLastTrapTimeStamp,
     trapChangedObjectId,
     trapChangedValueInteger,  
     trapAdditionalInfoInteger1, 
     trapAdditionalInfoInteger2, 
     trapAdditionalInfoInteger3     
    }
    DESCRIPTION
        "See corresponding alarm.  Additional Info is not used."
::= 1001

trapFatalSIFerror TRAP-TYPE
    ENTERPRISE mps
    VARIABLES
    {       
     trapIdentifier,
     trapNetworkElemModelNumber,
     trapNetworkElemSerialNum,
     trapPerceivedSeverity,
     trapNetworkElemOperState,
     trapNetworkElemAlarmStatus,  
     trapNetworkElemAdminState,
     trapNetworkElemAvailStatus,
     trapText,
     trapNETrapLastTrapTimeStamp,
     trapChangedObjectId,
     trapChangedValueInteger,  
     trapAdditionalInfoInteger1, 
     trapAdditionalInfoInteger2, 
     trapAdditionalInfoInteger3     
    }
    DESCRIPTION
        "See corresponding alarm.   Additional Info is not used."
::= 1002

trapConfigurationFailure TRAP-TYPE
    ENTERPRISE mps
    VARIABLES
    {       
     trapIdentifier,
     trapNetworkElemModelNumber,
     trapNetworkElemSerialNum,
     trapPerceivedSeverity,
     trapNetworkElemOperState,
     trapNetworkElemAlarmStatus,  
     trapNetworkElemAdminState,
     trapNetworkElemAvailStatus,
     trapText,
     trapNETrapLastTrapTimeStamp,
     trapChangedObjectId,
     trapChangedValueInteger,  
     trapAdditionalInfoInteger1, 
     trapAdditionalInfoInteger2, 
     trapAdditionalInfoInteger3     
    }
    DESCRIPTION
        "See corresponding alarm.  Additional Info 1 carries the 
         error code."
::= 1003

trapModuleFailure TRAP-TYPE
    ENTERPRISE mps
    VARIABLES
    {       
     trapIdentifier,
     trapNetworkElemModelNumber,
     trapNetworkElemSerialNum,
     trapPerceivedSeverity,
     trapNetworkElemOperState,
     trapNetworkElemAlarmStatus,  
     trapNetworkElemAdminState,
     trapNetworkElemAvailStatus,
     trapText,
     trapNETrapLastTrapTimeStamp,
     trapChangedObjectId,
     trapChangedValueInteger,  
     trapAdditionalInfoInteger1, 
     trapAdditionalInfoInteger2, 
     trapAdditionalInfoInteger3     
    }
    DESCRIPTION
        "See corresponding alarm.  Additional Info 1 carries the 
         error code."
::= 1004

trapCommandsInError TRAP-TYPE
    ENTERPRISE mps
    VARIABLES
    {       
     trapIdentifier,
     trapNetworkElemModelNumber,
     trapNetworkElemSerialNum,
     trapPerceivedSeverity,
     trapNetworkElemOperState,
     trapNetworkElemAlarmStatus,  
     trapNetworkElemAdminState,
     trapNetworkElemAvailStatus,
     trapText,
     trapNETrapLastTrapTimeStamp,
     trapChangedObjectId,
     trapChangedValueInteger,  
     trapAdditionalInfoInteger1, 
     trapAdditionalInfoInteger2, 
     trapAdditionalInfoInteger3     
    }
    DESCRIPTION
        "See corresponding alarm."
::= 1005

trapServiceNotAuthorized TRAP-TYPE
    ENTERPRISE mps
    VARIABLES
    {       
     trapIdentifier,
     trapNetworkElemModelNumber,
     trapNetworkElemSerialNum,
     trapPerceivedSeverity,
     trapNetworkElemOperState,
     trapNetworkElemAlarmStatus,  
     trapNetworkElemAdminState,
     trapNetworkElemAvailStatus,
     trapText,
     trapNETrapLastTrapTimeStamp,
     trapChangedObjectId,
     trapChangedValueInteger,  
     trapAdditionalInfoInteger1, 
     trapAdditionalInfoInteger2, 
     trapAdditionalInfoInteger3     
    }
    DESCRIPTION
        "See corresponding alarm.  Additional Info is not used."
::= 1006

trapNoCommandsWaiting TRAP-TYPE
    ENTERPRISE mps
    VARIABLES
    {       
     trapIdentifier,
     trapNetworkElemModelNumber,
     trapNetworkElemSerialNum,
     trapPerceivedSeverity,
     trapNetworkElemOperState,
     trapNetworkElemAlarmStatus,  
     trapNetworkElemAdminState,
     trapNetworkElemAvailStatus,
     trapText,
     trapNETrapLastTrapTimeStamp,
     trapChangedObjectId,
     trapChangedValueInteger,  
     trapAdditionalInfoInteger1, 
     trapAdditionalInfoInteger2, 
     trapAdditionalInfoInteger3     
    }
    DESCRIPTION
        "See corresponding alarm.  Additional Info is not used."
::= 1007

trapDcVoltageFault TRAP-TYPE
    ENTERPRISE mps
    VARIABLES
    {       
     trapIdentifier,
     trapNetworkElemModelNumber,
     trapNetworkElemSerialNum,
     trapPerceivedSeverity,
     trapNetworkElemOperState,
     trapNetworkElemAlarmStatus,  
     trapNetworkElemAdminState,
     trapNetworkElemAvailStatus,
     trapText,
     trapNETrapLastTrapTimeStamp,
     trapChangedObjectId,
     trapChangedValueInteger,  
     trapAdditionalInfoInteger1, 
     trapAdditionalInfoInteger2, 
     trapAdditionalInfoInteger3     
    }
    DESCRIPTION
        "See corresponding alarm.  Additional Info is not used."
::= 1008

trapTemperatureFault TRAP-TYPE
    ENTERPRISE mps
    VARIABLES
    {       
     trapIdentifier,
     trapNetworkElemModelNumber,
     trapNetworkElemSerialNum,
     trapPerceivedSeverity,
     trapNetworkElemOperState,
     trapNetworkElemAlarmStatus,  
     trapNetworkElemAdminState,
     trapNetworkElemAvailStatus,
     trapText,
     trapNETrapLastTrapTimeStamp,
     trapChangedObjectId,
     trapChangedValueInteger,  
     trapAdditionalInfoInteger1, 
     trapAdditionalInfoInteger2, 
     trapAdditionalInfoInteger3     
    }
    DESCRIPTION
        "See corresponding alarm.  Additional Info is not used."
::= 1009

trapFanFault TRAP-TYPE
    ENTERPRISE mps
    VARIABLES
    {       
     trapIdentifier,
     trapNetworkElemModelNumber,
     trapNetworkElemSerialNum,
     trapPerceivedSeverity,
     trapNetworkElemOperState,
     trapNetworkElemAlarmStatus,  
     trapNetworkElemAdminState,
     trapNetworkElemAvailStatus,
     trapText,
     trapNETrapLastTrapTimeStamp,
     trapChangedObjectId,
     trapChangedValueInteger,  
     trapAdditionalInfoInteger1, 
     trapAdditionalInfoInteger2, 
     trapAdditionalInfoInteger3     
    }
    DESCRIPTION
        "See corresponding alarm.  Additional Info is not used."
::= 1010

trapInputFailure TRAP-TYPE
    ENTERPRISE mps
    VARIABLES
    {       
     trapIdentifier,
     trapNetworkElemModelNumber,
     trapNetworkElemSerialNum,
     trapPerceivedSeverity,
     trapNetworkElemOperState,
     trapNetworkElemAlarmStatus,  
     trapNetworkElemAdminState,
     trapNetworkElemAvailStatus,
     trapText,
     trapNETrapLastTrapTimeStamp,
     trapChangedObjectId,
     trapChangedValueInteger,  
     trapAdditionalInfoInteger1, 
     trapAdditionalInfoInteger2, 
     trapAdditionalInfoInteger3     
    }
    DESCRIPTION
        "See corresponding alarm. Additional Info carries the
         error code."
::= 1011

trapWatchdogReboot TRAP-TYPE
    ENTERPRISE mps
    VARIABLES
    {       
     trapIdentifier,
     trapNetworkElemModelNumber,
     trapNetworkElemSerialNum,
     trapPerceivedSeverity,
     trapNetworkElemOperState,
     trapNetworkElemAlarmStatus,  
     trapNetworkElemAdminState,
     trapNetworkElemAvailStatus,
     trapText,
     trapNETrapLastTrapTimeStamp,
     trapChangedObjectId,
     trapChangedValueInteger,  
     trapAdditionalInfoInteger1, 
     trapAdditionalInfoInteger2, 
     trapAdditionalInfoInteger3     
    }
    DESCRIPTION
        "See corresponding alarm.  Additional Info is not used."
::= 1012

trapOutputOverflow TRAP-TYPE
    ENTERPRISE mps
    VARIABLES
    {       
     trapIdentifier,
     trapNetworkElemModelNumber,
     trapNetworkElemSerialNum,
     trapPerceivedSeverity,
     trapNetworkElemOperState,
     trapNetworkElemAlarmStatus,  
     trapNetworkElemAdminState,
     trapNetworkElemAvailStatus,
     trapText,
     trapNETrapLastTrapTimeStamp,
     trapChangedObjectId,
     trapChangedValueInteger,  
     trapAdditionalInfoInteger1, 
     trapAdditionalInfoInteger2, 
     trapAdditionalInfoInteger3     
    }
    DESCRIPTION
        "See corresponding alarm.   Additional Info is not used."
::= 1013

trapWaitingForExtractedData TRAP-TYPE
    ENTERPRISE mps
    VARIABLES
    {       
     trapIdentifier,
     trapNetworkElemModelNumber,
     trapNetworkElemSerialNum,
     trapPerceivedSeverity,
     trapNetworkElemOperState,
     trapNetworkElemAlarmStatus,  
     trapNetworkElemAdminState,
     trapNetworkElemAvailStatus,
     trapText,
     trapNETrapLastTrapTimeStamp,
     trapChangedObjectId,
     trapChangedValueInteger,  
     trapAdditionalInfoInteger1, 
     trapAdditionalInfoInteger2, 
     trapAdditionalInfoInteger3     
    }
    DESCRIPTION
        "See corresponding alarm.  Additional Info is not used."
::= 1014

trapNationalControlFault TRAP-TYPE
    ENTERPRISE mps
    VARIABLES
    {       
     trapIdentifier,
     trapNetworkElemModelNumber,
     trapNetworkElemSerialNum,
     trapPerceivedSeverity,
     trapNetworkElemOperState,
     trapNetworkElemAlarmStatus,  
     trapNetworkElemAdminState,
     trapNetworkElemAvailStatus,
     trapText,
     trapNETrapLastTrapTimeStamp,
     trapChangedObjectId,
     trapChangedValueInteger,  
     trapAdditionalInfoInteger1, 
     trapAdditionalInfoInteger2, 
     trapAdditionalInfoInteger3     
    }
    DESCRIPTION
        "See corresponding alarm.  Additional Info is not used."
::= 1015

trapBaseAcpUnitAddressChange TRAP-TYPE
    ENTERPRISE mps
    VARIABLES
    {       
     trapIdentifier,
     trapNetworkElemModelNumber,
     trapNetworkElemSerialNum,
     trapPerceivedSeverity,
     trapNetworkElemOperState,
     trapNetworkElemAlarmStatus,  
     trapNetworkElemAdminState,
     trapNetworkElemAvailStatus,
     trapText,
     trapNETrapLastTrapTimeStamp,
     trapChangedObjectId,
     trapChangedValueInteger,  
     trapAdditionalInfoInteger1, 
     trapAdditionalInfoInteger2, 
     trapAdditionalInfoInteger3     
    }
    DESCRIPTION
        "See corresponding alarm.  Additional Info is not used."
::= 1016

trapMissingSourceTime TRAP-TYPE
    ENTERPRISE mps
    VARIABLES
    {       
     trapIdentifier,
     trapNetworkElemModelNumber,
     trapNetworkElemSerialNum,
     trapPerceivedSeverity,
     trapNetworkElemOperState,
     trapNetworkElemAlarmStatus,  
     trapNetworkElemAdminState,
     trapNetworkElemAvailStatus,
     trapText,
     trapNETrapLastTrapTimeStamp,
     trapChangedObjectId,
     trapChangedValueInteger,  
     trapAdditionalInfoInteger1, 
     trapAdditionalInfoInteger2, 
     trapAdditionalInfoInteger3     
    }
    DESCRIPTION
        "See corresponding alarm.  Additional Info is not used."
::= 1017

trapInsertionRate TRAP-TYPE
    ENTERPRISE mps
    VARIABLES
    {       
     trapIdentifier,
     trapNetworkElemModelNumber,
     trapNetworkElemSerialNum,
     trapPerceivedSeverity,
     trapNetworkElemOperState,
     trapNetworkElemAlarmStatus,  
     trapNetworkElemAdminState,
     trapNetworkElemAvailStatus,
     trapText,
     trapNETrapLastTrapTimeStamp,
     trapChangedObjectId,
     trapChangedValueInteger,  
     trapAdditionalInfoInteger1, 
     trapAdditionalInfoInteger2, 
     trapAdditionalInfoInteger3     
    }
    DESCRIPTION
        "See corresponding alarm.  Additional Info is not used."
::= 1018

trapLoadMPSerror TRAP-TYPE
    ENTERPRISE mps
    VARIABLES
    {       
     trapIdentifier,
     trapNetworkElemModelNumber,
     trapNetworkElemSerialNum,
     trapPerceivedSeverity,
     trapNetworkElemOperState,
     trapNetworkElemAlarmStatus,  
     trapNetworkElemAdminState,
     trapNetworkElemAvailStatus,
     trapText,
     trapNETrapLastTrapTimeStamp,
     trapChangedObjectId,
     trapChangedValueInteger,  
     trapAdditionalInfoInteger1, 
     trapAdditionalInfoInteger2, 
     trapAdditionalInfoInteger3     
    }
    DESCRIPTION
        "See corresponding alarm.  Additional Info 1 carries the error
         code."
::= 1100

trapConfigurationError TRAP-TYPE
    ENTERPRISE mps
    VARIABLES
    {       
     trapIdentifier,
     trapNetworkElemModelNumber,
     trapNetworkElemSerialNum,
     trapPerceivedSeverity,
     trapNetworkElemOperState,
     trapNetworkElemAlarmStatus,  
     trapNetworkElemAdminState,
     trapNetworkElemAvailStatus,
     trapText,
     trapNETrapLastTrapTimeStamp,
     trapChangedObjectId,
     trapChangedValueInteger,  
     trapAdditionalInfoInteger1, 
     trapAdditionalInfoInteger2, 
     trapAdditionalInfoInteger3     
    }
    DESCRIPTION
        "See corresponding alarm.  Additional Info 1 carries the error
         code."
::= 1101

trapModuleStatusError TRAP-TYPE
    ENTERPRISE mps
    VARIABLES
    {       
     trapIdentifier,
     trapNetworkElemModelNumber,
     trapNetworkElemSerialNum,
     trapPerceivedSeverity,
     trapNetworkElemOperState,
     trapNetworkElemAlarmStatus,  
     trapNetworkElemAdminState,
     trapNetworkElemAvailStatus,
     trapText,
     trapNETrapLastTrapTimeStamp,
     trapChangedObjectId,
     trapChangedValueInteger,  
     trapAdditionalInfoInteger1, 
     trapAdditionalInfoInteger2, 
     trapAdditionalInfoInteger3     
    }
    DESCRIPTION
        "See corresponding alarm.  Additional Info 1 carries
         the error code."
::= 1102

trapUDPinterfaceError TRAP-TYPE
    ENTERPRISE mps
    VARIABLES
    {       
     trapIdentifier,
     trapNetworkElemModelNumber,
     trapNetworkElemSerialNum,
     trapPerceivedSeverity,
     trapNetworkElemOperState,
     trapNetworkElemAlarmStatus,  
     trapNetworkElemAdminState,
     trapNetworkElemAvailStatus,
     trapText,
     trapNETrapLastTrapTimeStamp,
     trapChangedObjectId,
     trapChangedValueInteger,  
     trapAdditionalInfoInteger1, 
     trapAdditionalInfoInteger2, 
     trapAdditionalInfoInteger3     
    }
    DESCRIPTION
        "See corresponding alarm."
::= 1103

trapTimeProcessingError TRAP-TYPE
    ENTERPRISE mps
    VARIABLES
    {       
     trapIdentifier,
     trapNetworkElemModelNumber,
     trapNetworkElemSerialNum,
     trapPerceivedSeverity,
     trapNetworkElemOperState,
     trapNetworkElemAlarmStatus,  
     trapNetworkElemAdminState,
     trapNetworkElemAvailStatus,
     trapText,
     trapNETrapLastTrapTimeStamp,
     trapChangedObjectId,
     trapChangedValueInteger,  
     trapAdditionalInfoInteger1, 
     trapAdditionalInfoInteger2, 
     trapAdditionalInfoInteger3     
    }
    DESCRIPTION
        "See corresponding alarm."
::= 1104

trapSIFinterfaceError TRAP-TYPE
    ENTERPRISE mps
    VARIABLES
    {       
     trapIdentifier,
     trapNetworkElemModelNumber,
     trapNetworkElemSerialNum,
     trapPerceivedSeverity,
     trapNetworkElemOperState,
     trapNetworkElemAlarmStatus,  
     trapNetworkElemAdminState,
     trapNetworkElemAvailStatus,
     trapText,
     trapNETrapLastTrapTimeStamp,
     trapChangedObjectId,
     trapChangedValueInteger,  
     trapAdditionalInfoInteger1, 
     trapAdditionalInfoInteger2, 
     trapAdditionalInfoInteger3     
    }
    DESCRIPTION
        "See corresponding alarm.  Additional Info indicates
         the failure as enumerated below:
         1 - ILL Set
         2 - XERR Set
         3 - ERROR Set"
::= 1105

trapInputError TRAP-TYPE
    ENTERPRISE mps
    VARIABLES
    {       
     trapIdentifier,
     trapNetworkElemModelNumber,
     trapNetworkElemSerialNum,
     trapPerceivedSeverity,
     trapNetworkElemOperState,
     trapNetworkElemAlarmStatus,  
     trapNetworkElemAdminState,
     trapNetworkElemAvailStatus,
     trapText,
     trapNETrapLastTrapTimeStamp,
     trapChangedObjectId,
     trapChangedValueInteger,  
     trapAdditionalInfoInteger1, 
     trapAdditionalInfoInteger2, 
     trapAdditionalInfoInteger3     
    }
    DESCRIPTION
        "See corresponding alarm. Additional Info carries the
         error code."
::= 1106


-- *******************************************************************
--  The NLSBBN Traps Group.
--
--  This group contains those objects which are commonly defined but
--  the ENTERPRISE is specific to the RPD .  Trap IDs start at 1.
-- *******************************************************************


trapNewNEFound TRAP-TYPE
    ENTERPRISE mps
    VARIABLES
    {       
    trapIdentifier,
    trapNetworkElemModelNumber,
    trapNetworkElemSerialNum,
    trapPerceivedSeverity,
    trapNetworkElemOperState,
    trapNetworkElemAlarmStatus,  
    trapNetworkElemAdminState,
    trapNetworkElemAvailStatus,
    trapText,
    trapNETrapLastTrapTimeStamp,
    trapChangedValueOID
    }
    DESCRIPTION
     "This trap is isssued if a Proxy Agent Detected A New NE.
      trapPerceivedSeverity - 'indeterminate'
      trapChangedValueOID - This  variable identifies the new
      Network Element.  This trap is not issues by non-proxy
      agents."
::= 1


trapNewNELost TRAP-TYPE
    ENTERPRISE mps
    VARIABLES
    {       
    trapIdentifier,
    trapNetworkElemModelNumber,
    trapNetworkElemSerialNum,
    trapPerceivedSeverity,
    trapNetworkElemOperState,
    trapNetworkElemAlarmStatus,  
    trapNetworkElemAdminState,
    trapNetworkElemAvailStatus,
    trapText,
    trapNETrapLastTrapTimeStamp,
    trapChangedValueOID
    }
    DESCRIPTION
     "This trap is isssued if a Proxy Agent lost communication with
      NE.  trapPerceivedSeverity - 'critical'.
      trapChangedValueOID - This  variable identifies the new
      Network Element. This trap is not issues by non-proxy agents."
::= 2


trapConfigurationChangeInteger TRAP-TYPE
    ENTERPRISE mps
    VARIABLES
    {       
    trapIdentifier,
    trapNetworkElemModelNumber,
    trapNetworkElemSerialNum,
    trapPerceivedSeverity,
    trapNetworkElemOperState,
    trapNetworkElemAlarmStatus,  
    trapNetworkElemAdminState,
    trapNetworkElemAvailStatus,
    trapText,
    trapNETrapLastTrapTimeStamp,
    trapChangedObjectId,
    trapChangedValueInteger
    }
    DESCRIPTION
     "This trap is issued if configuration of a single variable
      with integer type was changed (via ANY interface).  
      TrapChangedValueInteger variable may contain current reading
      of that variable.
      trapPerceivedSeverity - 'indeterminate'"
::= 3


trapConfigurationChangeDisplayString TRAP-TYPE
    ENTERPRISE mps
    VARIABLES
    {       
    trapIdentifier,
    trapNetworkElemModelNumber,
    trapNetworkElemSerialNum,
    trapPerceivedSeverity,
    trapNetworkElemOperState,
    trapNetworkElemAlarmStatus,  
    trapNetworkElemAdminState,
    trapNetworkElemAvailStatus,
    trapText,
    trapNETrapLastTrapTimeStamp,
    trapChangedObjectId,
    trapChangedValueDisplayString
    }
    DESCRIPTION
     "This trap is issued if configuration of a single variable
      with DispalayString type was changed (via ANY interface).  
      TrapChangedValueDisplayString variable may contain current
      reading of that variable.
      trapPerceivedSeverity - 'indeterminate'"
::= 4


trapConfigurationChangeOID TRAP-TYPE
    ENTERPRISE mps
    VARIABLES
    {       
    trapIdentifier,
    trapNetworkElemModelNumber,
    trapNetworkElemSerialNum,
    trapPerceivedSeverity,
    trapNetworkElemOperState,
    trapNetworkElemAlarmStatus,  
    trapNetworkElemAdminState,
    trapNetworkElemAvailStatus,
    trapText,
    trapNETrapLastTrapTimeStamp,
    trapChangedObjectId,
    trapChangedValueOID
    }
    DESCRIPTION
     "This trap is issued if configuration of a single variable
      with OID type was changed (via ANY interface).  
      TrapChangedValueOID variable may contain current reading
      of that variable.
      trapPerceivedSeverity - 'indeterminate'"
::= 5

trapConfigurationChangeIpAddress TRAP-TYPE
    ENTERPRISE mps
    VARIABLES
    {       
    trapIdentifier,
    trapNetworkElemModelNumber,
    trapNetworkElemSerialNum,
    trapPerceivedSeverity,
    trapNetworkElemOperState,
    trapNetworkElemAlarmStatus,  
    trapNetworkElemAdminState,
    trapNetworkElemAvailStatus,
    trapText,
    trapNETrapLastTrapTimeStamp,
    trapChangedObjectId,
    trapChangedValueIpAddress
    }
    DESCRIPTION
     "This trap is issued if configuration of a single variable
      with IpAddress type was changed (via ANY interface).  
      TrapChangedValueIpAddress variable may contain current reading
      of that variable.
      trapPerceivedSeverity - 'indeterminate'"
::= 6


trapToBeSendQueueOverflow TRAP-TYPE
    ENTERPRISE mps
    VARIABLES
    {       
    trapIdentifier,
    trapNetworkElemModelNumber,
    trapNetworkElemSerialNum,
    trapPerceivedSeverity,
    trapNetworkElemOperState,
    trapNetworkElemAlarmStatus,  
    trapNetworkElemAdminState,
    trapNetworkElemAvailStatus,
    trapText,
    trapNETrapLastTrapTimeStamp
    }
    DESCRIPTION
     "This trap is issued if SNMP agent's TrapToBeSendQueue is full.
      trapPerceivedSeverity - 'major'
      trapNetworkElemModelNumber - Model # of the Agent
      trapNetworkElemSerialNum - Serial # of the Agent
      trapNetworkElemOperState - from Ident MIB
      trapNetworkElemAlarmStatus - from Ident MIB   
      trapNetworkElemAdminState - from Ident MIB
      trapNetworkElemAvailStatus - from Ident MIB"
::= 7

-- *******************************************************************
--  The DNS Traps Group.
--
--  This group contains those objects which are commonly defined but
--  ENTERPRISE is sepecific to RPD. Traps ID starts from 20. 
-- *******************************************************************

trapConditionNotInList TRAP-TYPE
           ENTERPRISE mps
           VARIABLES
       {       
    trapIdentifier,
    trapNetworkElemModelNumber,
    trapNetworkElemSerialNum,
    trapPerceivedSeverity,
    trapNetworkElemOperState,
    trapNetworkElemAlarmStatus,  
    trapNetworkElemAdminState,
    trapNetworkElemAvailStatus,
    trapText,
    trapNETrapLastTrapTimeStamp,
    trapChangedObjectId,
    trapChangedValueInteger,  
    trapAdditionalInfoInteger1, 
    trapAdditionalInfoInteger2, 
    trapAdditionalInfoInteger3     
    }
    DESCRIPTION
      "This trap is issued if a condition is being cleared and
       it is not in the condition list.
       trapAdditionalInfoInteger1 : Task and Function ID (task
                        and function generates the
                        error condition)
       trapAdditionalInfoInteger2 : Condition number
       trapAdditionalInfoInteger3 : Condition severity" 
::= 20

trapConditionAlreadyInList TRAP-TYPE
    ENTERPRISE mps
    VARIABLES
    {       
    trapIdentifier,
    trapNetworkElemModelNumber,
    trapNetworkElemSerialNum,
    trapPerceivedSeverity,
    trapNetworkElemOperState,
    trapNetworkElemAlarmStatus,  
    trapNetworkElemAdminState,
    trapNetworkElemAvailStatus,
    trapText,
    trapNETrapLastTrapTimeStamp,
    trapChangedObjectId,
    trapChangedValueInteger,  
    trapAdditionalInfoInteger1, 
    trapAdditionalInfoInteger2, 
    trapAdditionalInfoInteger3     
    }
    DESCRIPTION
      "This trap is issued if a condition is being set and
       it is already in the condition list.
       trapAdditionalInfoInteger1 : Task and Function ID (task
                        and function generates the
                        error condition)
       trapAdditionalInfoInteger2 : Condition number
       trapAdditionalInfoInteger3 : Condition severity"
::= 21

trapConditionListFull TRAP-TYPE
    ENTERPRISE mps
    VARIABLES
    {       
    trapIdentifier,
    trapNetworkElemModelNumber,
    trapNetworkElemSerialNum,
    trapPerceivedSeverity,
    trapNetworkElemOperState,
    trapNetworkElemAlarmStatus,  
    trapNetworkElemAdminState,
    trapNetworkElemAvailStatus,
    trapText,
    trapNETrapLastTrapTimeStamp,
    trapChangedObjectId,
    trapChangedValueInteger,  
    trapAdditionalInfoInteger1, 
    trapAdditionalInfoInteger2, 
    trapAdditionalInfoInteger3     
    }
    DESCRIPTION
      "This trap is issued if a condition is being set and
       the condition list is full.
       trapAdditionalInfoInteger1 : Task and Function ID (task
                        and function generates the
                        error condition)
       trapAdditionalInfoInteger2 : Condition number
       trapAdditionalInfoInteger3 : Condition servirty" 
::= 22

trapInvalidCaseInSwitch TRAP-TYPE
    ENTERPRISE mps
    VARIABLES
    {       
    trapIdentifier,
    trapNetworkElemModelNumber,
    trapNetworkElemSerialNum,
    trapPerceivedSeverity,
    trapNetworkElemOperState,
    trapNetworkElemAlarmStatus,  
    trapNetworkElemAdminState,
    trapNetworkElemAvailStatus,
    trapText,
    trapNETrapLastTrapTimeStamp,
    trapChangedObjectId,
    trapChangedValueInteger,  
    trapAdditionalInfoInteger1, 
    trapAdditionalInfoInteger2, 
    trapAdditionalInfoInteger3     
    }
    DESCRIPTION
      "This trap is issued when in a switch statement the
       default case is reached.  The trapAdditionalInfoInteger1
       will contain the task and Function ID.  The
       trapAdditionalInfoInteger2 will contain value of the switch.
       The trapAdditionalInfoInteger3 is not used."
::= 23

trapCannotCreateSemaphore TRAP-TYPE
    ENTERPRISE mps
    VARIABLES
    {       
    trapIdentifier,
    trapNetworkElemModelNumber,
    trapNetworkElemSerialNum,
    trapPerceivedSeverity,
    trapNetworkElemOperState,
    trapNetworkElemAlarmStatus,  
    trapNetworkElemAdminState,
    trapNetworkElemAvailStatus,
    trapText,
    trapNETrapLastTrapTimeStamp,
    trapChangedObjectId,
    trapChangedValueInteger,  
    trapAdditionalInfoInteger1, 
    trapAdditionalInfoInteger2, 
    trapAdditionalInfoInteger3     
    }
    DESCRIPTION
      "This trap is issued when a semaphore cannot
       be created. The trapAdditionalInfoInteger1 will contain the
       task and Function ID, the trapAdditionalInfoInteger2 and
       trapAdditionalInfoInteger3 will not be used."
::= 24

trapCannotOpenSocket TRAP-TYPE
    ENTERPRISE mps
    VARIABLES
    {       
    trapIdentifier,
    trapNetworkElemModelNumber,
    trapNetworkElemSerialNum,
    trapPerceivedSeverity,
    trapNetworkElemOperState,
    trapNetworkElemAlarmStatus,  
    trapNetworkElemAdminState,
    trapNetworkElemAvailStatus,
    trapText,
    trapNETrapLastTrapTimeStamp,
    trapChangedObjectId,
    trapChangedValueInteger,  
    trapAdditionalInfoInteger1, 
    trapAdditionalInfoInteger2, 
    trapAdditionalInfoInteger3     
    }
    DESCRIPTION
      "This trap is issued when a socket cannot
       be opened. The trapAdditionalInfoInteger1 will contain the
       task and Function ID. The trapAdditionalInfoInteger2 will
       contain the errno returned by the call to socket(). The
       trapAdditionalInfoInteger3 is not used."
::= 25

trapUnknownMessageReceived TRAP-TYPE
    ENTERPRISE mps
    VARIABLES
    {       
    trapIdentifier,
    trapNetworkElemModelNumber,
    trapNetworkElemSerialNum,
    trapPerceivedSeverity,
    trapNetworkElemOperState,
    trapNetworkElemAlarmStatus,  
    trapNetworkElemAdminState,
    trapNetworkElemAvailStatus,
    trapText,
    trapNETrapLastTrapTimeStamp,
    trapChangedObjectId,
    trapChangedValueInteger,  
    trapAdditionalInfoInteger1, 
    trapAdditionalInfoInteger2, 
    trapAdditionalInfoInteger3     
    }
    DESCRIPTION
      "This trap is issued when an unknown message
       is received.  The trapAdditionalInfoInteger1 will contain the
       task and Function ID. The trapAdditionalInfoInteger2 will 
       contain the message ID and the trapAdditionalInfoInteger3 is
       not used."
::= 26

trapInvalidMessageReceived TRAP-TYPE
    ENTERPRISE mps
    VARIABLES
    {       
    trapIdentifier,
    trapNetworkElemModelNumber,
    trapNetworkElemSerialNum,
    trapPerceivedSeverity,
    trapNetworkElemOperState,
    trapNetworkElemAlarmStatus,  
    trapNetworkElemAdminState,
    trapNetworkElemAvailStatus,
    trapText,
    trapNETrapLastTrapTimeStamp,
    trapChangedObjectId,
    trapChangedValueInteger,  
    trapAdditionalInfoInteger1, 
    trapAdditionalInfoInteger2, 
    trapAdditionalInfoInteger3     
    }
    DESCRIPTION
      "This trap is issued when an invalid message
       is received.  The trapAdditionalInfoInteger1 will contain the
       task and Function ID. The trapAdditionalInfoInteger2 will
       contain the message ID and the trapAdditionalInfoInteger3 is
       not used."
::= 27


END
