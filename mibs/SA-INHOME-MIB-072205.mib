--
-- SA-INHOME-MIB.mib
-- MIB generated by MG-SOFT Visual MIB Builder Version 4.0 Build 349
-- Friday, July 22, 2005 at 15:48:03
--

-- Revision 1 : Initial Release
-- Date: Friday, July 22, 2005 at 15:08:30
-- Comment:
-- 
	SA-INHOME-MIB DEFINITIONS ::= BEGIN
 
		IMPORTS
			saInHomeMib			
				FROM SA-DBDSGEN-MIB			
			saModules			
				FROM SCIATL-COMMON-MIB			
			TimeTicks, IpAddress, Integer32, Unsigned32, OBJECT-TYPE, 
			MODULE-IDENTITY, OBJECT-IDENTITY			
				FROM SNMPv2-SMI;
	
	
-- Scientific-Atlanta Proprietary Information
-- 
-- Copyright 2005 Scientific-Atlanta, Inc.
-- 
-- All rights reserved.
-- 
--  
-- 
-- Unauthorized copying and distribution are prohibited.  
-- 
-- No part of this MIB may be reprinted, reproduced or utilized
-- 
-- in any form or by any electronic, mechanical, or other means, now known or
-- 
-- hereafter invented, including photocopying and recording, or using any
-- 
-- information storage and retrieval system, without permission in writing
-- 
-- from Scientific-Atlanta, Inc.
-- 
		-- 1.3.6.1.4.1.1429.7.1.13
		saInHomeMibModule MODULE-IDENTITY 
			LAST-UPDATED "200507221508Z"		-- July 22, 2005 at 15:08 GMT
			ORGANIZATION 
				"Scientific-Atlanta"
			CONTACT-INFO 
				"DBDS Software Engineering & Architecture
				Scientific-Atlanta
				5030 Sugarloaf Parkway
				Lawrenceville, GA 30044
				"
			DESCRIPTION 
				"SA MIB Module for In-Home Networking."
			REVISION "200507221542Z"		-- July 22, 2005 at 15:42 GMT
			DESCRIPTION 
				"Added ihsMrSessTrickTable subtree."
			::= { saModules 13 }

		
	
	
--
-- Node definitions
--
	
		-- 1.3.6.1.4.1.1429.9.1.7.1
		saInHomeConf OBJECT-IDENTITY
			STATUS current
			DESCRIPTION 
				"Conformance"
			::= { saInHomeMib 1 }

		
		-- 1.3.6.1.4.1.1429.9.1.7.1.1
		saInHomeGroups OBJECT-IDENTITY
			STATUS current
			DESCRIPTION 
				"Object Groups of the SA-INHOME-MIB"
			::= { saInHomeConf 1 }

		
		-- 1.3.6.1.4.1.1429.9.1.7.1.2
		saInHomeCompls OBJECT-IDENTITY
			STATUS current
			DESCRIPTION 
				"Compliances of the SA-INHOME-MIB"
			::= { saInHomeConf 2 }

		
		-- 1.3.6.1.4.1.1429.9.1.7.2
		saInHomeObjs OBJECT-IDENTITY
			STATUS current
			DESCRIPTION 
				"The MIB Objects defined for the SA-INHOME-MIB module."
			::= { saInHomeMib 2 }

		
		-- 1.3.6.1.4.1.1429.9.1.7.2.1
		saIhn OBJECT-IDENTITY
			STATUS current
			DESCRIPTION 
				"In-Home Network"
			::= { saInHomeObjs 1 }

		
		-- 1.3.6.1.4.1.1429.9.1.7.2.1.1
		saIhnConfig OBJECT-IDENTITY
			STATUS current
			DESCRIPTION 
				"In-Home Network Configuration"
			::= { saIhn 1 }

		
		-- 1.3.6.1.4.1.1429.9.1.7.2.1.1.1
		saIhnConfigQamParam OBJECT-IDENTITY
			STATUS current
			DESCRIPTION 
				"IHN QAM Configuration Parameters"
			::= { saIhnConfig 1 }

		
		-- 1.3.6.1.4.1.1429.9.1.7.2.1.1.1.1
		saIhnConfigQamParamCount OBJECT-TYPE
			SYNTAX Integer32
			MAX-ACCESS read-only
			STATUS current
			DESCRIPTION
				"The number of QAM Parameters. The QAM Parameters contain information regarding what frequency to tune to, the symbol rate and the modulation, to talk with the In-Home Network. These are read off a BFS file."
			::= { saIhnConfigQamParam 1 }

		
		-- 1.3.6.1.4.1.1429.9.1.7.2.1.1.1.2
		saIhnConfigQamParamTable OBJECT-TYPE
			SYNTAX SEQUENCE OF SaIhnConfigQamParamEntry
			MAX-ACCESS not-accessible
			STATUS current
			DESCRIPTION
				"The QAM Parameter table containing the values provided by the
				IHN Configuration file."
			::= { saIhnConfigQamParam 2 }

		
		-- 1.3.6.1.4.1.1429.9.1.7.2.1.1.1.2.1
		saIhnConfigQamParamEntry OBJECT-TYPE
			SYNTAX SaIhnConfigQamParamEntry
			MAX-ACCESS not-accessible
			STATUS current
			DESCRIPTION
				"The QAM Parameter table entry."
			INDEX { saIhnConfigQamParamIndex }
			::= { saIhnConfigQamParamTable 1 }

		
		SaIhnConfigQamParamEntry ::=
			SEQUENCE { 
				saIhnConfigQamParamIndex
					Unsigned32,
				saIhnConfigQamParamFrequency
					Unsigned32,
				saIhnConfigQamParamSymbolRate
					Unsigned32,
				saIhnConfigQamParamMod
					INTEGER
			 }

		-- 1.3.6.1.4.1.1429.9.1.7.2.1.1.1.2.1.1
		saIhnConfigQamParamIndex OBJECT-TYPE
			SYNTAX Unsigned32
			MAX-ACCESS read-only
			STATUS current
			DESCRIPTION
				"The QAM Parameter Table Index."
			::= { saIhnConfigQamParamEntry 1 }

		
		-- 1.3.6.1.4.1.1429.9.1.7.2.1.1.1.2.1.2
		saIhnConfigQamParamFrequency OBJECT-TYPE
			SYNTAX Unsigned32
			UNITS "Hz"
			MAX-ACCESS read-only
			STATUS current
			DESCRIPTION
				"The QAM Frequency in Hz. This is the frequency, the client station tunes to, 
				to receive data from the server station."
			::= { saIhnConfigQamParamEntry 2 }

		
		-- 1.3.6.1.4.1.1429.9.1.7.2.1.1.1.2.1.3
		saIhnConfigQamParamSymbolRate OBJECT-TYPE
			SYNTAX Unsigned32
			UNITS "Hz"
			MAX-ACCESS read-only
			STATUS current
			DESCRIPTION
				"The QAM Symbol Rate."
			::= { saIhnConfigQamParamEntry 3 }

		
		-- 1.3.6.1.4.1.1429.9.1.7.2.1.1.1.2.1.4
		saIhnConfigQamParamMod OBJECT-TYPE
			SYNTAX INTEGER
				{
				qam64(8),
				qam128(12),
				qam256(16)
				}
			MAX-ACCESS read-only
			STATUS current
			DESCRIPTION
				"The QAM Modulation."
			::= { saIhnConfigQamParamEntry 4 }

		
		-- 1.3.6.1.4.1.1429.9.1.7.2.1.1.1.3
		saIhnConfigSubnet OBJECT-IDENTITY
			STATUS current
			DESCRIPTION 
				"IP Subnet information for the In-Home Network"
			::= { saIhnConfigQamParam 3 }

		
		-- 1.3.6.1.4.1.1429.9.1.7.2.1.1.1.3.1
		ihnSubnetIP OBJECT-TYPE
			SYNTAX IpAddress
			MAX-ACCESS read-only
			STATUS current
			DESCRIPTION
				"The subnet IP Address. This is the subnet IP for the In-Home Network. 
				"
			::= { saIhnConfigSubnet 1 }

		
		-- 1.3.6.1.4.1.1429.9.1.7.2.1.1.1.3.2
		ihnSubnetMask OBJECT-TYPE
			SYNTAX IpAddress
			MAX-ACCESS read-only
			STATUS current
			DESCRIPTION
				"The subnet mask. The mask for the In-Home Network IP Addresses."
			::= { saIhnConfigSubnet 2 }

		
		-- 1.3.6.1.4.1.1429.9.1.7.2.1.2
		saIhnStation OBJECT-IDENTITY
			STATUS current
			DESCRIPTION 
				"Information pertaining to this IHN station"
			::= { saIhn 2 }

		
		-- 1.3.6.1.4.1.1429.9.1.7.2.1.2.1
		saIhnStationInfo OBJECT-IDENTITY
			STATUS current
			DESCRIPTION 
				"Description."
			::= { saIhnStation 1 }

		
		-- 1.3.6.1.4.1.1429.9.1.7.2.1.2.1.1
		saIhnStationRFMAC OBJECT-TYPE
			SYNTAX OCTET STRING
			MAX-ACCESS read-only
			STATUS current
			DESCRIPTION
				"The station's RF MAC Address."
			::= { saIhnStationInfo 1 }

		
		-- 1.3.6.1.4.1.1429.9.1.7.2.1.2.1.2
		saIhnStationID OBJECT-TYPE
			SYNTAX OCTET STRING
			MAX-ACCESS read-only
			STATUS current
			DESCRIPTION
				"The station's IHN Station ID."
			::= { saIhnStationInfo 2 }

		
		-- 1.3.6.1.4.1.1429.9.1.7.2.1.2.1.3
		saIhnStationIPAddress OBJECT-TYPE
			SYNTAX IpAddress
			MAX-ACCESS read-only
			STATUS current
			DESCRIPTION
				"The station's IHN IP Address. 
				This is the IP address of the station on the In-Home Network."
			::= { saIhnStationInfo 3 }

		
		-- 1.3.6.1.4.1.1429.9.1.7.2.1.2.1.4
		saIhnStationClass OBJECT-TYPE
			SYNTAX INTEGER
				{
				master(1),
				slave(2)
				}
			MAX-ACCESS read-only
			STATUS current
			DESCRIPTION
				"The station class. 
				This is the class of the station in the current configuration of the in home network."
			::= { saIhnStationInfo 4 }

		
		-- 1.3.6.1.4.1.1429.9.1.7.2.1.2.2
		saIhnService OBJECT-IDENTITY
			STATUS current
			DESCRIPTION 
				"Description."
			::= { saIhnStation 2 }

		
		-- 1.3.6.1.4.1.1429.9.1.7.2.1.2.2.1
		saIhnServiceCount OBJECT-TYPE
			SYNTAX Integer32
			MAX-ACCESS read-only
			STATUS current
			DESCRIPTION
				"The number of services offered by this station."
			::= { saIhnService 1 }

		
		-- 1.3.6.1.4.1.1429.9.1.7.2.1.2.2.2
		saIhnServiceTable OBJECT-TYPE
			SYNTAX SEQUENCE OF SaIhnServiceEntry
			MAX-ACCESS not-accessible
			STATUS current
			DESCRIPTION
				"The list of services for this station."
			::= { saIhnService 2 }

		
		-- 1.3.6.1.4.1.1429.9.1.7.2.1.2.2.2.1
		saIhnServiceEntry OBJECT-TYPE
			SYNTAX SaIhnServiceEntry
			MAX-ACCESS not-accessible
			STATUS current
			DESCRIPTION
				"The service type."
			INDEX { saIhnServiceIndex }
			::= { saIhnServiceTable 1 }

		
		SaIhnServiceEntry ::=
			SEQUENCE { 
				saIhnServiceIndex
					Unsigned32,
				saIhnServiceType
					Integer32
			 }

		-- 1.3.6.1.4.1.1429.9.1.7.2.1.2.2.2.1.1
		saIhnServiceIndex OBJECT-TYPE
			SYNTAX Unsigned32
			MAX-ACCESS read-only
			STATUS current
			DESCRIPTION
				"The index of the service type in the service table."
			::= { saIhnServiceEntry 1 }

		
		-- 1.3.6.1.4.1.1429.9.1.7.2.1.2.2.2.1.2
		saIhnServiceType OBJECT-TYPE
			SYNTAX Integer32
			MAX-ACCESS read-only
			STATUS current
			DESCRIPTION
				"The service type."
			::= { saIhnServiceEntry 2 }

		
		-- 1.3.6.1.4.1.1429.9.1.7.2.1.2.3
		saIhnAuthenticationsProvided OBJECT-IDENTITY
			STATUS current
			DESCRIPTION 
				"Stations that were authenticated by this station."
			::= { saIhnStation 3 }

		
		-- 1.3.6.1.4.1.1429.9.1.7.2.1.2.3.1
		saIhnAuthenticationsProvidedCount OBJECT-TYPE
			SYNTAX Integer32
			MAX-ACCESS read-only
			STATUS current
			DESCRIPTION
				"The number of stations that were authenticated by this station."
			::= { saIhnAuthenticationsProvided 1 }

		
		-- 1.3.6.1.4.1.1429.9.1.7.2.1.2.3.2
		saIhnAuthenticationsProvidedTable OBJECT-TYPE
			SYNTAX SEQUENCE OF SaIhnAuthenticationsProvidedEntry
			MAX-ACCESS not-accessible
			STATUS current
			DESCRIPTION
				"The list of stations that were authenticated by this station."
			::= { saIhnAuthenticationsProvided 2 }

		
		-- 1.3.6.1.4.1.1429.9.1.7.2.1.2.3.2.1
		saIhnAuthenticationsProvidedEntry OBJECT-TYPE
			SYNTAX SaIhnAuthenticationsProvidedEntry
			MAX-ACCESS not-accessible
			STATUS current
			DESCRIPTION
				"The authenticated station entry."
			INDEX { saIhnAuthenticationsProvidedRFMAC }
			::= { saIhnAuthenticationsProvidedTable 1 }

		
		SaIhnAuthenticationsProvidedEntry ::=
			SEQUENCE { 
				saIhnAuthenticationsProvidedRFMAC
					OCTET STRING,
				saIhnAuthenticationsProvidedStationID
					OCTET STRING
			 }

		-- 1.3.6.1.4.1.1429.9.1.7.2.1.2.3.2.1.1
		saIhnAuthenticationsProvidedRFMAC OBJECT-TYPE
			SYNTAX OCTET STRING
			MAX-ACCESS read-only
			STATUS current
			DESCRIPTION
				"The RF MAC Address of the authenticated Station."
			::= { saIhnAuthenticationsProvidedEntry 1 }

		
		-- 1.3.6.1.4.1.1429.9.1.7.2.1.2.3.2.1.2
		saIhnAuthenticationsProvidedStationID OBJECT-TYPE
			SYNTAX OCTET STRING
			MAX-ACCESS read-only
			STATUS current
			DESCRIPTION
				"The Station ID of the authenticated Station."
			::= { saIhnAuthenticationsProvidedEntry 2 }

		
		-- 1.3.6.1.4.1.1429.9.1.7.2.1.2.4
		saIhnAuthenticationProviderHistory OBJECT-IDENTITY
			STATUS current
			DESCRIPTION 
				"A history of authentication requests processed by this station."
			::= { saIhnStation 4 }

		
		-- 1.3.6.1.4.1.1429.9.1.7.2.1.2.4.1
		saIhnAuthProviderHistoryRequestCount OBJECT-TYPE
			SYNTAX Integer32
			MAX-ACCESS read-only
			STATUS current
			DESCRIPTION
				"The number of entries in saIhnAuthProviderHistoryTable"
			::= { saIhnAuthenticationProviderHistory 1 }

		
		-- 1.3.6.1.4.1.1429.9.1.7.2.1.2.4.2
		saIhnAuthProviderHistoryLimit OBJECT-TYPE
			SYNTAX Integer32
			MAX-ACCESS read-only
			STATUS current
			DESCRIPTION
				"The maximum number of entries that this IHN station will keep as history."
			::= { saIhnAuthenticationProviderHistory 2 }

		
		-- 1.3.6.1.4.1.1429.9.1.7.2.1.2.4.3
		saIhnAuthProviderHistoryTable OBJECT-TYPE
			SYNTAX SEQUENCE OF SaIhnAuthProviderHistoryEntry
			MAX-ACCESS not-accessible
			STATUS current
			DESCRIPTION
				"The last n authentication requests processed by this station."
			::= { saIhnAuthenticationProviderHistory 3 }

		
		-- 1.3.6.1.4.1.1429.9.1.7.2.1.2.4.3.1
		saIhnAuthProviderHistoryEntry OBJECT-TYPE
			SYNTAX SaIhnAuthProviderHistoryEntry
			MAX-ACCESS not-accessible
			STATUS current
			DESCRIPTION
				"The authentication history table entry. This table consists of the last n upto 10 authentication requests that this master station has handled."
			INDEX { saIhnAuthProviderRequestTimestamp }
			::= { saIhnAuthProviderHistoryTable 1 }

		
		SaIhnAuthProviderHistoryEntry ::=
			SEQUENCE { 
				saIhnAuthProviderRequestTimestamp
					TimeTicks,
				saIhnAuthProviderRequestRFMAC
					OCTET STRING,
				saIhnAuthProviderRequestType
					INTEGER,
				saIhnAuthProviderRequestResult
					INTEGER,
				saIhnAuthProviderRequestResultTimestamp
					TimeTicks
			 }

		-- 1.3.6.1.4.1.1429.9.1.7.2.1.2.4.3.1.1
		saIhnAuthProviderRequestTimestamp OBJECT-TYPE
			SYNTAX TimeTicks
			MAX-ACCESS read-only
			STATUS current
			DESCRIPTION
				"The request timestamp of the received authentication request."
			::= { saIhnAuthProviderHistoryEntry 1 }

		
		-- 1.3.6.1.4.1.1429.9.1.7.2.1.2.4.3.1.2
		saIhnAuthProviderRequestRFMAC OBJECT-TYPE
			SYNTAX OCTET STRING
			MAX-ACCESS read-only
			STATUS current
			DESCRIPTION
				"The RF MAC Address of the station from which the authentication request originated."
			::= { saIhnAuthProviderHistoryEntry 2 }

		
		-- 1.3.6.1.4.1.1429.9.1.7.2.1.2.4.3.1.3
		saIhnAuthProviderRequestType OBJECT-TYPE
			SYNTAX INTEGER
				{
				authRFMAC(1),
				authCertificate(2)
				}
			MAX-ACCESS read-only
			STATUS current
			DESCRIPTION
				"The authentication request type."
			::= { saIhnAuthProviderHistoryEntry 3 }

		
		-- 1.3.6.1.4.1.1429.9.1.7.2.1.2.4.3.1.4
		saIhnAuthProviderRequestResult OBJECT-TYPE
			SYNTAX INTEGER
				{
				authGrant(3),
				authDenied(4),
				authCertChallenge(5),
				authNotRegistered(6),
				authInvalidPacket(7)
				}
			MAX-ACCESS read-only
			STATUS current
			DESCRIPTION
				"The result of the authentication request."
			::= { saIhnAuthProviderHistoryEntry 4 }

		
		-- 1.3.6.1.4.1.1429.9.1.7.2.1.2.4.3.1.5
		saIhnAuthProviderRequestResultTimestamp OBJECT-TYPE
			SYNTAX TimeTicks
			MAX-ACCESS read-only
			STATUS current
			DESCRIPTION
				"The Timestamp of the result."
			::= { saIhnAuthProviderHistoryEntry 5 }

		
		-- 1.3.6.1.4.1.1429.9.1.7.2.1.2.5
		saIhnAuthenticationsReceived OBJECT-IDENTITY
			STATUS current
			DESCRIPTION 
				"The list of stations that have authenticated this station."
			::= { saIhnStation 5 }

		
		-- 1.3.6.1.4.1.1429.9.1.7.2.1.2.5.1
		saIhnAuthenticationsReceivedCount OBJECT-TYPE
			SYNTAX Integer32
			MAX-ACCESS read-only
			STATUS current
			DESCRIPTION
				"The number of stations that have authenticated this station."
			::= { saIhnAuthenticationsReceived 1 }

		
		-- 1.3.6.1.4.1.1429.9.1.7.2.1.2.5.2
		saIhnAuthenticationsReceivedTable OBJECT-TYPE
			SYNTAX SEQUENCE OF SaIhnAuthenticationsReceivedEntry
			MAX-ACCESS not-accessible
			STATUS current
			DESCRIPTION
				"The list of stations that have authenticated this station."
			::= { saIhnAuthenticationsReceived 2 }

		
		-- 1.3.6.1.4.1.1429.9.1.7.2.1.2.5.2.1
		saIhnAuthenticationsReceivedEntry OBJECT-TYPE
			SYNTAX SaIhnAuthenticationsReceivedEntry
			MAX-ACCESS not-accessible
			STATUS current
			DESCRIPTION
				"The authenticated station entry."
			INDEX { saIhnAuthenticationsReceivedRFMAC }
			::= { saIhnAuthenticationsReceivedTable 1 }

		
		SaIhnAuthenticationsReceivedEntry ::=
			SEQUENCE { 
				saIhnAuthenticationsReceivedRFMAC
					OCTET STRING,
				saIhnAuthenticationsReceivedStationID
					OCTET STRING
			 }

		-- 1.3.6.1.4.1.1429.9.1.7.2.1.2.5.2.1.1
		saIhnAuthenticationsReceivedRFMAC OBJECT-TYPE
			SYNTAX OCTET STRING
			MAX-ACCESS read-only
			STATUS current
			DESCRIPTION
				"The RF MAC Address of the provider that authenticated this station."
			::= { saIhnAuthenticationsReceivedEntry 1 }

		
		-- 1.3.6.1.4.1.1429.9.1.7.2.1.2.5.2.1.2
		saIhnAuthenticationsReceivedStationID OBJECT-TYPE
			SYNTAX OCTET STRING
			MAX-ACCESS read-only
			STATUS current
			DESCRIPTION
				"The station ID of the provider that authenticated this station."
			::= { saIhnAuthenticationsReceivedEntry 2 }

		
		-- 1.3.6.1.4.1.1429.9.1.7.2.1.2.6
		saIhnAuthenticationRequestorHistory OBJECT-IDENTITY
			STATUS current
			DESCRIPTION 
				"A history of authentication request attempts by this station.
				"
			::= { saIhnStation 6 }

		
		-- 1.3.6.1.4.1.1429.9.1.7.2.1.2.6.1
		saIhnAuthRequestorHistoryRequestCount OBJECT-TYPE
			SYNTAX Integer32
			MAX-ACCESS read-only
			STATUS current
			DESCRIPTION
				"The number of entries in saIhnAuthRequestorHistoryTable"
			::= { saIhnAuthenticationRequestorHistory 1 }

		
		-- 1.3.6.1.4.1.1429.9.1.7.2.1.2.6.2
		saIhnAuthRequestorHistoryLimit OBJECT-TYPE
			SYNTAX Integer32
			MAX-ACCESS read-only
			STATUS current
			DESCRIPTION
				"The maximum number of entries that this IHN station will keep as history."
			::= { saIhnAuthenticationRequestorHistory 2 }

		
		-- 1.3.6.1.4.1.1429.9.1.7.2.1.2.6.3
		saIhnAuthRequestorHistoryTable OBJECT-TYPE
			SYNTAX SEQUENCE OF SaIhnAuthRequestorHistoryEntry
			MAX-ACCESS not-accessible
			STATUS current
			DESCRIPTION
				"The last n authentication requests processed by this station."
			::= { saIhnAuthenticationRequestorHistory 3 }

		
		-- 1.3.6.1.4.1.1429.9.1.7.2.1.2.6.3.1
		saIhnAuthRequestorHistoryEntry OBJECT-TYPE
			SYNTAX SaIhnAuthRequestorHistoryEntry
			MAX-ACCESS not-accessible
			STATUS current
			DESCRIPTION
				"The authentication history table entry. This table consists of the last n upto 10 authentication requests that this master station has handled."
			INDEX { saIhnAuthRequestorRequestTimestamp }
			::= { saIhnAuthRequestorHistoryTable 1 }

		
		SaIhnAuthRequestorHistoryEntry ::=
			SEQUENCE { 
				saIhnAuthRequestorRequestTimestamp
					TimeTicks,
				saIhnAuthRequestorRequestRFMAC
					OCTET STRING,
				saIhnAuthRequestorRequestType
					INTEGER,
				saIhnAuthRequestorRequestResult
					INTEGER,
				saIhnAuthRequestorRequestResultTimestamp
					TimeTicks
			 }

		-- 1.3.6.1.4.1.1429.9.1.7.2.1.2.6.3.1.1
		saIhnAuthRequestorRequestTimestamp OBJECT-TYPE
			SYNTAX TimeTicks
			MAX-ACCESS read-only
			STATUS current
			DESCRIPTION
				"The request timestamp of the received authentication request."
			::= { saIhnAuthRequestorHistoryEntry 1 }

		
		-- 1.3.6.1.4.1.1429.9.1.7.2.1.2.6.3.1.2
		saIhnAuthRequestorRequestRFMAC OBJECT-TYPE
			SYNTAX OCTET STRING
			MAX-ACCESS read-only
			STATUS current
			DESCRIPTION
				"The RF MAC Address of the station to which the authentication request was sent."
			::= { saIhnAuthRequestorHistoryEntry 2 }

		
		-- 1.3.6.1.4.1.1429.9.1.7.2.1.2.6.3.1.3
		saIhnAuthRequestorRequestType OBJECT-TYPE
			SYNTAX INTEGER
				{
				authRFMAC(1),
				authCertificate(2)
				}
			MAX-ACCESS read-only
			STATUS current
			DESCRIPTION
				"The authentication request type."
			::= { saIhnAuthRequestorHistoryEntry 3 }

		
		-- 1.3.6.1.4.1.1429.9.1.7.2.1.2.6.3.1.4
		saIhnAuthRequestorRequestResult OBJECT-TYPE
			SYNTAX INTEGER
				{
				authGrant(3),
				authDenied(4),
				authCertChallenge(5),
				authNotRegistered(6),
				authInvalidPacket(7)
				}
			MAX-ACCESS read-only
			STATUS current
			DESCRIPTION
				"The result of the authentication request."
			::= { saIhnAuthRequestorHistoryEntry 4 }

		
		-- 1.3.6.1.4.1.1429.9.1.7.2.1.2.6.3.1.5
		saIhnAuthRequestorRequestResultTimestamp OBJECT-TYPE
			SYNTAX TimeTicks
			MAX-ACCESS read-only
			STATUS current
			DESCRIPTION
				"The Timestamp of the result."
			::= { saIhnAuthRequestorHistoryEntry 5 }

		
		-- 1.3.6.1.4.1.1429.9.1.7.2.2
		saIhc OBJECT-IDENTITY
			STATUS current
			DESCRIPTION 
				"In-Home Carousel"
			::= { saInHomeObjs 2 }

		
		-- 1.3.6.1.4.1.1429.9.1.7.2.2.1
		ihcCount OBJECT-TYPE
			SYNTAX Integer32
			MAX-ACCESS read-only
			STATUS current
			DESCRIPTION
				"The number of entries in the saIhcTable."
			::= { saIhc 1 }

		
		-- 1.3.6.1.4.1.1429.9.1.7.2.2.2
		saIhcTable OBJECT-TYPE
			SYNTAX SEQUENCE OF SaIhcEntry
			MAX-ACCESS not-accessible
			STATUS current
			DESCRIPTION
				"The ihc table."
			::= { saIhc 2 }

		
		-- 1.3.6.1.4.1.1429.9.1.7.2.2.2.1
		saIhcEntry OBJECT-TYPE
			SYNTAX SaIhcEntry
			MAX-ACCESS not-accessible
			STATUS current
			DESCRIPTION
				"The ihc table entry."
			INDEX { saIhcCarouselID, saIhcModuleID }
			::= { saIhcTable 1 }

		
		SaIhcEntry ::=
			SEQUENCE { 
				saIhcCarouselID
					Unsigned32,
				saIhcModuleID
					Unsigned32,
				saIhcVersion
					Integer32,
				saIhcSize
					Integer32,
				saIhcState
					INTEGER,
				saIhcDuration
					Integer32,
				saIhcTimePosted
					Unsigned32
			 }

		-- 1.3.6.1.4.1.1429.9.1.7.2.2.2.1.1
		saIhcCarouselID OBJECT-TYPE
			SYNTAX Unsigned32
			MAX-ACCESS read-only
			STATUS current
			DESCRIPTION
				"The carousel ID."
			::= { saIhcEntry 1 }

		
		-- 1.3.6.1.4.1.1429.9.1.7.2.2.2.1.2
		saIhcModuleID OBJECT-TYPE
			SYNTAX Unsigned32
			MAX-ACCESS read-only
			STATUS current
			DESCRIPTION
				"The module ID."
			::= { saIhcEntry 2 }

		
		-- 1.3.6.1.4.1.1429.9.1.7.2.2.2.1.3
		saIhcVersion OBJECT-TYPE
			SYNTAX Integer32
			MAX-ACCESS read-only
			STATUS current
			DESCRIPTION
				"The module version number."
			::= { saIhcEntry 3 }

		
		-- 1.3.6.1.4.1.1429.9.1.7.2.2.2.1.4
		saIhcSize OBJECT-TYPE
			SYNTAX Integer32
			UNITS "bytes"
			MAX-ACCESS read-only
			STATUS current
			DESCRIPTION
				"The carousel module size. 
				This is the size of the module in bytes."
			::= { saIhcEntry 4 }

		
		-- 1.3.6.1.4.1.1429.9.1.7.2.2.2.1.5
		saIhcState OBJECT-TYPE
			SYNTAX INTEGER
				{
				ready(0),
				start(1),
				stop(2),
				pause(3),
				delete(4)
				}
			MAX-ACCESS read-only
			STATUS current
			DESCRIPTION
				"The state of the carousel module."
			::= { saIhcEntry 5 }

		
		-- 1.3.6.1.4.1.1429.9.1.7.2.2.2.1.6
		saIhcDuration OBJECT-TYPE
			SYNTAX Integer32
			MAX-ACCESS read-only
			STATUS current
			DESCRIPTION
				"Duration in seconds to carousel the module data."
			::= { saIhcEntry 6 }

		
		-- 1.3.6.1.4.1.1429.9.1.7.2.2.2.1.7
		saIhcTimePosted OBJECT-TYPE
			SYNTAX Unsigned32
			MAX-ACCESS read-only
			STATUS current
			DESCRIPTION
				"Time in seconds since the module was posted.
				The epoch for this time value is January 1, 1970, 12:00:00AM GMT.
				"
			::= { saIhcEntry 7 }

		
		-- 1.3.6.1.4.1.1429.9.1.7.2.3
		saIhs OBJECT-IDENTITY
			STATUS current
			DESCRIPTION 
				"In-Home Sessions"
			::= { saInHomeObjs 3 }

		
		-- 1.3.6.1.4.1.1429.9.1.7.2.3.1
		saIhsCount OBJECT-TYPE
			SYNTAX Integer32
			MAX-ACCESS read-only
			STATUS current
			DESCRIPTION
				"The number of entries in the saIhsTable."
			::= { saIhs 1 }

		
		-- 1.3.6.1.4.1.1429.9.1.7.2.3.2
		ihsTable OBJECT-TYPE
			SYNTAX SEQUENCE OF IhsEntry
			MAX-ACCESS not-accessible
			STATUS current
			DESCRIPTION
				"The table of all currently-known In-Home sessions."
			::= { saIhs 2 }

		
		-- 1.3.6.1.4.1.1429.9.1.7.2.3.2.1
		ihsEntry OBJECT-TYPE
			SYNTAX IhsEntry
			MAX-ACCESS not-accessible
			STATUS current
			DESCRIPTION
				"An entry in the table."
			INDEX { saIhsSessionID }
			::= { ihsTable 1 }

		
		IhsEntry ::=
			SEQUENCE { 
				saIhsSessionID
					OCTET STRING,
				saIhsServerID
					OCTET STRING,
				saIhsClientID
					OCTET STRING,
				saIhsServiceType
					INTEGER,
				saIhsState
					INTEGER,
				saIhsSendIP
					IpAddress,
				saIhsSendPort
					Integer32
			 }

		-- 1.3.6.1.4.1.1429.9.1.7.2.3.2.1.1
		saIhsSessionID OBJECT-TYPE
			SYNTAX OCTET STRING
			MAX-ACCESS read-only
			STATUS current
			DESCRIPTION
				"The sessionID."
			::= { ihsEntry 1 }

		
		-- 1.3.6.1.4.1.1429.9.1.7.2.3.2.1.2
		saIhsServerID OBJECT-TYPE
			SYNTAX OCTET STRING
			MAX-ACCESS read-only
			STATUS current
			DESCRIPTION
				"The serverID. This is the station ID of the server in the In Home Network."
			::= { ihsEntry 2 }

		
		-- 1.3.6.1.4.1.1429.9.1.7.2.3.2.1.3
		saIhsClientID OBJECT-TYPE
			SYNTAX OCTET STRING
			MAX-ACCESS read-only
			STATUS current
			DESCRIPTION
				"The clientID. This is the station ID of the client in the In Home Network."
			::= { ihsEntry 3 }

		
		-- 1.3.6.1.4.1.1429.9.1.7.2.3.2.1.4
		saIhsServiceType OBJECT-TYPE
			SYNTAX INTEGER
				{
				generic(0),
				mrdvr(1)
				}
			MAX-ACCESS read-only
			STATUS current
			DESCRIPTION
				"The service type of the session."
			::= { ihsEntry 4 }

		
		-- 1.3.6.1.4.1.1429.9.1.7.2.3.2.1.5
		saIhsState OBJECT-TYPE
			SYNTAX INTEGER
				{
				sessNotEstablished(0),
				sessEstablishing(1),
				sessEstablished(2),
				sessReleasing(3)
				}
			MAX-ACCESS read-only
			STATUS current
			DESCRIPTION
				"The state of the session."
			::= { ihsEntry 5 }

		
		-- 1.3.6.1.4.1.1429.9.1.7.2.3.2.1.6
		saIhsSendIP OBJECT-TYPE
			SYNTAX IpAddress
			MAX-ACCESS read-only
			STATUS current
			DESCRIPTION
				"The IP address that the session message is sent to. 
				The In Home Network IP Address of the client station."
			::= { ihsEntry 6 }

		
		-- 1.3.6.1.4.1.1429.9.1.7.2.3.2.1.7
		saIhsSendPort OBJECT-TYPE
			SYNTAX Integer32
			MAX-ACCESS read-only
			STATUS current
			DESCRIPTION
				"The port number the session message is sent to. 
				The port the client listens to."
			::= { ihsEntry 7 }

		
		-- 1.3.6.1.4.1.1429.9.1.7.2.3.3
		ihsMrSessTrickModeTable OBJECT-TYPE
			SYNTAX SEQUENCE OF IhsMrSessTrickModeEntry
			MAX-ACCESS not-accessible
			STATUS current
			DESCRIPTION
				"For Multi-Room DVR sessions, provides the streaming trick mode type 
				used for the session. This is a sparse table which only provides
				an entry if the corresponding ihsEntry has saIhsServiceType of mrdvr."
			::= { saIhs 3 }

		
		-- 1.3.6.1.4.1.1429.9.1.7.2.3.3.1
		ihsMrSessTrickModeEntry OBJECT-TYPE
			SYNTAX IhsMrSessTrickModeEntry
			MAX-ACCESS not-accessible
			STATUS current
			DESCRIPTION
				"An entry in the table."
			INDEX { saIhsSessionID }
			::= { ihsMrSessTrickModeTable 1 }

		
		IhsMrSessTrickModeEntry ::=
			SEQUENCE { 
				ihsMrSessTrickMode
					INTEGER
			 }

		-- 1.3.6.1.4.1.1429.9.1.7.2.3.3.1.1
		ihsMrSessTrickMode OBJECT-TYPE
			SYNTAX INTEGER
				{
				mode1(1),
				mode2(2)
				}
			MAX-ACCESS read-only
			STATUS current
			DESCRIPTION
				"The streaming trick mode type used for the session."
			REFERENCE
				"MR-DVR Trick Mode Specification, Scientific-Atlanta"
			::= { ihsMrSessTrickModeEntry 1 }

		
		-- 1.3.6.1.4.1.1429.9.1.7.3
		saInHomeEvents OBJECT-IDENTITY
			STATUS current
			DESCRIPTION 
				"Events associated with the SA-INHOME-MIB."
			::= { saInHomeMib 3 }

		
		-- 1.3.6.1.4.1.1429.9.1.7.3.0
		saInHomeEventsV2 OBJECT-IDENTITY
			STATUS current
			DESCRIPTION 
				"Dummy node under which all events must be defined. 
				This is required for SNMP v1/v2 compatability."
			::= { saInHomeEvents 0 }

		
	
	END

--
-- SA-INHOME-MIB.mib
--
