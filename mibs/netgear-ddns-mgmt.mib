-- **************************************************************************
-- 
--  Copyright (c) 2012  NETGEAR, Inc.
--    All Rights Reserved
--  No portions of this material may be reproduced in any form without the
--    written permission of:
--          NETGEAR, Inc.
--          San Jose CA 95134
--  All information contained in this document is NETGEAR, Inc.
--  private, proprietary, and trade secret.
-- 
-- 
-- 
-- **************************************************************************
--    Filename: netgear-ddns-mgmt.mib
--    Creation Date: November 23, 2012
-- 
-- **************************************************************************
--    Description:
-- 
--		private MIB for ddns management.
-- 
-- **************************************************************************
--    Revision History:
-- 
-- **************************************************************************

NETGEAR-DDNS-MGMT-MIB DEFINITIONS ::= BEGIN

IMPORTS
	MODULE-IDENTITY,
	OBJECT-TYPE,
	enterprises,
	IpAddress,
	Counter32,
	Integer32,
	NOTIFICATION-TYPE       FROM SNMPv2-SMI
	TruthValue,
	DisplayString,
	MacAddress,
	PhysAddress,
	RowStatus,
 	DateAndTime,
   	TEXTUAL-CONVENTION      FROM SNMPv2-TC
	OBJECT-GROUP,
	MODULE-COMPLIANCE,
	NOTIFICATION-GROUP      FROM SNMPv2-CONF
	SnmpAdminString         FROM SNMP-FRAMEWORK-MIB
	InetAddressType,
	InetAddress,
	InetAddressIPv4,
	InetAddressIPv6         FROM INET-ADDRESS-MIB
    ifIndex                 FROM IF-MIB
    PositiveInteger         FROM UPS-MIB
    cableMgmt               FROM NETGEAR-CABLEMGMT-SMI;

-- 
-- Netgear Group
-- 
-- 
-- groups in NETGEAR-CABLE-MIB
-- 

ntgrDdnsMgmt MODULE-IDENTITY
	LAST-UPDATED "201211230000Z"
	ORGANIZATION 
		"Netgear, Inc"
	CONTACT-INFO 
		""
	DESCRIPTION 
		"Initial version of this MIB module."
::= { cableMgmt 17 }


ddnsEnable  OBJECT-TYPE
	SYNTAX     TruthValue
	MAX-ACCESS read-write
	STATUS     current
	DESCRIPTION 
		"Setting Ddns Enable."
	::= { ntgrDdnsMgmt 1 }

ddnsProviderTable  OBJECT-TYPE
	SYNTAX SEQUENCE OF ddnsProviderEntry
	MAX-ACCESS not-accessible
	STATUS     current
	DESCRIPTION 
		""
	::= { ntgrDdnsMgmt 2 }

ddnsProviderEntry  OBJECT-TYPE
	SYNTAX 	ddnsProviderEntry
	MAX-ACCESS not-accessible
	STATUS     current
	DESCRIPTION 
		""
	INDEX { ddnsHostName }
	::= { ddnsProviderTable 1 }

ddnsProviderEntry ::= SEQUENCE {
	ddnsHostName
		SnmpAdminString,
	ddnsUserName
		SnmpAdminString,
	ddnsPassword
		SnmpAdminString
}

ddnsHostName  OBJECT-TYPE
	SYNTAX     SnmpAdminString
	MAX-ACCESS read-write
	STATUS     current
	DESCRIPTION 
		"Set host name"
	::= { ddnsProviderEntry 1 }

ddnsUserName  OBJECT-TYPE
	SYNTAX     SnmpAdminString
	MAX-ACCESS read-write
	STATUS     current
	DESCRIPTION 
		"Set user name"
	::= { ddnsProviderEntry 2 }

ddnsPassword  OBJECT-TYPE
	SYNTAX     SnmpAdminString
	MAX-ACCESS read-write
	STATUS     current
	DESCRIPTION 
		"Set password"
	::= { ddnsProviderEntry 3 }

END
