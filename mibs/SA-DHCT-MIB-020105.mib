--
-- SA-DHCT-MIB.mib
-- MIB generated by MG-SOFT Visual MIB Builder Version 4.0 Build 349
-- Tuesday, February 01, 2005 at 15:08:24
--

-- Revision 1 : Initial Revision
-- Date: Friday, May 09, 2003 at 10:40:21
-- Comment:
-- Initial Revision
-- 
-- Revision 2 : Pre-UHF
-- Date: Tuesday, February 01, 2005 at 14:44:47
-- Comment:
-- 
	SA-DHCT-MIB DEFINITIONS ::= BEGIN
 
		IMPORTS
			saDhctMib			
				FROM SA-DBDSPROD-MIB			
			saModules			
				FROM SCIATL-COMMON-MIB			
			OBJECT-GROUP			
				FROM SNMPv2-CONF			
			TimeTicks, IpAddress, Integer32, Unsigned32, Gauge32, 
			Counter32, OBJECT-TYPE, MODULE-IDENTITY, OBJECT-IDENTITY			
				FROM SNMPv2-SMI			
			DisplayString, DateAndTime			
				FROM SNMPv2-TC;
	
	
		-- 1.3.6.1.4.1.1429.7.1.3
		saDhctMibModule MODULE-IDENTITY 
			LAST-UPDATED "200502011444Z"		-- February 01, 2005 at 14:44 GMT
			ORGANIZATION 
				"Scientific-Atlanta"
			CONTACT-INFO 
				"DBDS Software Engineering & Architecture
				Scientific-Atlanta
				5030 Sugarloaf Parkway
				Lawrencville, GA 30044
				"
			DESCRIPTION 
				"General module for DHCTs."
			REVISION "200502011444Z"		-- February 01, 2005 at 14:44 GMT
			DESCRIPTION 
				"."
			REVISION "200305091040Z"		-- May 09, 2003 at 10:40 GMT
			DESCRIPTION 
				"Initial Revision"
			REVISION "200305091035Z"		-- May 09, 2003 at 10:35 GMT
			DESCRIPTION 
				"Initial version of this MIB."
			::= { saModules 3 }

		
	
	
--
-- Node definitions
--
	
		-- 1.3.6.1.4.1.1429.5.1.1.1
		saDhctConf OBJECT-IDENTITY
			STATUS current
			DESCRIPTION 
				"Conformance"
			::= { saDhctMib 1 }

		
		-- 1.3.6.1.4.1.1429.5.1.1.1.1
		saDhctGroups OBJECT-IDENTITY
			STATUS current
			DESCRIPTION 
				"Object groups of the DHCT MIB"
			::= { saDhctConf 1 }

		
		-- 1.3.6.1.4.1.1429.5.1.1.1.1.1
		saDhctAllObjs OBJECT-GROUP
			OBJECTS { uptimeSinceServiceInterruption }
			STATUS current
			DESCRIPTION 
				"All the objects in this MIB."
			::= { saDhctGroups 1 }

		
		-- 1.3.6.1.4.1.1429.5.1.1.1.1.2
		saDhctSimpleEventLogDescTableGroup OBJECT-GROUP
			OBJECTS { saDhctSimpleEventLogDescIndex, saDhctSimpleEventLogDescName, saDhctSimpleEventLogDescMaxNumEvents, saDhctSimpleEventLogDescCurNumEvents }
			STATUS current
			DESCRIPTION 
				"The objects in saDhctSimpleEventLogDescTable."
			::= { saDhctGroups 2 }

		
		-- 1.3.6.1.4.1.1429.5.1.1.1.1.3
		saDhctSimpleEventLogGroup OBJECT-GROUP
			OBJECTS { saDhctSimpleEventLogEntryIndex, saDhctSimpleEventLogTimeStamp, saDhctSimpleEventLogEventCode, saDhctSimpleEventLogEventDesc }
			STATUS current
			DESCRIPTION 
				"The objects in saDhctSimpleEventLogTable."
			::= { saDhctGroups 3 }

		
		-- 1.3.6.1.4.1.1429.5.1.1.1.1.4
		saDhctDnsServerTableGroup OBJECT-GROUP
			OBJECTS { saDhctDnsServerIp }
			STATUS current
			DESCRIPTION 
				"Description."
			::= { saDhctGroups 4 }

		
		-- 1.3.6.1.4.1.1429.5.1.1.1.1.5
		saDhctAchTableGroup OBJECT-GROUP
			OBJECTS { achUnitNumber, achMpegErrors, achAC3Errors, achWDTimeouts, achFatalErrors, 
				achDmaOverruns, achPesStatistics, achFrameCounters, achPlaybackStatus, achBitBufferLevel, 
				achPTS, achDecoderStatus, achDecoderPaused, achSrDetected }
			STATUS current
			DESCRIPTION 
				"Objects in the achTable."
			::= { saDhctGroups 5 }

		
		-- 1.3.6.1.4.1.1429.5.1.1.1.1.6
		saDhctMpgaTableGroup OBJECT-GROUP
			OBJECTS { mpgaUnitNumber, mpgaDeviceState, mpgaPtsDelta, mpgaReSyncCount, mpgaSkips, 
				mpgaRepeats }
			STATUS current
			DESCRIPTION 
				"Objects in the mpgaTable."
			::= { saDhctGroups 6 }

		
		-- 1.3.6.1.4.1.1429.5.1.1.1.1.7
		saDhctAdadTableGroup OBJECT-GROUP
			OBJECTS { adadUnitNumber, adadPlaying }
			STATUS current
			DESCRIPTION 
				"Objects in the adadTable."
			::= { saDhctGroups 7 }

		
		-- 1.3.6.1.4.1.1429.5.1.1.1.1.8
		saDhctPcmTableGroup OBJECT-GROUP
			OBJECTS { pcmUnitNumber, pcmDeviceState }
			STATUS current
			DESCRIPTION 
				"Objects in the pcmTable."
			::= { saDhctGroups 8 }

		
		-- 1.3.6.1.4.1.1429.5.1.1.1.1.9
		saDhctMvcTableGroup OBJECT-GROUP
			OBJECTS { mvcUnitNumber, mvcStreamType, mvcDecodeSkips, mvcStreamChangeCount, mvcMpegStreamType, 
				mvcProgressive, mvcPid, mvcState, mvcBitBufferLevel, mvcFramePerSecond, 
				mvcVideoSyncError, mvcVertical, mvcHorizontal, mvcRffCount, mvcFrameCount
				 }
			STATUS current
			DESCRIPTION 
				"Objects in the mvcTable."
			::= { saDhctGroups 9 }

		
		-- 1.3.6.1.4.1.1429.5.1.1.1.1.10
		saDhctMvpTableGroup OBJECT-GROUP
			OBJECTS { mvpUnitNumber, mvpDiscardedFrames, mvpDeinterlacerOn, mvpLowDelay, mvpHorizontalSize, 
				mvpVerticalSize, mvpUserDisplayConfig }
			STATUS current
			DESCRIPTION 
				"Objects in the mvpTable."
			::= { saDhctGroups 10 }

		
		-- 1.3.6.1.4.1.1429.5.1.1.1.1.11
		saDhctDccTableGroup OBJECT-GROUP
			OBJECTS { dccUnitNumber, dccDecodingClosedCaptionType, dccNumOfCCtypesInStream }
			STATUS current
			DESCRIPTION 
				"Objects in the dccTable."
			::= { saDhctGroups 11 }

		
		-- 1.3.6.1.4.1.1429.5.1.1.1.1.12
		saDhctHdmiTableGroup OBJECT-GROUP
			OBJECTS { hdmiConnectionStaus, hdmiFormat480i4By3, hdmiFormat480i16By9, hdmiFormat480p4By3, hdmiFormat480p16By9, 
				hdmiFormat720p, hdmiFormat1080i, hdmiState, hdmiExtensionVersion, hdmiMonitorName, 
				hdmiAudioFormat }
			STATUS current
			DESCRIPTION 
				"Objects in the hdmiTable."
			::= { saDhctGroups 12 }

		
		-- 1.3.6.1.4.1.1429.5.1.1.1.1.13
		saDhctHdcpTableGroup OBJECT-GROUP
			OBJECTS { hdcpState }
			STATUS current
			DESCRIPTION 
				"Objects in the hdcpTable."
			::= { saDhctGroups 13 }

		
		-- 1.3.6.1.4.1.1429.5.1.1.1.1.14
		saDhctBldrTableGroup OBJECT-GROUP
			OBJECTS { bldrVersion, bldrVendorID, bldrHwVersion, bldrSwVersion, bldrHwModel, 
				bldrCompatibilityDesc1, bldrCompatibilityDesc2, bldrCompatibilityDesc3, bldrCompatibilityDesc4, bldrGroupID, 
				bldrCurrentLoadType, bldrConscRecvLdFrNetwork, bldrCodeDnLdCounter, bldrDnLdSaveCounter }
			STATUS current
			DESCRIPTION 
				"Objects in the bldrTable."
			::= { saDhctGroups 14 }

		
		-- 1.3.6.1.4.1.1429.5.1.1.1.1.15
		saDhctDevUhfModTableGroup OBJECT-GROUP
			OBJECTS { saDhctDevUhfModHiLoAttenuation, saDhctDevUhfModChannel, saDhctDevUhfModVisionCarrier }
			STATUS current
			DESCRIPTION 
				"bjects in the saDhctDevUhfModTable."
			::= { saDhctGroups 15 }

		
		-- 1.3.6.1.4.1.1429.5.1.1.1.2
		saDhctCompls OBJECT-IDENTITY
			STATUS current
			DESCRIPTION 
				"Compliances of the DHCT MIB"
			::= { saDhctConf 2 }

		
		-- 1.3.6.1.4.1.1429.5.1.1.2
		saDhctObjs OBJECT-IDENTITY
			STATUS current
			DESCRIPTION 
				"The MIB objects defined for DHCTs."
			::= { saDhctMib 2 }

		
		-- 1.3.6.1.4.1.1429.5.1.1.2.2
		system OBJECT-IDENTITY
			STATUS current
			DESCRIPTION 
				"Information regarding the DHCT as a system"
			::= { saDhctObjs 2 }

		
		-- 1.3.6.1.4.1.1429.5.1.1.2.2.2
		diag OBJECT-IDENTITY
			STATUS current
			DESCRIPTION 
				"Diagnostics"
			::= { system 2 }

		
		-- 1.3.6.1.4.1.1429.5.1.1.2.2.2.2
		reboot OBJECT-IDENTITY
			STATUS current
			DESCRIPTION 
				"DHCT reboot data collection."
			::= { diag 2 }

		
		-- 1.3.6.1.4.1.1429.5.1.1.2.2.2.2.3
		uptimeSinceServiceInterruption OBJECT-TYPE
			SYNTAX TimeTicks
			MAX-ACCESS read-only
			STATUS current
			DESCRIPTION
				"The time, in hundredths of a second, since the last service affecting reboot.
				                               
				A reboot is service affecting if it takes place while the unit's soft power 
				state is 'on'. This includes when the subscriber is watching or recording TV.
				                               
				This object returns 0 if the uptime is unknown or otherwise unavailable.
				"
			::= { reboot 3 }

		
		-- 1.3.6.1.4.1.1429.5.1.1.2.2.2.3
		saDhctLogs OBJECT-IDENTITY
			STATUS current
			DESCRIPTION 
				"Diagnostic Logs"
			::= { diag 3 }

		
		-- 1.3.6.1.4.1.1429.5.1.1.2.2.2.3.1
		saDhctSimpleEventLogDescTable OBJECT-TYPE
			SYNTAX SEQUENCE OF SaDhctSimpleEventLogDescEntry
			MAX-ACCESS not-accessible
			STATUS current
			DESCRIPTION
				"This table contains the description of each simple
				event log maintained by the DHCT."
			::= { saDhctLogs 1 }

		
		-- 1.3.6.1.4.1.1429.5.1.1.2.2.2.3.1.1
		saDhctSimpleEventLogDescEntry OBJECT-TYPE
			SYNTAX SaDhctSimpleEventLogDescEntry
			MAX-ACCESS not-accessible
			STATUS current
			DESCRIPTION
				"An entry in the table."
			INDEX { saDhctSimpleEventLogDescIndex }
			::= { saDhctSimpleEventLogDescTable 1 }

		
		SaDhctSimpleEventLogDescEntry ::=
			SEQUENCE { 
				saDhctSimpleEventLogDescIndex
					Integer32,
				saDhctSimpleEventLogDescName
					DisplayString,
				saDhctSimpleEventLogDescMaxNumEvents
					Integer32,
				saDhctSimpleEventLogDescCurNumEvents
					Integer32
			 }

		-- 1.3.6.1.4.1.1429.5.1.1.2.2.2.3.1.1.1
		saDhctSimpleEventLogDescIndex OBJECT-TYPE
			SYNTAX Integer32 (1..2147483647)
			MAX-ACCESS read-only
			STATUS current
			DESCRIPTION
				"A unique number for this log that differentiates it
				from other SimpleEventLogs."
			::= { saDhctSimpleEventLogDescEntry 1 }

		
		-- 1.3.6.1.4.1.1429.5.1.1.2.2.2.3.1.1.2
		saDhctSimpleEventLogDescName OBJECT-TYPE
			SYNTAX DisplayString
			MAX-ACCESS read-only
			STATUS current
			DESCRIPTION
				"A name and description for the log that identifies the kinds of
				events that are provided in the log. A required format is to have
				the name followed by a colon and then the description. For example:
				
				logname:This is an example description.
				
				"
			::= { saDhctSimpleEventLogDescEntry 2 }

		
		-- 1.3.6.1.4.1.1429.5.1.1.2.2.2.3.1.1.3
		saDhctSimpleEventLogDescMaxNumEvents OBJECT-TYPE
			SYNTAX Integer32 (0..2147483647)
			MAX-ACCESS read-only
			STATUS current
			DESCRIPTION
				"The maximum number of events that this DHCT will keep in the log.
				Once this number is reached, adding a new event will cause the
				oldest event to be removed from the log. The index number for the 
				new event will be one more than the index number of the most recent
				event before the new event was added. 
				
				If the maximum allowable index number is reached, then the next event
				causes the entire log to be re-indexed from 1.
				
				
				
				"
			::= { saDhctSimpleEventLogDescEntry 3 }

		
		-- 1.3.6.1.4.1.1429.5.1.1.2.2.2.3.1.1.4
		saDhctSimpleEventLogDescCurNumEvents OBJECT-TYPE
			SYNTAX Integer32 (0..2147483647)
			MAX-ACCESS read-only
			STATUS current
			DESCRIPTION
				"The current number of events in the log."
			::= { saDhctSimpleEventLogDescEntry 4 }

		
		-- 1.3.6.1.4.1.1429.5.1.1.2.2.2.3.2
		saDhctSimpleEventLogTable OBJECT-TYPE
			SYNTAX SEQUENCE OF SaDhctSimpleEventLogEntry
			MAX-ACCESS not-accessible
			STATUS current
			DESCRIPTION
				"A list of events for the simple event logs."
			::= { saDhctLogs 2 }

		
		-- 1.3.6.1.4.1.1429.5.1.1.2.2.2.3.2.1
		saDhctSimpleEventLogEntry OBJECT-TYPE
			SYNTAX SaDhctSimpleEventLogEntry
			MAX-ACCESS not-accessible
			STATUS current
			DESCRIPTION
				"An entry in the table."
			INDEX { saDhctSimpleEventLogDescIndex, saDhctSimpleEventLogEntryIndex }
			::= { saDhctSimpleEventLogTable 1 }

		
		SaDhctSimpleEventLogEntry ::=
			SEQUENCE { 
				saDhctSimpleEventLogEntryIndex
					Integer32,
				saDhctSimpleEventLogTimeStamp
					DateAndTime,
				saDhctSimpleEventLogEventCode
					Unsigned32,
				saDhctSimpleEventLogEventDesc
					DisplayString
			 }

		-- 1.3.6.1.4.1.1429.5.1.1.2.2.2.3.2.1.1
		saDhctSimpleEventLogEntryIndex OBJECT-TYPE
			SYNTAX Integer32 (1..2147483647)
			MAX-ACCESS read-only
			STATUS current
			DESCRIPTION
				"A unique number to index the entry. This number must be
				between 0 (inclusive) and saDhctSimpleEventLogDescMaxNumEvents (exclusive).
				
				Once this number is reached, adding a new event will cause the
				oldest event to be removed from the log. The index number for the 
				new event will be one more than the index number of the most recent
				event before the new event was added. 
				
				If the maximum allowable index number is reached, then the next event
				causes the entire log to be re-indexed from 1.
				"
			::= { saDhctSimpleEventLogEntry 1 }

		
		-- 1.3.6.1.4.1.1429.5.1.1.2.2.2.3.2.1.2
		saDhctSimpleEventLogTimeStamp OBJECT-TYPE
			SYNTAX DateAndTime
			MAX-ACCESS read-only
			STATUS current
			DESCRIPTION
				"The time the event occurred."
			::= { saDhctSimpleEventLogEntry 2 }

		
		-- 1.3.6.1.4.1.1429.5.1.1.2.2.2.3.2.1.3
		saDhctSimpleEventLogEventCode OBJECT-TYPE
			SYNTAX Unsigned32
			MAX-ACCESS read-only
			STATUS current
			DESCRIPTION
				"The code associated with the event."
			::= { saDhctSimpleEventLogEntry 3 }

		
		-- 1.3.6.1.4.1.1429.5.1.1.2.2.2.3.2.1.4
		saDhctSimpleEventLogEventDesc OBJECT-TYPE
			SYNTAX DisplayString
			MAX-ACCESS read-only
			STATUS current
			DESCRIPTION
				"A description of the event."
			::= { saDhctSimpleEventLogEntry 4 }

		
		-- 1.3.6.1.4.1.1429.5.1.1.2.2.3
		saDhctIds OBJECT-IDENTITY
			STATUS current
			DESCRIPTION 
				"Various identifification numbers associated with 
				the DHCT."
			::= { system 3 }

		
		-- 1.3.6.1.4.1.1429.5.1.1.2.2.3.1
		saDhctIdsAribStbId OBJECT-TYPE
			SYNTAX OCTET STRING
			MAX-ACCESS read-only
			STATUS current
			DESCRIPTION
				"Unit ID as assigned by ARIB"
			::= { saDhctIds 1 }

		
		-- 1.3.6.1.4.1.1429.5.1.1.2.2.3.2
		saDhctIdsBCasId OBJECT-TYPE
			SYNTAX DisplayString
			MAX-ACCESS read-only
			STATUS current
			DESCRIPTION
				"The B-CAS ID of the DHCT."
			::= { saDhctIds 2 }

		
		-- 1.3.6.1.4.1.1429.5.1.1.2.2.3.3
		saDhctIdsCCasId OBJECT-TYPE
			SYNTAX DisplayString
			MAX-ACCESS read-only
			STATUS current
			DESCRIPTION
				"The C-CAS ID of the DHCT."
			::= { saDhctIds 3 }

		
		-- 1.3.6.1.4.1.1429.5.1.1.2.2.4
		saDhctHardware OBJECT-IDENTITY
			STATUS current
			DESCRIPTION 
				"Basic information about the hardware platform"
			::= { system 4 }

		
		-- 1.3.6.1.4.1.1429.5.1.1.2.2.4.1
		saDhctHardwareVersion OBJECT-TYPE
			SYNTAX DisplayString
			MAX-ACCESS read-only
			STATUS current
			DESCRIPTION
				"The overall hardware version number."
			::= { saDhctHardware 1 }

		
		-- 1.3.6.1.4.1.1429.5.1.1.2.5
		saDhctNetwork OBJECT-IDENTITY
			STATUS current
			DESCRIPTION 
				"Network Information"
			::= { saDhctObjs 5 }

		
		-- 1.3.6.1.4.1.1429.5.1.1.2.5.1
		saDhctDnsServerTable OBJECT-TYPE
			SYNTAX SEQUENCE OF SaDhctDnsServerEntry
			MAX-ACCESS not-accessible
			STATUS current
			DESCRIPTION
				"The Domain Name Server IP addresses."
			::= { saDhctNetwork 1 }

		
		-- 1.3.6.1.4.1.1429.5.1.1.2.5.1.1
		saDhctDnsServerEntry OBJECT-TYPE
			SYNTAX SaDhctDnsServerEntry
			MAX-ACCESS not-accessible
			STATUS current
			DESCRIPTION
				"An entry in the table."
			INDEX { saDhctDnsServerIp }
			::= { saDhctDnsServerTable 1 }

		
		SaDhctDnsServerEntry ::=
			SEQUENCE { 
				saDhctDnsServerIp
					IpAddress
			 }

		-- 1.3.6.1.4.1.1429.5.1.1.2.5.1.1.1
		saDhctDnsServerIp OBJECT-TYPE
			SYNTAX IpAddress
			MAX-ACCESS read-only
			STATUS current
			DESCRIPTION
				"The IP address of the DNS server."
			::= { saDhctDnsServerEntry 1 }

		
		-- 1.3.6.1.4.1.1429.5.1.1.2.6
		saDhctDevice OBJECT-IDENTITY
			STATUS current
			DESCRIPTION 
				"Information specific to the DHCT-oriented devices.
				
				Items in this sub-tree have the option of being correlated to 
				entries in the HOST-RESOURCES-MIB hrDeviceTable."
			::= { saDhctObjs 6 }

		
		-- 1.3.6.1.4.1.1429.5.1.1.2.6.2
		audio OBJECT IDENTIFIER ::= { saDhctDevice 2 }

		
		-- 1.3.6.1.4.1.1429.5.1.1.2.6.2.1
		audioChannel OBJECT IDENTIFIER ::= { audio 1 }

		
		-- 1.3.6.1.4.1.1429.5.1.1.2.6.2.1.1
		achTable OBJECT-TYPE
			SYNTAX SEQUENCE OF AchEntry
			MAX-ACCESS not-accessible
			STATUS current
			DESCRIPTION
				"Status and error conditions for audio channel devices.
				"
			::= { audioChannel 1 }

		
		-- 1.3.6.1.4.1.1429.5.1.1.2.6.2.1.1.1
		achEntry OBJECT-TYPE
			SYNTAX AchEntry
			MAX-ACCESS not-accessible
			STATUS current
			DESCRIPTION
				"An entry in the table.
				
				If this device is also represented in the HOST-RESOURCES-MIB
				hrDeviceTable, then the value of saAchDeviceIndex must match hrDeviceIndex
				from HOST-RESOURCES-MIB."
			INDEX { achDeviceIndex }
			::= { achTable 1 }

		
		AchEntry ::=
			SEQUENCE { 
				achUnitNumber
					Integer32,
				achMpegErrors
					Counter32,
				achAC3Errors
					Counter32,
				achWDTimeouts
					Counter32,
				achFatalErrors
					Counter32,
				achDmaOverruns
					Counter32,
				achPesStatistics
					Integer32,
				achFrameCounters
					Counter32,
				achPlaybackStatus
					Integer32,
				achBitBufferLevel
					Gauge32,
				achPTS
					Integer32,
				achDecoderStatus
					Integer32,
				achDecoderPaused
					INTEGER,
				achSrDetected
					INTEGER,
				achDeviceIndex
					Integer32
			 }

		-- 1.3.6.1.4.1.1429.5.1.1.2.6.2.1.1.1.1
		achUnitNumber OBJECT-TYPE
			SYNTAX Integer32 (1..2147483647)
			MAX-ACCESS read-only
			STATUS current
			DESCRIPTION
				"Unique number identifying the particular audio channel."
			::= { achEntry 1 }

		
		-- 1.3.6.1.4.1.1429.5.1.1.2.6.2.1.1.1.2
		achMpegErrors OBJECT-TYPE
			SYNTAX Counter32
			MAX-ACCESS read-only
			STATUS current
			DESCRIPTION
				"The number of MPEG decoding errors detected by the audio DSP 
				since playback of the stream started."
			::= { achEntry 2 }

		
		-- 1.3.6.1.4.1.1429.5.1.1.2.6.2.1.1.1.3
		achAC3Errors OBJECT-TYPE
			SYNTAX Counter32
			MAX-ACCESS read-only
			STATUS current
			DESCRIPTION
				"The number of AC3 decoding errors detected by the audio DSP 
				since playback of the stream started."
			::= { achEntry 3 }

		
--  
		-- 1.3.6.1.4.1.1429.5.1.1.2.6.2.1.1.1.4
		achWDTimeouts OBJECT-TYPE
			SYNTAX Counter32
			MAX-ACCESS read-only
			STATUS current
			DESCRIPTION
				"A count of how many times audio DSP reset due to a Watch Dog timeout since DHCT reboot."
			::= { achEntry 4 }

		
--  
		-- 1.3.6.1.4.1.1429.5.1.1.2.6.2.1.1.1.5
		achFatalErrors OBJECT-TYPE
			SYNTAX Counter32
			MAX-ACCESS read-only
			STATUS current
			DESCRIPTION
				"A count of how many times audio DSP reset due to a Fatal Error since DHCT reboot."
			::= { achEntry 5 }

		
--  
		-- 1.3.6.1.4.1.1429.5.1.1.2.6.2.1.1.1.6
		achDmaOverruns OBJECT-TYPE
			SYNTAX Counter32
			MAX-ACCESS read-only
			STATUS current
			DESCRIPTION
				"The number of DMA overruns detected by the audio DSP since DHCT reboot."
			::= { achEntry 6 }

		
--  
		-- 1.3.6.1.4.1.1429.5.1.1.2.6.2.1.1.1.7
		achPesStatistics OBJECT-TYPE
			SYNTAX Integer32
			MAX-ACCESS read-only
			STATUS current
			DESCRIPTION
				"Statistics of the PES parser.
				Bitfield definition:
				b[31]  1-> PES parser locked, 0-> Unlocked
				b[7:0] number of times PES framer has entered lock state.
				
				 
				
				"
			::= { achEntry 7 }

		
--  
		-- 1.3.6.1.4.1.1429.5.1.1.2.6.2.1.1.1.8
		achFrameCounters OBJECT-TYPE
			SYNTAX Counter32
			MAX-ACCESS read-only
			STATUS current
			DESCRIPTION
				"The number of audio frames decoded by the audio DSP since DHCT reboot."
			::= { achEntry 8 }

		
--  
		-- 1.3.6.1.4.1.1429.5.1.1.2.6.2.1.1.1.9
		achPlaybackStatus OBJECT-TYPE
			SYNTAX Integer32
			MAX-ACCESS read-only
			STATUS current
			DESCRIPTION
				"Describes what audio is currently playing.
				Bitfield : bit is set indicates audio from the following sources is currently being played.
				
				b[0] -> PCM
				
				b[1] -> Digital
				
				b[2] -> Analog
				
				b[3] -> External
				
				 
				
				"
			::= { achEntry 9 }

		
--  
		-- 1.3.6.1.4.1.1429.5.1.1.2.6.2.1.1.1.10
		achBitBufferLevel OBJECT-TYPE
			SYNTAX Gauge32 (0..100)
			UNITS "Percent"
			MAX-ACCESS read-only
			STATUS current
			DESCRIPTION
				"Expressed as a percentage of filled capacity 0% - 100%."
			::= { achEntry 10 }

		
--  
		-- 1.3.6.1.4.1.1429.5.1.1.2.6.2.1.1.1.11
		achPTS OBJECT-TYPE
			SYNTAX Integer32
			MAX-ACCESS read-only
			STATUS current
			DESCRIPTION
				"The 32MSB of the last decoded PTS."
			::= { achEntry 11 }

		
--  
		-- 1.3.6.1.4.1.1429.5.1.1.2.6.2.1.1.1.12
		achDecoderStatus OBJECT-TYPE
			SYNTAX Integer32
			MAX-ACCESS read-only
			STATUS current
			DESCRIPTION
				"State of the audio decoder.
				b[0:3]
				
				0 -> Idle
				
				1 -> PCM passthrough
				
				2 -> AC3 Decode
				
				3 -> MPEG Decode
				
				4 -> Auto Detect
				
				5 -> Test tone generator
				
				6 -> Secondary PCM only
				
				7 -> AAC Passthough
				
				15 -> Initialized
				
				 
				
				b[4] 1 -> decoder is paused
				
				"
			::= { achEntry 12 }

		
--  
		-- 1.3.6.1.4.1.1429.5.1.1.2.6.2.1.1.1.13
		achDecoderPaused OBJECT-TYPE
			SYNTAX INTEGER (0..1)
			MAX-ACCESS read-only
			STATUS current
			DESCRIPTION
				"State of the audio decoder.
				b[4] 1 -> decoder is paused"
			::= { achEntry 13 }

		
--  
		-- 1.3.6.1.4.1.1429.5.1.1.2.6.2.1.1.1.14
		achSrDetected OBJECT-TYPE
			SYNTAX INTEGER
				{
				kFREQ48KHz(0),
				kFREQ44dot1KHz(1),
				kFREQ32KHz(2),
				kFREQ96KHz(3),
				kFREQ88dot2KHz(4),
				kFREQ64KHz(5),
				kFREQ24KHz(6),
				kFREQ22dot05KHz(7),
				kFREQ16KHz(8),
				kFREQ12KHz(9),
				kFREQ11dot025KHz(10)
				}
			MAX-ACCESS read-only
			STATUS current
			DESCRIPTION
				"Sample rate detected.
				
				
				"
			::= { achEntry 14 }

		
		-- 1.3.6.1.4.1.1429.5.1.1.2.6.2.1.1.1.15
		achDeviceIndex OBJECT-TYPE
			SYNTAX Integer32 (1..2147483647)
			MAX-ACCESS not-accessible
			STATUS current
			DESCRIPTION
				"A unique number for each audio channel device in the table.
				
				If this device is also represented in the HOST-RESOURCES-MIB
				hrDeviceTable, then the value of saAchDeviceIndex must match hrDeviceIndex
				from HOST-RESOURCES-MIB."
			::= { achEntry 15 }

		
--  
		-- 1.3.6.1.4.1.1429.5.1.1.2.6.2.2
		mpegdAudioDecoder OBJECT IDENTIFIER ::= { audio 2 }

		
--  
		-- 1.3.6.1.4.1.1429.5.1.1.2.6.2.2.1
		mpgaTable OBJECT-TYPE
			SYNTAX SEQUENCE OF MpgaEntry
			MAX-ACCESS not-accessible
			STATUS current
			DESCRIPTION
				"Status and error conditions of digital audio decoder devices (either AC3 or MPEG)."
			::= { mpegdAudioDecoder 1 }

		
--  
		-- 1.3.6.1.4.1.1429.5.1.1.2.6.2.2.1.1
		mpgaEntry OBJECT-TYPE
			SYNTAX MpgaEntry
			MAX-ACCESS not-accessible
			STATUS current
			DESCRIPTION
				"A entry in the table.
				
				If this device is also represented in the HOST-RESOURCES-MIB
				hrDeviceTable, then the value of saAchDeviceIndex must match hrDeviceIndex
				from HOST-RESOURCES-MIB."
			INDEX { mpgaDeviceIndex }
			::= { mpgaTable 1 }

		
		MpgaEntry ::=
			SEQUENCE { 
				mpgaUnitNumber
					Integer32,
				mpgaDeviceState
					INTEGER,
				mpgaPtsDelta
					Integer32,
				mpgaReSyncCount
					Counter32,
				mpgaSkips
					Counter32,
				mpgaRepeats
					Counter32,
				mpgaDeviceIndex
					Integer32
			 }

--  
		-- 1.3.6.1.4.1.1429.5.1.1.2.6.2.2.1.1.1
		mpgaUnitNumber OBJECT-TYPE
			SYNTAX Integer32 (1..2147483647)
			MAX-ACCESS read-only
			STATUS current
			DESCRIPTION
				"Unique number identifying the particular mpeg audio channel device."
			::= { mpgaEntry 1 }

		
--  
		-- 1.3.6.1.4.1.1429.5.1.1.2.6.2.2.1.1.2
		mpgaDeviceState OBJECT-TYPE
			SYNTAX INTEGER
				{
				kPREINIT(0),
				kCLOSED(3),
				kOPENED(4),
				kCONNECTED(5),
				kBBfill(6),
				kSYNCING(7),
				kPLAYBACK(8)
				}
			MAX-ACCESS read-only
			STATUS current
			DESCRIPTION
				"State of each MPEG channel driver."
			::= { mpgaEntry 2 }

		
--  
		-- 1.3.6.1.4.1.1429.5.1.1.2.6.2.2.1.1.3
		mpgaPtsDelta OBJECT-TYPE
			SYNTAX Integer32
			MAX-ACCESS read-only
			STATUS current
			DESCRIPTION
				"The difference (delta) between the PTS and STC."
			::= { mpgaEntry 3 }

		
--  
		-- 1.3.6.1.4.1.1429.5.1.1.2.6.2.2.1.1.4
		mpgaReSyncCount OBJECT-TYPE
			SYNTAX Counter32
			MAX-ACCESS read-only
			STATUS current
			DESCRIPTION
				"The number of times digital audio re-synced since the stream was started."
			::= { mpgaEntry 4 }

		
--  
		-- 1.3.6.1.4.1.1429.5.1.1.2.6.2.2.1.1.5
		mpgaSkips OBJECT-TYPE
			SYNTAX Counter32
			MAX-ACCESS read-only
			STATUS current
			DESCRIPTION
				"The number of digital audio skips since the stream was started."
			::= { mpgaEntry 5 }

		
--  
		-- 1.3.6.1.4.1.1429.5.1.1.2.6.2.2.1.1.6
		mpgaRepeats OBJECT-TYPE
			SYNTAX Counter32
			MAX-ACCESS read-only
			STATUS current
			DESCRIPTION
				"The number of digital audio repeats since the stream was started."
			::= { mpgaEntry 6 }

		
		-- 1.3.6.1.4.1.1429.5.1.1.2.6.2.2.1.1.7
		mpgaDeviceIndex OBJECT-TYPE
			SYNTAX Integer32 (1..2147483647)
			MAX-ACCESS not-accessible
			STATUS current
			DESCRIPTION
				"A unique number for each audio channel device in the table.
				
				If this device is also represented in the HOST-RESOURCES-MIB
				hrDeviceTable, then the value of saAchDeviceIndex must match hrDeviceIndex
				from HOST-RESOURCES-MIB."
			::= { mpgaEntry 7 }

		
--  
		-- 1.3.6.1.4.1.1429.5.1.1.2.6.2.3
		audioAnalogDecoder OBJECT IDENTIFIER ::= { audio 3 }

		
--  
		-- 1.3.6.1.4.1.1429.5.1.1.2.6.2.3.1
		adadTable OBJECT-TYPE
			SYNTAX SEQUENCE OF AdadEntry
			MAX-ACCESS not-accessible
			STATUS current
			DESCRIPTION
				"Analog Audio Decoder devices. These devices are used to
				enable and disable analog audio pathways from the tuners and
				the AUX inputs."
			::= { audioAnalogDecoder 1 }

		
--  
		-- 1.3.6.1.4.1.1429.5.1.1.2.6.2.3.1.1
		adadEntry OBJECT-TYPE
			SYNTAX AdadEntry
			MAX-ACCESS not-accessible
			STATUS current
			DESCRIPTION
				"Each row entry describes a status or an error of this element."
			INDEX { adadDeviceIndex }
			::= { adadTable 1 }

		
		AdadEntry ::=
			SEQUENCE { 
				adadUnitNumber
					Integer32,
				adadPlaying
					INTEGER,
				adadDeviceIndex
					Integer32
			 }

--  
		-- 1.3.6.1.4.1.1429.5.1.1.2.6.2.3.1.1.1
		adadUnitNumber OBJECT-TYPE
			SYNTAX Integer32 (1..2147483647)
			MAX-ACCESS read-only
			STATUS current
			DESCRIPTION
				"Number identifying the particular audio analog decoder channel."
			::= { adadEntry 1 }

		
--  
		-- 1.3.6.1.4.1.1429.5.1.1.2.6.2.3.1.1.2
		adadPlaying OBJECT-TYPE
			SYNTAX INTEGER
				{
				notPlaying(0),
				playing(1)
				}
			MAX-ACCESS read-only
			STATUS current
			DESCRIPTION
				"Indicates if analog audio is currently playing on this channel."
			::= { adadEntry 2 }

		
		-- 1.3.6.1.4.1.1429.5.1.1.2.6.2.3.1.1.3
		adadDeviceIndex OBJECT-TYPE
			SYNTAX Integer32 (1..2147483647)
			MAX-ACCESS not-accessible
			STATUS current
			DESCRIPTION
				"A unique number for each audio analog decoder device in the table.
				
				If this device is also represented in the HOST-RESOURCES-MIB
				hrDeviceTable, then the value of adadDeviceIndex must match hrDeviceIndex
				from HOST-RESOURCES-MIB."
			::= { adadEntry 3 }

		
--  
		-- 1.3.6.1.4.1.1429.5.1.1.2.6.2.4
		cpuGeneratedAudio OBJECT IDENTIFIER ::= { audio 4 }

		
--  
		-- 1.3.6.1.4.1.1429.5.1.1.2.6.2.4.1
		pcmTable OBJECT-TYPE
			SYNTAX SEQUENCE OF PcmEntry
			MAX-ACCESS not-accessible
			STATUS current
			DESCRIPTION
				"Status and error conditions of PCM devices."
			::= { cpuGeneratedAudio 1 }

		
--  
		-- 1.3.6.1.4.1.1429.5.1.1.2.6.2.4.1.1
		pcmEntry OBJECT-TYPE
			SYNTAX PcmEntry
			MAX-ACCESS not-accessible
			STATUS current
			DESCRIPTION
				"A row in the table.
				
				If this device is also represented in the HOST-RESOURCES-MIB
				hrDeviceTable, then the value of pcmDeviceIndex must match hrDeviceIndex
				from HOST-RESOURCES-MIB."
			INDEX { pcmDeviceIndex }
			::= { pcmTable 1 }

		
		PcmEntry ::=
			SEQUENCE { 
				pcmUnitNumber
					Integer32,
				pcmDeviceState
					INTEGER,
				pcmDeviceIndex
					Integer32
			 }

--  
		-- 1.3.6.1.4.1.1429.5.1.1.2.6.2.4.1.1.1
		pcmUnitNumber OBJECT-TYPE
			SYNTAX Integer32 (1..2147483647)
			MAX-ACCESS read-only
			STATUS current
			DESCRIPTION
				"Unique number identifying the particular audio analog decoder channel."
			::= { pcmEntry 1 }

		
--  
		-- 1.3.6.1.4.1.1429.5.1.1.2.6.2.4.1.1.2
		pcmDeviceState OBJECT-TYPE
			SYNTAX INTEGER
				{
				kCLOSED(1),
				kOPEND(2),
				kACTIVE(3),
				kPAUSED(4)
				}
			MAX-ACCESS read-only
			STATUS current
			DESCRIPTION
				"State of the PCM device."
			::= { pcmEntry 2 }

		
		-- 1.3.6.1.4.1.1429.5.1.1.2.6.2.4.1.1.3
		pcmDeviceIndex OBJECT-TYPE
			SYNTAX Integer32 (1..2147483647)
			MAX-ACCESS not-accessible
			STATUS current
			DESCRIPTION
				"A unique number for each pcm device in the table.
				
				If this device is also represented in the HOST-RESOURCES-MIB
				hrDeviceTable, then the value of pcmDeviceIndex must match hrDeviceIndex
				from HOST-RESOURCES-MIB."
			::= { pcmEntry 3 }

		
--  
		-- 1.3.6.1.4.1.1429.5.1.1.2.6.3
		vcxo OBJECT IDENTIFIER ::= { saDhctDevice 3 }

		
--  
		-- 1.3.6.1.4.1.1429.5.1.1.2.6.4
		video OBJECT IDENTIFIER ::= { saDhctDevice 4 }

		
--  
		-- 1.3.6.1.4.1.1429.5.1.1.2.6.4.1
		mpegdVideoDecoder OBJECT IDENTIFIER ::= { video 1 }

		
--  
		-- 1.3.6.1.4.1.1429.5.1.1.2.6.4.1.1
		mvcTable OBJECT-TYPE
			SYNTAX SEQUENCE OF MvcEntry
			MAX-ACCESS not-accessible
			STATUS current
			DESCRIPTION
				"Status and error conditions of MPEG Video Decoder devices."
			::= { mpegdVideoDecoder 1 }

		
--  
		-- 1.3.6.1.4.1.1429.5.1.1.2.6.4.1.1.1
		mvcEntry OBJECT-TYPE
			SYNTAX MvcEntry
			MAX-ACCESS not-accessible
			STATUS current
			DESCRIPTION
				"A row in the table.
				
				If this device is also represented in the HOST-RESOURCES-MIB
				hrDeviceTable, then the value of mvcDeviceIndex must match hrDeviceIndex
				from HOST-RESOURCES-MIB."
			INDEX { mvcDeviceIndex }
			::= { mvcTable 1 }

		
		MvcEntry ::=
			SEQUENCE { 
				mvcUnitNumber
					Integer32,
				mvcStreamType
					INTEGER,
				mvcDecodeSkips
					Counter32,
				mvcStreamChangeCount
					Counter32,
				mvcMpegStreamType
					INTEGER,
				mvcProgressive
					INTEGER,
				mvcPid
					Integer32,
				mvcState
					Integer32,
				mvcBitBufferLevel
					Gauge32,
				mvcFramePerSecond
					Integer32,
				mvcVideoSyncError
					Counter32,
				mvcVertical
					Integer32,
				mvcHorizontal
					Integer32,
				mvcRffCount
					Counter32,
				mvcFrameCount
					Counter32,
				mvcDeviceIndex
					Integer32
			 }

--  
		-- 1.3.6.1.4.1.1429.5.1.1.2.6.4.1.1.1.1
		mvcUnitNumber OBJECT-TYPE
			SYNTAX Integer32 (1..2)
			MAX-ACCESS read-only
			STATUS current
			DESCRIPTION
				"Unique number identifying the particular mpegd video decoder channel."
			::= { mvcEntry 1 }

		
--  
		-- 1.3.6.1.4.1.1429.5.1.1.2.6.4.1.1.1.2
		mvcStreamType OBJECT-TYPE
			SYNTAX INTEGER
				{
				kSD(0),
				kHD(1)
				}
			MAX-ACCESS read-only
			STATUS current
			DESCRIPTION
				"The current stream type."
			::= { mvcEntry 2 }

		
--  
		-- 1.3.6.1.4.1.1429.5.1.1.2.6.4.1.1.1.3
		mvcDecodeSkips OBJECT-TYPE
			SYNTAX Counter32
			MAX-ACCESS read-only
			STATUS current
			DESCRIPTION
				"The number of times that the decoder skipped a decode since tuned to the current channel."
			::= { mvcEntry 3 }

		
--  
		-- 1.3.6.1.4.1.1429.5.1.1.2.6.4.1.1.1.4
		mvcStreamChangeCount OBJECT-TYPE
			SYNTAX Counter32
			MAX-ACCESS read-only
			STATUS current
			DESCRIPTION
				"The number of times that the stream has change since tune to the current channel."
			::= { mvcEntry 4 }

		
--  
		-- 1.3.6.1.4.1.1429.5.1.1.2.6.4.1.1.1.5
		mvcMpegStreamType OBJECT-TYPE
			SYNTAX INTEGER
				{
				kMPEG1(0),
				kMPEG2(1)
				}
			MAX-ACCESS read-only
			STATUS current
			DESCRIPTION
				"The type of stream being decoded."
			::= { mvcEntry 5 }

		
--  
		-- 1.3.6.1.4.1.1429.5.1.1.2.6.4.1.1.1.6
		mvcProgressive OBJECT-TYPE
			SYNTAX INTEGER
				{
				kINTERLACED(0),
				kPROGRESSIVE(1)
				}
			MAX-ACCESS read-only
			STATUS current
			DESCRIPTION
				"Indicates if the stream is progressive scan or interlaced."
			::= { mvcEntry 6 }

		
--  
		-- 1.3.6.1.4.1.1429.5.1.1.2.6.4.1.1.1.7
		mvcPid OBJECT-TYPE
			SYNTAX Integer32
			MAX-ACCESS read-only
			STATUS current
			DESCRIPTION
				"The current PID value of the stream being decoded."
			::= { mvcEntry 7 }

		
--  
		-- 1.3.6.1.4.1.1429.5.1.1.2.6.4.1.1.1.8
		mvcState OBJECT-TYPE
			SYNTAX Integer32
			MAX-ACCESS read-only
			STATUS current
			DESCRIPTION
				"The current stream type."
			::= { mvcEntry 8 }

		
--  
		-- 1.3.6.1.4.1.1429.5.1.1.2.6.4.1.1.1.9
		mvcBitBufferLevel OBJECT-TYPE
			SYNTAX Gauge32 (0..100)
			UNITS "Percent"
			MAX-ACCESS read-only
			STATUS current
			DESCRIPTION
				"The % full level of the bit buffer."
			::= { mvcEntry 9 }

		
--  
		-- 1.3.6.1.4.1.1429.5.1.1.2.6.4.1.1.1.10
		mvcFramePerSecond OBJECT-TYPE
			SYNTAX Integer32
			MAX-ACCESS read-only
			STATUS current
			DESCRIPTION
				"The stream frame rate."
			::= { mvcEntry 10 }

		
		-- 1.3.6.1.4.1.1429.5.1.1.2.6.4.1.1.1.11
		mvcVideoSyncError OBJECT-TYPE
			SYNTAX Counter32
			MAX-ACCESS read-only
			STATUS current
			DESCRIPTION
				"The delta value for video-to-PCR synchronization"
			::= { mvcEntry 11 }

		
		-- 1.3.6.1.4.1.1429.5.1.1.2.6.4.1.1.1.12
		mvcVertical OBJECT-TYPE
			SYNTAX Integer32
			MAX-ACCESS read-only
			STATUS current
			DESCRIPTION
				"The vertical size of the current stream."
			::= { mvcEntry 12 }

		
		-- 1.3.6.1.4.1.1429.5.1.1.2.6.4.1.1.1.13
		mvcHorizontal OBJECT-TYPE
			SYNTAX Integer32
			MAX-ACCESS read-only
			STATUS current
			DESCRIPTION
				"The horizontal size of the current stream."
			::= { mvcEntry 13 }

		
		-- 1.3.6.1.4.1.1429.5.1.1.2.6.4.1.1.1.14
		mvcRffCount OBJECT-TYPE
			SYNTAX Counter32
			MAX-ACCESS read-only
			STATUS current
			DESCRIPTION
				"Counts the number of repeat-first-field flags encountered."
			::= { mvcEntry 14 }

		
		-- 1.3.6.1.4.1.1429.5.1.1.2.6.4.1.1.1.15
		mvcFrameCount OBJECT-TYPE
			SYNTAX Counter32
			MAX-ACCESS read-only
			STATUS current
			DESCRIPTION
				"The number of frames that have been decoded since the current channel was tuned.
				"
			::= { mvcEntry 15 }

		
		-- 1.3.6.1.4.1.1429.5.1.1.2.6.4.1.1.1.16
		mvcDeviceIndex OBJECT-TYPE
			SYNTAX Integer32 (1..2147483647)
			MAX-ACCESS not-accessible
			STATUS current
			DESCRIPTION
				"A unique number for each mvc device in the table.
				
				If this device is also represented in the HOST-RESOURCES-MIB
				hrDeviceTable, then the value of mvcDeviceIndex must match hrDeviceIndex
				from HOST-RESOURCES-MIB."
			::= { mvcEntry 16 }

		
--  
		-- 1.3.6.1.4.1.1429.5.1.1.2.6.4.2
		mpegdVideoDisplay OBJECT IDENTIFIER ::= { video 2 }

		
--  
		-- 1.3.6.1.4.1.1429.5.1.1.2.6.4.2.1
		mvpTable OBJECT-TYPE
			SYNTAX SEQUENCE OF MvpEntry
			MAX-ACCESS not-accessible
			STATUS current
			DESCRIPTION
				"Status and error conditions of MPEGD Video Display devices."
			::= { mpegdVideoDisplay 1 }

		
--  
		-- 1.3.6.1.4.1.1429.5.1.1.2.6.4.2.1.1
		mvpEntry OBJECT-TYPE
			SYNTAX MvpEntry
			MAX-ACCESS not-accessible
			STATUS current
			DESCRIPTION
				"A row in the table.
				
				If this device is also represented in the HOST-RESOURCES-MIB
				hrDeviceTable, then the value of mvpDeviceIndex must match hrDeviceIndex
				from HOST-RESOURCES-MIB."
			INDEX { mvpDeviceIndex }
			::= { mvpTable 1 }

		
		MvpEntry ::=
			SEQUENCE { 
				mvpUnitNumber
					Integer32,
				mvpDiscardedFrames
					Counter32,
				mvpDeinterlacerOn
					INTEGER,
				mvpLowDelay
					INTEGER,
				mvpHorizontalSize
					Integer32,
				mvpVerticalSize
					Integer32,
				mvpUserDisplayConfig
					INTEGER,
				mvpDeviceIndex
					Integer32
			 }

--  
		-- 1.3.6.1.4.1.1429.5.1.1.2.6.4.2.1.1.1
		mvpUnitNumber OBJECT-TYPE
			SYNTAX Integer32 (1..2)
			MAX-ACCESS read-only
			STATUS current
			DESCRIPTION
				"Unique number identifying the particular MPEGD video display channel."
			::= { mvpEntry 1 }

		
--  
		-- 1.3.6.1.4.1.1429.5.1.1.2.6.4.2.1.1.2
		mvpDiscardedFrames OBJECT-TYPE
			SYNTAX Counter32
			MAX-ACCESS read-only
			STATUS current
			DESCRIPTION
				"The number of late frames discared since tuning to the current channel."
			::= { mvpEntry 2 }

		
--  
		-- 1.3.6.1.4.1.1429.5.1.1.2.6.4.2.1.1.3
		mvpDeinterlacerOn OBJECT-TYPE
			SYNTAX INTEGER (0..1)
			MAX-ACCESS read-only
			STATUS current
			DESCRIPTION
				"Indicates if the De-interlacer is currently running."
			::= { mvpEntry 3 }

		
--  
		-- 1.3.6.1.4.1.1429.5.1.1.2.6.4.2.1.1.4
		mvpLowDelay OBJECT-TYPE
			SYNTAX INTEGER (0..1)
			MAX-ACCESS read-only
			STATUS current
			DESCRIPTION
				"Indicates if the current stream is a low delay stream."
			::= { mvpEntry 4 }

		
--  
		-- 1.3.6.1.4.1.1429.5.1.1.2.6.4.2.1.1.5
		mvpHorizontalSize OBJECT-TYPE
			SYNTAX Integer32
			MAX-ACCESS read-only
			STATUS current
			DESCRIPTION
				"Horizontal Size of Frame."
			::= { mvpEntry 5 }

		
--  
		-- 1.3.6.1.4.1.1429.5.1.1.2.6.4.2.1.1.6
		mvpVerticalSize OBJECT-TYPE
			SYNTAX Integer32
			MAX-ACCESS read-only
			STATUS current
			DESCRIPTION
				"Vertical Size of Frame."
			::= { mvpEntry 6 }

		
--  
		-- 1.3.6.1.4.1.1429.5.1.1.2.6.4.2.1.1.7
		mvpUserDisplayConfig OBJECT-TYPE
			SYNTAX INTEGER
				{
				k1080i(1),
				k720p(2),
				k480p(3),
				k480i(4)
				}
			MAX-ACCESS read-only
			STATUS current
			DESCRIPTION
				"Returns the current output configuration of the display: 
				1 = 1080i; 2 = 720p; 3 = 480p. 4 = 480i."
			::= { mvpEntry 7 }

		
		-- 1.3.6.1.4.1.1429.5.1.1.2.6.4.2.1.1.8
		mvpDeviceIndex OBJECT-TYPE
			SYNTAX Integer32 (1..2147483647)
			MAX-ACCESS not-accessible
			STATUS current
			DESCRIPTION
				"A unique number for each mvp device in the table.
				
				If this device is also represented in the HOST-RESOURCES-MIB
				hrDeviceTable, then the value of mvpDeviceIndex must match hrDeviceIndex
				from HOST-RESOURCES-MIB."
			::= { mvpEntry 8 }

		
--  
		-- 1.3.6.1.4.1.1429.5.1.1.2.6.4.3
		digitalClosedCaption OBJECT IDENTIFIER ::= { video 3 }

		
--  
		-- 1.3.6.1.4.1.1429.5.1.1.2.6.4.3.1
		dccTable OBJECT-TYPE
			SYNTAX SEQUENCE OF DccEntry
			MAX-ACCESS not-accessible
			STATUS current
			DESCRIPTION
				"Status and error conditions of Digital Closed Caption devices."
			::= { digitalClosedCaption 1 }

		
--  
		-- 1.3.6.1.4.1.1429.5.1.1.2.6.4.3.1.1
		dccEntry OBJECT-TYPE
			SYNTAX DccEntry
			MAX-ACCESS not-accessible
			STATUS current
			DESCRIPTION
				"A row in the table.
				
				If this device is also represented in the HOST-RESOURCES-MIB
				hrDeviceTable, then the value of dccDeviceIndex must match hrDeviceIndex
				from HOST-RESOURCES-MIB."
			INDEX { dccDeviceIndex }
			::= { dccTable 1 }

		
		DccEntry ::=
			SEQUENCE { 
				dccUnitNumber
					Integer32,
				dccDecodingClosedCaptionType
					INTEGER,
				dccNumOfCCtypesInStream
					Integer32,
				dccDeviceIndex
					Integer32
			 }

--  
		-- 1.3.6.1.4.1.1429.5.1.1.2.6.4.3.1.1.1
		dccUnitNumber OBJECT-TYPE
			SYNTAX Integer32 (1..2)
			MAX-ACCESS read-only
			STATUS current
			DESCRIPTION
				"Unique number identifying the particular digital closed caption channel."
			::= { dccEntry 1 }

		
--  
		-- 1.3.6.1.4.1.1429.5.1.1.2.6.4.3.1.1.2
		dccDecodingClosedCaptionType OBJECT-TYPE
			SYNTAX INTEGER
				{
				kNone(0),
				kSaType0(1),
				kDvs157(2),
				kEia708WithoutDtvcc(3),
				kEia708WithDtvcc(4)
				}
			MAX-ACCESS read-only
			STATUS current
			DESCRIPTION
				"The type of CC being decoded: 
				
				kNone               = none, 
				kSaType0            = SA Type 0, 
				kDvs157             = DVS-157 (Digicypher), 
				kEia708WithoutDtvcc = EIA-708 w/o DTVCC, 
				kEia708WithDtvcc    = EIA-708 w/ DTVCC."
			::= { dccEntry 2 }

		
--  
		-- 1.3.6.1.4.1.1429.5.1.1.2.6.4.3.1.1.3
		dccNumOfCCtypesInStream OBJECT-TYPE
			SYNTAX Integer32
			MAX-ACCESS read-write
			STATUS current
			DESCRIPTION
				"The number of CC formats currently available in the stream.
				If the MPEG decoder is not active, this value is 0."
			::= { dccEntry 3 }

		
		-- 1.3.6.1.4.1.1429.5.1.1.2.6.4.3.1.1.4
		dccDeviceIndex OBJECT-TYPE
			SYNTAX Integer32 (1..2147483647)
			MAX-ACCESS not-accessible
			STATUS current
			DESCRIPTION
				"A unique number for each dcc device in the table.
				
				If this device is also represented in the HOST-RESOURCES-MIB
				hrDeviceTable, then the value of dccDeviceIndex must match hrDeviceIndex
				from HOST-RESOURCES-MIB."
			::= { dccEntry 4 }

		
--  
		-- 1.3.6.1.4.1.1429.5.1.1.2.6.4.4
		scaler OBJECT IDENTIFIER ::= { video 4 }

		
--  
		-- 1.3.6.1.4.1.1429.5.1.1.2.6.4.5
		digitalVideoPort OBJECT IDENTIFIER ::= { video 5 }

		
--  
		-- 1.3.6.1.4.1.1429.5.1.1.2.6.5
		graphics OBJECT IDENTIFIER ::= { saDhctDevice 5 }

		
--  
		-- 1.3.6.1.4.1.1429.5.1.1.2.6.5.1
		plane OBJECT IDENTIFIER ::= { graphics 1 }

		
--  
		-- 1.3.6.1.4.1.1429.5.1.1.2.6.5.2
		layer OBJECT IDENTIFIER ::= { graphics 2 }

		
--  
		-- 1.3.6.1.4.1.1429.5.1.1.2.6.5.3
		bqm OBJECT IDENTIFIER ::= { graphics 3 }

		
--  
		-- 1.3.6.1.4.1.1429.5.1.1.2.6.5.4
		bnm OBJECT IDENTIFIER ::= { graphics 4 }

		
--  
		-- 1.3.6.1.4.1.1429.5.1.1.2.6.6
		hdmi OBJECT IDENTIFIER ::= { saDhctDevice 6 }

		
		-- 1.3.6.1.4.1.1429.5.1.1.2.6.6.1
		hdmiTable OBJECT-TYPE
			SYNTAX SEQUENCE OF HdmiEntry
			MAX-ACCESS not-accessible
			STATUS current
			DESCRIPTION
				"Status and error conditions of high definition multimedia interface devices."
			::= { hdmi 1 }

		
		-- 1.3.6.1.4.1.1429.5.1.1.2.6.6.1.1
		hdmiEntry OBJECT-TYPE
			SYNTAX HdmiEntry
			MAX-ACCESS not-accessible
			STATUS current
			DESCRIPTION
				"A row in the table.
				
				If this device is also represented in the HOST-RESOURCES-MIB
				hrDeviceTable, then the value of hdmiDeviceIndex must match hrDeviceIndex
				from HOST-RESOURCES-MIB."
			INDEX { hdmiDeviceIndex }
			::= { hdmiTable 1 }

		
		HdmiEntry ::=
			SEQUENCE { 
				hdmiConnectionStaus
					INTEGER,
				hdmiFormat480i4By3
					INTEGER,
				hdmiFormat480i16By9
					INTEGER,
				hdmiFormat480p4By3
					INTEGER,
				hdmiFormat480p16By9
					INTEGER,
				hdmiFormat720p
					INTEGER,
				hdmiFormat1080i
					INTEGER,
				hdmiState
					INTEGER,
				hdmiExtensionVersion
					INTEGER,
				hdmiMonitorName
					DisplayString,
				hdmiAudioFormat
					INTEGER,
				hdmiDeviceIndex
					Integer32
			 }

		-- 1.3.6.1.4.1.1429.5.1.1.2.6.6.1.1.1
		hdmiConnectionStaus OBJECT-TYPE
			SYNTAX INTEGER
				{
				notConnected(0),
				connected(1)
				}
			MAX-ACCESS read-only
			STATUS current
			DESCRIPTION
				"Indicates if an HDMI monitor is connected or not."
			::= { hdmiEntry 1 }

		
		-- 1.3.6.1.4.1.1429.5.1.1.2.6.6.1.1.2
		hdmiFormat480i4By3 OBJECT-TYPE
			SYNTAX INTEGER
				{
				noSupport(0),
				implicit(1),
				explicit(2),
				native(3),
				preferred(4)
				}
			MAX-ACCESS read-only
			STATUS current
			DESCRIPTION
				"Level of support for 720 x 480i 4:3 format
				0 - No Support           
				1 - Implicit (doesn't exceed limits)      
				2 - Explicit
				3 - Native (EIA-861B Only)
				4 - Preferred"
			::= { hdmiEntry 2 }

		
		-- 1.3.6.1.4.1.1429.5.1.1.2.6.6.1.1.3
		hdmiFormat480i16By9 OBJECT-TYPE
			SYNTAX INTEGER
				{
				noSupport(0),
				implicit(1),
				explicit(2),
				native(3),
				preferred(4)
				}
			MAX-ACCESS read-only
			STATUS current
			DESCRIPTION
				"Level of support for 720 x 480i 16:9 format
				0 - No Support           
				1 - Implicit (doesn't exceed limits)      
				2 - Explicit
				3 - Native (EIA-861B Only)
				4 - Preferred"
			::= { hdmiEntry 3 }

		
		-- 1.3.6.1.4.1.1429.5.1.1.2.6.6.1.1.4
		hdmiFormat480p4By3 OBJECT-TYPE
			SYNTAX INTEGER
				{
				noSupport(0),
				implicit(1),
				explicit(2),
				native(3),
				preferred(4)
				}
			MAX-ACCESS read-only
			STATUS current
			DESCRIPTION
				"Level of support for 720 x 480p 4:3 format
				0 - No Support           
				1 - Implicit (doesn't exceed limits)      
				2 - Explicit
				3 - Native (EIA-861B Only)
				4 - Preferred"
			::= { hdmiEntry 4 }

		
		-- 1.3.6.1.4.1.1429.5.1.1.2.6.6.1.1.5
		hdmiFormat480p16By9 OBJECT-TYPE
			SYNTAX INTEGER
				{
				noSupport(0),
				implicit(1),
				explicit(2),
				native(3),
				preferred(4)
				}
			MAX-ACCESS read-only
			STATUS current
			DESCRIPTION
				"Level of support for 720 x 480p 16:9 format
				0 - No Support           
				1 - Implicit (doesn't exceed limits)      
				2 - Explicit
				3 - Native (EIA-861B Only)
				4 - Preferred"
			::= { hdmiEntry 5 }

		
		-- 1.3.6.1.4.1.1429.5.1.1.2.6.6.1.1.6
		hdmiFormat720p OBJECT-TYPE
			SYNTAX INTEGER
				{
				noSupport(0),
				implicit(1),
				explicit(2),
				native(3),
				preferred(4)
				}
			MAX-ACCESS read-only
			STATUS current
			DESCRIPTION
				"Level of support for 1280 x 720p format
				0 - No Support           
				1 - Implicit (doesn't exceed limits)      
				2 - Explicit
				3 - Native (EIA-861B Only)
				4 - Preferred"
			::= { hdmiEntry 6 }

		
		-- 1.3.6.1.4.1.1429.5.1.1.2.6.6.1.1.7
		hdmiFormat1080i OBJECT-TYPE
			SYNTAX INTEGER
				{
				noSupport(0),
				implicit(1),
				explicit(2),
				native(3),
				preferred(4)
				}
			MAX-ACCESS read-only
			STATUS current
			DESCRIPTION
				"Level of support for 1920 x 1080i format
				0 - No Support           
				1 - Implicit (doesn't exceed limits)      
				2 - Explicit
				3 - Native (EIA-861B Only)
				4 - Preferred"
			::= { hdmiEntry 7 }

		
		-- 1.3.6.1.4.1.1429.5.1.1.2.6.6.1.1.8
		hdmiState OBJECT-TYPE
			SYNTAX INTEGER
				{
				preInitialized(0),
				initialized(1),
				compatibleMonitorCrnnected(2),
				inCompatibleMonitorCrnnected(3),
				revokedMonitorConnected(4)
				}
			MAX-ACCESS read-only
			STATUS current
			DESCRIPTION
				"State of the DVI port
				0 - Pre-Initialized
				1 - Initialized
				2 - Compatible Monitor connected
				3 - Incompatible Monitor connected
				4 - Revoked Monitor connected"
			::= { hdmiEntry 8 }

		
		-- 1.3.6.1.4.1.1429.5.1.1.2.6.6.1.1.9
		hdmiExtensionVersion OBJECT-TYPE
			SYNTAX INTEGER
				{
				unKnown(0),
				eia861compliantMonitor(1),
				eia861AcompliantMonitor(2),
				eia861BcompliantMonitor(3),
				edidOnlyCompliantMonitor(256)
				}
			MAX-ACCESS read-only
			STATUS current
			DESCRIPTION
				"DTD Extension Revision number:
				0 - Unknown
				1 - EIA-861 compliant monitor
				2 - EIA-861A compliant monitor
				3 - EIA-861B compliant monitor
				256 - EDID-only compliant monitor"
			::= { hdmiEntry 9 }

		
		-- 1.3.6.1.4.1.1429.5.1.1.2.6.6.1.1.10
		hdmiMonitorName OBJECT-TYPE
			SYNTAX DisplayString
			MAX-ACCESS read-only
			STATUS current
			DESCRIPTION
				"The monitor name."
			::= { hdmiEntry 10 }

		
		-- 1.3.6.1.4.1.1429.5.1.1.2.6.6.1.1.11
		hdmiAudioFormat OBJECT-TYPE
			SYNTAX INTEGER
				{
				noAudio(0),
				lpcm(1),
				ac3(2)
				}
			MAX-ACCESS read-only
			STATUS current
			DESCRIPTION
				"Format of audio used in HDMI port 
				0 - No Audio, 
				1 - LPCM(un-compressed), 
				2 - AC3 (compressed)"
			::= { hdmiEntry 11 }

		
		-- 1.3.6.1.4.1.1429.5.1.1.2.6.6.1.1.12
		hdmiDeviceIndex OBJECT-TYPE
			SYNTAX Integer32 (1..2147483647)
			MAX-ACCESS not-accessible
			STATUS current
			DESCRIPTION
				"A unique number for each hdmi device in the table.
				
				If this device is also represented in the HOST-RESOURCES-MIB
				hrDeviceTable, then the value of hdmiDeviceIndex must match hrDeviceIndex
				from HOST-RESOURCES-MIB."
			::= { hdmiEntry 12 }

		
--  
		-- 1.3.6.1.4.1.1429.5.1.1.2.6.7
		hdcp OBJECT IDENTIFIER ::= { saDhctDevice 7 }

		
		-- 1.3.6.1.4.1.1429.5.1.1.2.6.7.1
		hdcpTable OBJECT-TYPE
			SYNTAX SEQUENCE OF HdcpEntry
			MAX-ACCESS not-accessible
			STATUS current
			DESCRIPTION
				"Status and error conditions of HDCP devices."
			::= { hdcp 1 }

		
		-- 1.3.6.1.4.1.1429.5.1.1.2.6.7.1.1
		hdcpEntry OBJECT-TYPE
			SYNTAX HdcpEntry
			MAX-ACCESS not-accessible
			STATUS current
			DESCRIPTION
				"A row in the table.
				
				If this device is also represented in the HOST-RESOURCES-MIB
				hrDeviceTable, then the value of hdcpDeviceIndex must match hrDeviceIndex
				from HOST-RESOURCES-MIB."
			INDEX { hdcpDeviceIndex }
			::= { hdcpTable 1 }

		
		HdcpEntry ::=
			SEQUENCE { 
				hdcpState
					INTEGER,
				hdcpDeviceIndex
					Integer32
			 }

		-- 1.3.6.1.4.1.1429.5.1.1.2.6.7.1.1.1
		hdcpState OBJECT-TYPE
			SYNTAX INTEGER
				{
				preInitialized(0),
				initialized(1),
				keyExchangeInProcess(2),
				incompatible(3),
				authenticated(4)
				}
			MAX-ACCESS read-only
			STATUS current
			DESCRIPTION
				"State of HDCP device:
				0 - Pre-Initialized
				1 - Initialized
				2 - Key Exchange in process
				3 - Incompatible
				4 - Authenticated"
			::= { hdcpEntry 1 }

		
		-- 1.3.6.1.4.1.1429.5.1.1.2.6.7.1.1.2
		hdcpDeviceIndex OBJECT-TYPE
			SYNTAX Integer32 (1..2147483647)
			MAX-ACCESS not-accessible
			STATUS current
			DESCRIPTION
				"A unique number for each hdcp device in the table.
				
				If this device is also represented in the HOST-RESOURCES-MIB
				hrDeviceTable, then the value of hdcpDeviceIndex must match hrDeviceIndex
				from HOST-RESOURCES-MIB."
			::= { hdcpEntry 2 }

		
		-- 1.3.6.1.4.1.1429.5.1.1.2.6.8
		bldr OBJECT IDENTIFIER ::= { saDhctDevice 8 }

		
		-- 1.3.6.1.4.1.1429.5.1.1.2.6.8.1
		bldrTable OBJECT-TYPE
			SYNTAX SEQUENCE OF BldrEntry
			MAX-ACCESS not-accessible
			STATUS current
			DESCRIPTION
				"Status and error conditions of boot loader devices."
			::= { bldr 1 }

		
		-- 1.3.6.1.4.1.1429.5.1.1.2.6.8.1.1
		bldrEntry OBJECT-TYPE
			SYNTAX BldrEntry
			MAX-ACCESS not-accessible
			STATUS current
			DESCRIPTION
				"A row in the table.
				
				If this device is also represented in the HOST-RESOURCES-MIB
				hrDeviceTable, then the value of bldrDeviceIndex must match hrDeviceIndex
				from HOST-RESOURCES-MIB."
			INDEX { bldrDeviceIndex }
			::= { bldrTable 1 }

		
		BldrEntry ::=
			SEQUENCE { 
				bldrVersion
					DisplayString,
				bldrVendorID
					DisplayString,
				bldrHwVersion
					DisplayString,
				bldrSwVersion
					DisplayString,
				bldrHwModel
					DisplayString,
				bldrCompatibilityDesc1
					DisplayString,
				bldrCompatibilityDesc2
					DisplayString,
				bldrCompatibilityDesc3
					DisplayString,
				bldrCompatibilityDesc4
					DisplayString,
				bldrGroupID
					DisplayString,
				bldrCurrentLoadType
					INTEGER,
				bldrConscRecvLdFrNetwork
					Counter32,
				bldrCodeDnLdCounter
					Counter32,
				bldrDnLdSaveCounter
					Counter32,
				bldrDeviceIndex
					Integer32
			 }

		-- 1.3.6.1.4.1.1429.5.1.1.2.6.8.1.1.1
		bldrVersion OBJECT-TYPE
			SYNTAX DisplayString
			MAX-ACCESS read-only
			STATUS current
			DESCRIPTION
				"Boot loader version."
			::= { bldrEntry 1 }

		
		-- 1.3.6.1.4.1.1429.5.1.1.2.6.8.1.1.2
		bldrVendorID OBJECT-TYPE
			SYNTAX DisplayString
			MAX-ACCESS read-only
			STATUS current
			DESCRIPTION
				"Boot loader vendorID"
			::= { bldrEntry 2 }

		
		-- 1.3.6.1.4.1.1429.5.1.1.2.6.8.1.1.3
		bldrHwVersion OBJECT-TYPE
			SYNTAX DisplayString
			MAX-ACCESS read-only
			STATUS current
			DESCRIPTION
				"Boot loader Hardware Version"
			::= { bldrEntry 3 }

		
		-- 1.3.6.1.4.1.1429.5.1.1.2.6.8.1.1.4
		bldrSwVersion OBJECT-TYPE
			SYNTAX DisplayString
			MAX-ACCESS read-only
			STATUS current
			DESCRIPTION
				"Boot loader Software Version"
			::= { bldrEntry 4 }

		
		-- 1.3.6.1.4.1.1429.5.1.1.2.6.8.1.1.5
		bldrHwModel OBJECT-TYPE
			SYNTAX DisplayString
			MAX-ACCESS read-only
			STATUS current
			DESCRIPTION
				"Boot loader Hardware Model Version"
			::= { bldrEntry 5 }

		
		-- 1.3.6.1.4.1.1429.5.1.1.2.6.8.1.1.6
		bldrCompatibilityDesc1 OBJECT-TYPE
			SYNTAX DisplayString
			MAX-ACCESS read-only
			STATUS current
			DESCRIPTION
				"Boot loader Compatibility Description 1"
			::= { bldrEntry 6 }

		
		-- 1.3.6.1.4.1.1429.5.1.1.2.6.8.1.1.7
		bldrCompatibilityDesc2 OBJECT-TYPE
			SYNTAX DisplayString
			MAX-ACCESS read-only
			STATUS current
			DESCRIPTION
				"Boot loader Compatibility Description 2"
			::= { bldrEntry 7 }

		
		-- 1.3.6.1.4.1.1429.5.1.1.2.6.8.1.1.8
		bldrCompatibilityDesc3 OBJECT-TYPE
			SYNTAX DisplayString
			MAX-ACCESS read-only
			STATUS current
			DESCRIPTION
				"Boot loader Compatibility Description 3"
			::= { bldrEntry 8 }

		
		-- 1.3.6.1.4.1.1429.5.1.1.2.6.8.1.1.9
		bldrCompatibilityDesc4 OBJECT-TYPE
			SYNTAX DisplayString
			MAX-ACCESS read-only
			STATUS current
			DESCRIPTION
				"Boot loader Compatibility Description 4"
			::= { bldrEntry 9 }

		
		-- 1.3.6.1.4.1.1429.5.1.1.2.6.8.1.1.10
		bldrGroupID OBJECT-TYPE
			SYNTAX DisplayString
			MAX-ACCESS read-only
			STATUS current
			DESCRIPTION
				"Boot loader Group ID"
			::= { bldrEntry 10 }

		
		-- 1.3.6.1.4.1.1429.5.1.1.2.6.8.1.1.11
		bldrCurrentLoadType OBJECT-TYPE
			SYNTAX INTEGER
				{
				normalLoad(0),
				firstLoadNewCode(1),
				firstLoadCorrupt(2),
				bootAfterLoad(3)
				}
			MAX-ACCESS read-only
			STATUS current
			DESCRIPTION
				"Current Load Type, 
				0 - Normal load from disk, 
				1 - first load after saving new code to disk due to upgrade request, 
				2 - As above, but as result of disk corruption recovery, 
				3 - boot after loading code from network."
			::= { bldrEntry 11 }

		
		-- 1.3.6.1.4.1.1429.5.1.1.2.6.8.1.1.12
		bldrConscRecvLdFrNetwork OBJECT-TYPE
			SYNTAX Counter32
			MAX-ACCESS read-only
			STATUS current
			DESCRIPTION
				"Consecutive recovery loads from network - 
				Counts how many times in the row box booted loading code 
				from network (not from disk). 
				Non-zero only if LSByte is 3 (type load from network), 
				reset on first boot other than type 3."
			::= { bldrEntry 12 }

		
		-- 1.3.6.1.4.1.1429.5.1.1.2.6.8.1.1.13
		bldrCodeDnLdCounter OBJECT-TYPE
			SYNTAX Counter32
			MAX-ACCESS read-only
			STATUS current
			DESCRIPTION
				"Code downloadCounter. 
				Updated on every code load from the network."
			::= { bldrEntry 13 }

		
		-- 1.3.6.1.4.1.1429.5.1.1.2.6.8.1.1.14
		bldrDnLdSaveCounter OBJECT-TYPE
			SYNTAX Counter32
			MAX-ACCESS read-only
			STATUS current
			DESCRIPTION
				"Download and Save Counter. 
				Updated on every disk save of downloaded code."
			::= { bldrEntry 14 }

		
		-- 1.3.6.1.4.1.1429.5.1.1.2.6.8.1.1.15
		bldrDeviceIndex OBJECT-TYPE
			SYNTAX Integer32 (1..2147483647)
			MAX-ACCESS not-accessible
			STATUS current
			DESCRIPTION
				"A unique number for each bldr device in the table.
				
				If this device is also represented in the HOST-RESOURCES-MIB
				hrDeviceTable, then the value of bldrDeviceIndex must match hrDeviceIndex
				from HOST-RESOURCES-MIB."
			::= { bldrEntry 15 }

		
		-- 1.3.6.1.4.1.1429.5.1.1.2.6.9
		saDhctUhfMod OBJECT IDENTIFIER ::= { saDhctDevice 9 }

		
		-- 1.3.6.1.4.1.1429.5.1.1.2.6.9.1
		saDhctDevUhfModTable OBJECT-TYPE
			SYNTAX SEQUENCE OF SaDhctDevUhfModEntry
			MAX-ACCESS not-accessible
			STATUS current
			DESCRIPTION
				"Status and configuration of UHF Modulator Devices."
			::= { saDhctUhfMod 1 }

		
		-- 1.3.6.1.4.1.1429.5.1.1.2.6.9.1.1
		saDhctDevUhfModEntry OBJECT-TYPE
			SYNTAX SaDhctDevUhfModEntry
			MAX-ACCESS not-accessible
			STATUS current
			DESCRIPTION
				"A row in the table.
				
				If the device is also represented in the HOST-RESOURCES-MIBhrDeviceTable, 
				then the value of saDhctDevUhfModDeviceIndex must match hrDeviceIndex
				from HOST-RESOURCES-MIB.
				"
			INDEX { saDhctDevUhfModDeviceIndex }
			::= { saDhctDevUhfModTable 1 }

		
		SaDhctDevUhfModEntry ::=
			SEQUENCE { 
				saDhctDevUhfModDeviceIndex
					Integer32,
				saDhctDevUhfModHiLoAttenuation
					INTEGER,
				saDhctDevUhfModChannel
					Integer32,
				saDhctDevUhfModVisionCarrier
					Integer32
			 }

		-- 1.3.6.1.4.1.1429.5.1.1.2.6.9.1.1.1
		saDhctDevUhfModDeviceIndex OBJECT-TYPE
			SYNTAX Integer32 (1..2147483647)
			MAX-ACCESS not-accessible
			STATUS current
			DESCRIPTION
				"A unique number for each UhfMod device in the table.
				If this device is also represented in the HOST-RESOURCES-MIB hrDeviceTable, 
				then the value of saDhctDevUhfModDeviceIndex must match hrDeviceIndex
				from HOST-RESOURCES-MIB.
				"
			::= { saDhctDevUhfModEntry 1 }

		
		-- 1.3.6.1.4.1.1429.5.1.1.2.6.9.1.1.2
		saDhctDevUhfModHiLoAttenuation OBJECT-TYPE
			SYNTAX INTEGER
				{
				na(1),
				high(2),
				low(3)
				}
			MAX-ACCESS read-only
			STATUS current
			DESCRIPTION
				"Attenuation."
			::= { saDhctDevUhfModEntry 2 }

		
		-- 1.3.6.1.4.1.1429.5.1.1.2.6.9.1.1.3
		saDhctDevUhfModChannel OBJECT-TYPE
			SYNTAX Integer32
			MAX-ACCESS read-only
			STATUS current
			DESCRIPTION
				"Channel Number"
			::= { saDhctDevUhfModEntry 3 }

		
		-- 1.3.6.1.4.1.1429.5.1.1.2.6.9.1.1.4
		saDhctDevUhfModVisionCarrier OBJECT-TYPE
			SYNTAX Integer32
			UNITS "Hertz"
			MAX-ACCESS read-only
			STATUS current
			DESCRIPTION
				"Vision Carrier"
			::= { saDhctDevUhfModEntry 4 }

		
		-- 1.3.6.1.4.1.1429.5.1.1.3
		saDhctEvents OBJECT-IDENTITY
			STATUS current
			DESCRIPTION 
				"Events associated with DHCTs."
			::= { saDhctMib 3 }

		
		-- 1.3.6.1.4.1.1429.5.1.1.3.0
		saDhctEventsV2 OBJECT-IDENTITY
			STATUS current
			DESCRIPTION 
				"Dummy node under which all events must be defined. This is
				required for SNMP v1/v2 compatability."
			::= { saDhctEvents 0 }

		
	
	END

--
-- SA-DHCT-MIB.mib
--
