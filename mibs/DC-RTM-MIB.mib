DC-RTM-MIB DEFINITIONS ::= BEGIN

  -- PRODUCT-SHORT-NAME rtm

  IMPORTS
      MODULE-IDENTITY,
      OBJECT-TYPE,
      Integer32,
      Unsigned32,
      IpAddress
                                        FROM SNMPv2-SMI

   MODULE-COMPLIANCE, OBJECT-GROUP
      FROM SNMPv2-CONF

      TEXTUAL-CONVENTION,
      RowStatus,
      TruthValue
                                        FROM SNMPv2-TC

      IANAipRouteProtocol               FROM IANA-RTPROTO-MIB

      InetAddressType,
      InetAddress
                                        FROM INET-ADDRESS-MIB

      AdminStatus,
      OperStatus
                                        FROM DC-MASTER-TC;

  rtmMib MODULE-IDENTITY
      LAST-UPDATED "200905270000Z" -- Wed May 27 00:00:00 GMT 2009
      ORGANIZATION "Data Connection Ltd."
      CONTACT-INFO
                   "Postal: Data Connection Ltd.
                            100 Church Street
                            Enfield
                            Middlesex EN2 6BQ
                            United Kingdom
                    Tel:    +44 20 83661177
                    E-mail: dcospf@dataconnection.com"
      DESCRIPTION  "The MIB module for management of the DC-RTM
                    product."
                    
    REVISION      "200905270000Z"
    DESCRIPTION
            "Change rtmEntityRouteNumber to read-only for defect 143640."

  ::= { iso member-body(2) gb(826) national(0) eng-ltd(1)
        dataConnectionLtd(1578918) adg(5) cipr(61) 1 }

  rtmObjects OBJECT IDENTIFIER ::= { rtmMib 1 } -- tables

-- Textual conventions

  FteIndex ::= TEXTUAL-CONVENTION
      STATUS      current
      DESCRIPTION "The index value identifying a fault tolerant entity."
      SYNTAX      Unsigned32

  OspfTag ::= TEXTUAL-CONVENTION
      STATUS      current
      DESCRIPTION "An OSPF Tag."
      SYNTAX      Unsigned32 (0..'FFFFFFFF'h)

  MjStatus ::= TEXTUAL-CONVENTION
      STATUS      current
      DESCRIPTION "The status of a master join."
      SYNTAX     INTEGER {
                  mjNotJoined(1),        -- initial state of join
                  mjSentAddJoin(2),      -- sent ATG_FT_ADD_JOIN to slave
                  mjSentRegister(3),     -- sent registration signal to slave
                  mjJoinActive(4),       -- join is active
                  mjSentDelJoin(5),      -- sent ATG_FT_DELETE_JOIN to slave
                  mjSentUnregister(6),   -- sent unregistration signal to slave
                  mjJoinGone(7),         -- join has been deleted
                  mjFailedToRegister(8), -- slave rejected registration message
                  mjFailingOver(9),      -- slave is failing over
                  mjFailed(10)           -- join has permanently failed
                }

  SjStatus ::= TEXTUAL-CONVENTION
      STATUS      current
      DESCRIPTION "The status of a slave join."
      SYNTAX     INTEGER {
                  sjNotJoined(1),        -- initial state of join
                  sjJoined(2),           -- master has sent an ATG_FT_ADD_JOIN
                  sjJoinActive(3),       -- master has registered the join
                  sjJoinUnreg(4),        -- master has unregistered the join
                  sjJoinGone(5),         -- master has deleted the join
                  sjFailingOver(6),      -- master is failing over
                  sjFailed(7)            -- join has permanently failed
                }

  InterfaceType ::= TEXTUAL-CONVENTION
      STATUS      current
      DESCRIPTION "The type of interface to which a join applies."
      SYNTAX     INTEGER {
                  ifActiveRoutes(1),       -- Active Routes
                  ifRteProtInput(2)        -- Routing Protocol Input
                }

  AriPrtnrType ::= TEXTUAL-CONVENTION
      STATUS      current
      DESCRIPTION "The type of slave partner to join to over the Active
                   Routes Interface."
      SYNTAX      INTEGER {
                  ariPrtnrFt(1),    -- Forwarding Table Stub
                  ariPrtnrLdf(2),   -- Labelled Data Forwarding Table Stub
                  ariPrtnrRsm(3),   -- Route Selection Manager
                  ariPrtnrBgp(4),   -- BGP Protocol Manager
                  ariPrtnrPim(5)    -- PIM Protocol Manager
                }

  RdstSetFieldType ::= TEXTUAL-CONVENTION
      STATUS      current
      DESCRIPTION "The type of action a Set Field entry performs."
      SYNTAX      INTEGER {
                  rdstSetBgpComm(1),    -- Set BGP Community
                  rdstSetBgpExtComm(2)  -- Set BGP Extended Community
                }

  AdminDistance ::= TEXTUAL-CONVENTION
      STATUS       current
      DESCRIPTION
           "The adminstrative distance used in prioritizing routes from
           different sources when selecting active routes in DC-RTM.
           The active route is chosen from those available routes which
           have the lowest associated administrative distance."
      SYNTAX       Integer32 (0..255)

  CostMetric ::= TEXTUAL-CONVENTION
      STATUS       current
      DESCRIPTION
           "The cost metric used in prioritizing routes when selecting
	   active routes in DC-RTM. The active route is chosen from those
	   available routes which have the lowest associated cost metric."
      SYNTAX       Integer32 (0..255)

  EqualCostRouteOpts ::= TEXTUAL-CONVENTION
      STATUS      current
      DESCRIPTION
           "The method used to determine how to choose which equal cost
           routes for a given destination to give to the active routing
           information consumers, if there is more than one route.  This value
           is used in building responses to ATG_QCAR_GET_ROUTES and
           ATG_QCAR_QUERY_ROUTE signals, and also in building
           ATG_QCAR_ROUTE_UPDATE and ATG_QCAR_ROUTE_IND signals for consumers
           that require them.

           The permitted values for this field are as follows.

           all:
             All equal cost routes should be given to the active routing
             information consumers.

           one:
             DC-RTM picks one as soon as it can, and only tells the active
             routing information consumers about that one route.
             It only switches to another route if the chosen one is deleted,
             or if the chosen one no longer has the lowest administrative
             distance among routes to this destination (for example if a new
             route is added with a lower adminstrative distance)."
      SYNTAX     INTEGER {
                  equalCostAll(1),  -- all routes
                  equalCostOne(2)   -- one route
                }

  MetricConversion ::= TEXTUAL-CONVENTION
      STATUS      current
      DESCRIPTION
           "How to convert the metric in the source routing information to
           a new metric in the destination routing information.

           Possible actions are

           same:
             Use the supplied metric value

           constant:
             Ignore the supplied metric and use the constant value given in
             the metric numeric parameter field

           inverse:
             Map high values onto low ones, and vice-versa, by subtracting the
             supplied metric from 0xffffffff.

           scale up:
             Use the supplied metric multiplied by the value given in the
             metric numeric parameter field, or 0xffffffff if this is smaller.

           scale down:
             Use the supplied metric divided by the value given in the metric
             numeric parameter field (which must not be zero), rounding down
             to the next whole number.

           truncate:
             Use the smaller of the supplied metric or the metric numeric
             parameter field."
      SYNTAX     INTEGER {
                  metricConvSame(1),      -- same
                  metricConvConstant(2),  -- constant
                  metricConvInverse(3),   -- inverse
                  metricConvScaleUp(4),   -- scale up
                  metricConvScaleDown(5), -- scale down
                  metricConvTruncate(6)   -- truncate
                }

  InfoSourceDest ::= TEXTUAL-CONVENTION
      STATUS      current
      DESCRIPTION
           "A source of, or destination for, routing information.  These
           values are used when redistributing routing information."
      SYNTAX     INTEGER {
                  infoSourceAll(0),            -- all values
                  infoSourceOther(65536),      -- not specified
                  infoSourceConnected(131072), -- directly connected network
                  infoSourceStatic(196608),    -- static route
                  infoSourceIcmp(262144),      -- ICMP redirect
                  infoSourceEgp(327680),       -- Exterior Gateway Protocol
                  infoSourceGgp(393216),       -- Gateway-Gateway Protocol
                  infoSourceHello(458752),     -- FuzzBall HelloSpeak
                  infoSourceRip(524288),       -- RIP
                  infoSourceIsis(589824),      -- IS-IS
                  infoSourceEsis(655360),      -- ISO 9542
                  infoSourceIgrp(720896),      -- IGRP
                  infoSourceBbnSpfIgp(786432), -- BBN SPF IGP
                  infoSourceOspf(851968),      -- OSPF
                  infoSourceBgp(917504),       -- BGP
                  infoSourceIdpr(983040),      -- InterDomain Policy Routing
                  infoSourceEigrp(1048576),    -- EIGRP
                  infoSourceDvmrp(1114112),    -- DVMRP
                  infoSourceDdrp(1179648)      -- DDRP
                }

  RouteAction ::= TEXTUAL-CONVENTION
      STATUS       current
      DESCRIPTION
           "Action to perform on receipt of a packet which matches the
           destination for a static route.  This is one of:

           -  forward the packet to the address specified as the
              next-hop address

           -  handle the packet locally

           -  reject [drop and send ICMP]

           -  discard [drop but do not send ICMP]

           - forward the packet using a tunnel."
      SYNTAX     INTEGER {
                  routeActionLocal(1),
                  routeActionForward(2),
                  routeActionReject(3),
                  routeActionDiscard(4),
                  routeActionTunnel(5)
                }

  PathType ::= TEXTUAL-CONVENTION
      STATUS       current
      DESCRIPTION "Protocol-specific path type."
      SYNTAX     INTEGER {
                  pathTypeNone(0),                 -- None
                  pathTypeOther(65536),            -- Other
                  pathTypeConnected(131072),       -- Connected
                  pathTypeStatic(196608),          -- Static
                  pathTypeIcmp(262144),            -- ICMP
                  pathTypeEgp(327680),             -- Exterior Gateway Protocol
                  pathTypeGgp(393216),             -- GGP
                  pathTypeHello(458752),           -- FuzzBall HelloSpeak
                  pathTypeRip(524288),             -- RIP route
                  pathTypeIsisLevel1Int(589824),   -- IS-IS internal level 1
                  pathTypeIsisLevel2Int(589825),   -- IS-IS internal level 2
                  pathTypeIsisLevel1Ext(589826),   -- IS-IS external level 1
                  pathTypeIsisLevel2Ext(589827),   -- IS-IS external level 2
                  pathTypeEsis(655360),            -- ESIS route
                  pathTypeIgrp(720896),            -- IGRP route
                  pathTypeBbnspfigp(786432),       -- BBNSPFIGP route
                  pathTypeOspfIntraArea(851968),   -- OSPF Intra-area route
                  pathTypeOspfInterArea(851969),   -- OSPF Inter-area route
                  pathTypeOspfType1Ext(851970),    -- OSPF exterior type 1
                  pathTypeOspfType2Ext(851971),    -- OSPF exterior type 2
                  pathTypeBgpInt(917504),          -- BGP Internal
                  pathTypeBgpExt(917505),          -- BGP External
                  pathTypeBgpVpn(917506),          -- BGP VPN route
                  pathTypeIdpr(983040),            -- IDPR route
                  pathTypeEigrp(1048576),          -- EIGRP summary route
                  pathTypeEigrpInt(1048577),       -- EIGRP internal route
                  pathTypeEigrpExt(1048578),       -- EIGRP external route
                  pathTypeDvmrp(1114112)           -- DVMRP route
               }

  BgpOriginCode ::= TEXTUAL-CONVENTION
      STATUS      current
      DESCRIPTION "A BGP origin code."
      SYNTAX     INTEGER {
                bgpOriginIgp(0),        -- path interior to originating AS
                bgpOriginEgp(1),        -- path learned via EGP protocol
                bgpOriginIncomplete(2)  -- path was learned by some other means
              }

  BgpCommunity ::= TEXTUAL-CONVENTION
    STATUS       current
    DESCRIPTION "The representation of a BGP Community."
    SYNTAX OCTET STRING (SIZE(4))

  BgpExtendedCommunity ::= TEXTUAL-CONVENTION
    STATUS       current
    DESCRIPTION "The representation of a BGP Extended Community."
    SYNTAX OCTET STRING (SIZE(8))

  RouteInfo ::= TEXTUAL-CONVENTION
      STATUS      current
      DESCRIPTION "A Routing Protocol Information Type.  This is an integer
                   representation of the OID which is required by RFC 2096.
                   The RFCs which define the OIDs, and the represented OIDs,
                   are show here.
                     OSPF - RFC 1850."
      SYNTAX     INTEGER {
                none(0),
                ospfIntraArea(1),       -- { ospfRouteGroup 1 }
                ospfInterArea(2),       -- { ospfRouteGroup 2 }
                ospfExternalType1(3),   -- { ospfRouteGroup 3 }
                ospfExternalType2(4)    -- { ospfRouteGroup 4 }
              }

  RouteType ::= TEXTUAL-CONVENTION
      STATUS      current
      DESCRIPTION "Routing Type."
      SYNTAX     INTEGER {
                other(1),               -- not specified by this MIB
                reject(2),              -- route which discards traffic
                local(3),               -- local interface
                remote(4)               -- remote destination
              }

-------------------------------------------------------------------------------

-- DC-RTM Entity Table
-- This table is used to create and manage DC-RTM entities.

  rtmEntityTable OBJECT-TYPE
  -- FAMILY-SHORT-NAME qcr_ent
       SYNTAX      SEQUENCE OF RtmEntityEntry
       MAX-ACCESS  not-accessible
       STATUS      current
       DESCRIPTION
          "The table of DC-RTM entities."
       ::= { rtmObjects 1 }

  rtmEntityEntry OBJECT-TYPE
       SYNTAX      RtmEntityEntry
       MAX-ACCESS  not-accessible
       STATUS      current
       DESCRIPTION
          "Each entry represents an instance of the DC-RTM entity."
       INDEX { rtmEntityFteIndex }
       ::= { rtmEntityTable 1 }

  RtmEntityEntry ::= SEQUENCE {
         rtmEntityFteIndex      FteIndex,
         rtmEntityRowStatus     RowStatus,
         rtmEntityAdminStat     AdminStatus,
         rtmEntityOperStatus    OperStatus,
         rtmEntityDsConnctd     AdminDistance,
         rtmEntityDsStatDf      AdminDistance,
         rtmEntityDsOspfInt     AdminDistance,
         rtmEntityDsOspfExt     AdminDistance,
         rtmEntityDsIntBgp      AdminDistance,
         rtmEntityDsExtBgp      AdminDistance,
         rtmEntityDsIsisInt1    AdminDistance,
         rtmEntityDsIsisInt2    AdminDistance,
         rtmEntityDsIsisExt1    AdminDistance,
         rtmEntityDsIsisExt2    AdminDistance,
         rtmEntityDsRip         AdminDistance,
         rtmEntityDsEgp         AdminDistance,
         rtmEntityDsGgp         AdminDistance,
         rtmEntityDsHello       AdminDistance,
         rtmEntityDsEsis        AdminDistance,
         rtmEntityDsBbnspfigp   AdminDistance,
         rtmEntityDsIdpr        AdminDistance,
         rtmEntityDsIgrp        AdminDistance,
         rtmEntityDsEigrpSmm    AdminDistance,
         rtmEntityDsIntEigrp    AdminDistance,
         rtmEntityDsEigrpExt    AdminDistance,
         rtmEntityDsUnknown     AdminDistance,
         rtmEntityEqlCostOpt    EqualCostRouteOpts,
         rtmEntityDelDeadRte    TruthValue,
         rtmEntityDeadRpmTmr    Integer32,
         rtmEntityRouteNumber   Integer32,
         rtmEntityAddressFamily InetAddressType,
         rtmEntityDsDvmrp       AdminDistance
       }

  rtmEntityFteIndex OBJECT-TYPE
       SYNTAX       FteIndex
       MAX-ACCESS   not-accessible
       STATUS       current
       DESCRIPTION
          "The index of this rtmEntityEntry.  This is the HAF entity index
          passed on the entity create parameters."
       ::= { rtmEntityEntry 1 }

  rtmEntityRowStatus OBJECT-TYPE
       SYNTAX       RowStatus
       MAX-ACCESS   read-create
       STATUS       current
       DESCRIPTION
          "Used to create and delete a DC-RTM fault tolerant entity."
       ::= { rtmEntityEntry 2 }

  rtmEntityAdminStat OBJECT-TYPE
       SYNTAX       AdminStatus
       MAX-ACCESS   read-create
       STATUS       current
       DESCRIPTION
          "The desired administrative state of the DC-RTM entity."
       DEFVAL { adminStatusDown }
       ::= { rtmEntityEntry 3 }

  rtmEntityOperStatus OBJECT-TYPE
       SYNTAX       OperStatus
       MAX-ACCESS   read-only
       STATUS       current
       DESCRIPTION
          "The current operational state of the DC-RTM entity."
       ::= { rtmEntityEntry 4 }

  rtmEntityDsConnctd OBJECT-TYPE
       SYNTAX       AdminDistance
       MAX-ACCESS   read-create
       STATUS       current
       DESCRIPTION
          "The administrative distance used for directly connected
           routes.  The lower the distance for a given type of route,
           the more likely a route of this type is to be used by DC-RTM
           as the active route for the given destination."
       DEFVAL { 0 }
       ::= { rtmEntityEntry 5 }

  rtmEntityDsStatDf OBJECT-TYPE
       SYNTAX       AdminDistance
       MAX-ACCESS   read-create
       STATUS       current
       DESCRIPTION
          "The default administrative distance used for statically
           defined routes in the static routes MIB table.  It can be
           overridden for individual static routes.  The lower the
           distance for a given route, the more likely that route is to
           be used by DC-RTM as the active route for the given
           destination."
       DEFVAL { 1 }
       ::= { rtmEntityEntry 6 }

  rtmEntityDsOspfInt OBJECT-TYPE
       SYNTAX       AdminDistance
       MAX-ACCESS   read-create
       STATUS       current
       DESCRIPTION
          "The administrative distance used for OSPF internal routes.
           The lower the distance for a given type of route,
           the more likely a route of this type is to be used by DC-RTM
           as the active route for the given destination."
       DEFVAL { 30 }
       ::= { rtmEntityEntry 7 }

  rtmEntityDsOspfExt OBJECT-TYPE
       SYNTAX       AdminDistance
       MAX-ACCESS   read-create
       STATUS       current
       DESCRIPTION
          "The administrative distance used for OSPF Autonomous System
           external routes.  The lower the distance for a given type of route,
           the more likely a route of this type is to be used by DC-RTM
           as the active route for the given destination."
       DEFVAL { 110 }
       ::= { rtmEntityEntry 8 }

  rtmEntityDsIntBgp OBJECT-TYPE
       SYNTAX       AdminDistance
       MAX-ACCESS   read-create
       STATUS       current
       DESCRIPTION
          "The administrative distance used for internal BGP routes.
           The lower the distance for a given type of route,
           the more likely a route of this type is to be used by DC-RTM
           as the active route for the given destination."
       DEFVAL { 200 }
       ::= { rtmEntityEntry 9 }

  rtmEntityDsExtBgp OBJECT-TYPE
       SYNTAX       AdminDistance
       MAX-ACCESS   read-create
       STATUS       current
       DESCRIPTION
          "The administrative distance used for external BGP routes.
           The lower the distance for a given type of route,
           the more likely a route of this type is to be used by DC-RTM
           as the active route for the given destination."
       DEFVAL { 20 }
       ::= { rtmEntityEntry 10 }

  rtmEntityDsIsisInt1 OBJECT-TYPE
       SYNTAX       AdminDistance
       MAX-ACCESS   read-create
       STATUS       current
       DESCRIPTION
          "The administrative distance used for IS-IS level 1 internal routes.
           The lower the distance for a given type of route,
           the more likely a route of this type is to be used by DC-RTM
           as the active route for the given destination."
       DEFVAL { 115 }
       ::= { rtmEntityEntry 11 }

  rtmEntityDsIsisInt2 OBJECT-TYPE
       SYNTAX       AdminDistance
       MAX-ACCESS   read-create
       STATUS       current
       DESCRIPTION
          "The administrative distance used for IS-IS level 2 internal routes.
           The lower the distance for a given type of route,
           the more likely a route of this type is to be used by DC-RTM
           as the active route for the given destination."
       DEFVAL { 116 }
       ::= { rtmEntityEntry 12 }

  rtmEntityDsIsisExt1 OBJECT-TYPE
       SYNTAX       AdminDistance
       MAX-ACCESS   read-create
       STATUS       current
       DESCRIPTION
          "The administrative distance used for IS-IS level 1 external routes.
           The lower the distance for a given type of route,
           the more likely a route of this type is to be used by DC-RTM
           as the active route for the given destination."
       DEFVAL { 117 }
       ::= { rtmEntityEntry 13 }

  rtmEntityDsIsisExt2 OBJECT-TYPE
       SYNTAX       AdminDistance
       MAX-ACCESS   read-create
       STATUS       current
       DESCRIPTION
          "The administrative distance used for IS-IS level 2 external routes.
           The lower the distance for a given type of route,
           the more likely a route of this type is to be used by DC-RTM
           as the active route for the given destination."
       DEFVAL { 118 }
       ::= { rtmEntityEntry 14 }

  rtmEntityDsRip OBJECT-TYPE
       SYNTAX       AdminDistance
       MAX-ACCESS   read-create
       STATUS       current
       DESCRIPTION
          "The administrative distance used for RIP routes.
           The lower the distance for a given type of route,
           the more likely a route of this type is to be used by DC-RTM
           as the active route for the given destination."
       DEFVAL { 120 }
       ::= { rtmEntityEntry 15 }

  rtmEntityDsEgp OBJECT-TYPE
       SYNTAX       AdminDistance
       MAX-ACCESS   read-create
       STATUS       current
       DESCRIPTION
          "The administrative distance used for Exterior Gateway Protocol
           routes.  The lower the distance for a given type of route,
           the more likely a route of this type is to be used by DC-RTM
           as the active route for the given destination."
       DEFVAL { 205 }
       ::= { rtmEntityEntry 16 }

  rtmEntityDsGgp OBJECT-TYPE
       SYNTAX       AdminDistance
       MAX-ACCESS   read-create
       STATUS       current
       DESCRIPTION
          "The administrative distance used for Gateway-Gateway Protocol
           routes.  The lower the distance for a given type of route,
           the more likely a route of this type is to be used by DC-RTM
           as the active route for the given destination."
       DEFVAL { 210 }
       ::= { rtmEntityEntry 17 }

  rtmEntityDsHello OBJECT-TYPE
       SYNTAX       AdminDistance
       MAX-ACCESS   read-create
       STATUS       current
       DESCRIPTION
          "The administrative distance used for FuzzBall HelloSpeak routes.
           The lower the distance for a given type of route,
           the more likely a route of this type is to be used by DC-RTM
           as the active route for the given destination."
       DEFVAL { 215 }
       ::= { rtmEntityEntry 18 }

  rtmEntityDsEsis OBJECT-TYPE
       SYNTAX       AdminDistance
       MAX-ACCESS   read-create
       STATUS       current
       DESCRIPTION
          "The administrative distance used for ISO 9542 routes.
           The lower the distance for a given type of route,
           the more likely a route of this type is to be used by DC-RTM
           as the active route for the given destination."
       DEFVAL { 225 }
       ::= { rtmEntityEntry 19 }

  rtmEntityDsBbnspfigp OBJECT-TYPE
       SYNTAX       AdminDistance
       MAX-ACCESS   read-create
       STATUS       current
       DESCRIPTION
          "The administrative distance used for BBN SPF IGP routes.
           The lower the distance for a given type of route,
           the more likely a route of this type is to be used by DC-RTM
           as the active route for the given destination."
       DEFVAL { 225 }
       ::= { rtmEntityEntry 20 }

  rtmEntityDsIdpr OBJECT-TYPE
       SYNTAX       AdminDistance
       MAX-ACCESS   read-create
       STATUS       current
       DESCRIPTION
          "The administrative distance used for InterDomain Policy Routing
           routes.  The lower the distance for a given type of route,
           the more likely a route of this type is to be used by DC-RTM
           as the active route for the given destination."
       DEFVAL { 225 }
       ::= { rtmEntityEntry 21 }

  rtmEntityDsIgrp OBJECT-TYPE
       SYNTAX       AdminDistance
       MAX-ACCESS   read-create
       STATUS       current
       DESCRIPTION
          "The administrative distance used for IGRP routes.
           The lower the distance for a given type of route,
           the more likely a route of this type is to be used by DC-RTM
           as the active route for the given destination."
       DEFVAL { 100 }
       ::= { rtmEntityEntry 22 }

  rtmEntityDsEigrpSmm OBJECT-TYPE
       SYNTAX       AdminDistance
       MAX-ACCESS   read-create
       STATUS       current
       DESCRIPTION
          "The administrative distance used for enhanced IGRP summary routes.
           The lower the distance for a given type of route,
           the more likely a route of this type is to be used by DC-RTM
           as the active route for the given destination."
       DEFVAL { 5 }
       ::= { rtmEntityEntry 23 }

  rtmEntityDsIntEigrp OBJECT-TYPE
       SYNTAX       AdminDistance
       MAX-ACCESS   read-create
       STATUS       current
       DESCRIPTION
          "The administrative distance used for internal enhanced IGRP routes.
           The lower the distance for a given type of route,
           the more likely a route of this type is to be used by DC-RTM
           as the active route for the given destination."
       DEFVAL { 90 }
       ::= { rtmEntityEntry 24 }

  rtmEntityDsEigrpExt OBJECT-TYPE
       SYNTAX       AdminDistance
       MAX-ACCESS   read-create
       STATUS       current
       DESCRIPTION
          "The administrative distance used for enhanced IGRP external routes.
           The lower the distance for a given type of route,
           the more likely a route of this type is to be used by DC-RTM
           as the active route for the given destination."
       DEFVAL { 170 }
       ::= { rtmEntityEntry 25 }

  rtmEntityDsUnknown OBJECT-TYPE
       SYNTAX       AdminDistance
       MAX-ACCESS   read-create
       STATUS       current
       DESCRIPTION
          "The administrative distance used for routes which come from
           an unrecognized routing protocol.  The lower the distance for a
           given type of route, the more likely a route of this type is to
           be used by DC-RTM as the active route for the given destination."
       DEFVAL { 255 }
       ::= { rtmEntityEntry 26 }

  rtmEntityEqlCostOpt OBJECT-TYPE
       SYNTAX       EqualCostRouteOpts
       MAX-ACCESS   read-create
       STATUS       current
       DESCRIPTION
          "How to select which equal cost routes to give to a active
           routing information consumer, if there is more than one
           route to a given destination with the lowest administrative
           distance.  This parameter is used in building responses to
           ATG_QCAR_GET_ROUTES and ATG_QCAR_QUERY_ROUTE signals, and
           also in building ATG_QCAR_ROUTE_UPDATE and
           ATG_QCAR_ROUTE_IND signals for consumers that require them."
       DEFVAL       { equalCostAll }
       ::= { rtmEntityEntry 27 }

  rtmEntityDelDeadRte OBJECT-TYPE
       SYNTAX       TruthValue
       MAX-ACCESS   read-create
       STATUS       current
       DESCRIPTION
           "Whether to delete routes from a Routing Protocol Manager (RPM)
           whose join to DC-RTM goes down.  If this is set to TRUE then the
           routes are deleted after the time specified in the 'dead RPM timer'
           parameter.

           If the join between an RPM and DC-RTM goes down, typically because
           the RPM is no longer running, then the routes received from that
           RPM gradually become out of date.  This parameter allows DC-RTM to
           continue to use these routes regardless of whether the RPM ever
           restarts, or to stop using them after a period of time.  This
           period of time should represent the maximum amount of time for
           which the RPM would be down if this were only a temporary state
           of affairs."
       DEFVAL       { true }
       ::= { rtmEntityEntry 28 }

  rtmEntityDeadRpmTmr OBJECT-TYPE
       SYNTAX       Integer32
       MAX-ACCESS   read-create
       STATUS       current
       DESCRIPTION
           "Only defined if the option is set to TRUE to delete routes from an
           RPM which DC-RTM can no longer see.  This field defines
           the period of time that the join to an RPM can be down before its
           routes are deleted.  This period of time should represent the
           maximum amount of time for which the RPM would be down if this were
           only a temporary state of affairs.

           The units for this field are minutes by default."

       DEFVAL { 0 }
       ::= { rtmEntityEntry 29 }

  rtmEntityRouteNumber OBJECT-TYPE
       SYNTAX       Integer32
       MAX-ACCESS   read-only
       STATUS       current
       DESCRIPTION
           "The number of current rtmRouteTable entries
           that are not invalid.  This is the RTM support for RFC 2096
           defined ipCidrRouteNumber."
       DEFVAL { 0 }
       ::= { rtmEntityEntry 30 }

  rtmEntityAddressFamily OBJECT-TYPE
       SYNTAX       InetAddressType
       MAX-ACCESS   read-create
       STATUS       current
       DESCRIPTION
           "The address family that this instance of DC-RTM supports.
            The value of this field must not be changed while the row
            status of this MIB is AMB_ROW_STATUS_ACTIVE and the admin
            status is AMB_ADMIN_STATUS_UP."
       DEFVAL { ipv4 }
       ::= { rtmEntityEntry 31 }

  rtmEntityDsDvmrp OBJECT-TYPE
       SYNTAX       AdminDistance
       MAX-ACCESS   read-create
       STATUS       current
       DESCRIPTION
          "The administrative distance used for DVMRP routes.
           The lower the distance for a given type of route,
           the more likely a route of this type is to be used by DC-RTM
           as the active route for the given destination."
       DEFVAL { 225 }
       ::= { rtmEntityEntry 32 }

-------------------------------------------------------------------------------

-- DC-RTM Redistribution Table
-- This table is used to determine how routing information is redistributed to
-- routing protocol managers (RPMs) using DC-RTM's Routing Protocol Input
-- interface.  The RPM to which the information may be redistributed is
-- called the destination RPM.
-- Routing information is received from RPMs and from the MIB (for static
-- routes); these are referred to as the routing information source.
-- There are two key aspects to an entry in this table.
-- Firstly, it contains a set of filters which determine whether or not the
-- entry applies to a given pairing of a given set of routing information and
-- a given destination RPM.  There is a filter priority to determine which
-- entry to use if there are multiple entries whose filters match a given
-- pairing.
-- Secondly, it contains parameters to use when redistributing the routing
-- information to the destination RPM, including a flag which determines
-- whether or not to redistribute at all.

  rtmRedistTable OBJECT-TYPE
  -- FAMILY-SHORT-NAME qcr_rds
       SYNTAX      SEQUENCE OF RtmRedistEntry
       MAX-ACCESS  not-accessible
       STATUS      current
       DESCRIPTION
          "The table of DC-RTM redistribution information entries.
          This table is used to determine how routing information is
          redistributed to routing protocol managers (RPMs) using DC-RTM's
          Routing Protocol Input interface.  The RPM to which the information
          may be redistributed is called the destination RPM.  Routing
          information is received from RPMs and from the MIB (for static
          routes); these are referred to as the routing information source."
       ::= { rtmObjects 2 }

  rtmRedistEntry OBJECT-TYPE
       SYNTAX      RtmRedistEntry
       MAX-ACCESS  not-accessible
       STATUS      current
       DESCRIPTION
          "Information defining how routing information is redistributed
          to routing protocol managers (RPMs)by DC-RTM on its Routing
          Protocol Input interface.

          There are two key aspects to an entry in this table.

          Firstly, it contains a set of filters which determine whether or not
          the entry applies to a given pairing of a given set of routing
          information and a given destination RPM.  There is a filter priority
          to determine which entry to use if there are multiple entries whose
          filters match a given pairing.

          Secondly, it contains parameters to use when redistributing the
          routing information to the destination RPM, including a flag which
          determines whether or not to redistribute at all."
        INDEX {
                rtmRedistFteIndex,
                rtmRedistEntryId
              }
       ::= { rtmRedistTable 1 }

  RtmRedistEntry ::= SEQUENCE {
         rtmRedistFteIndex               FteIndex,
         rtmRedistEntryId                Unsigned32,
         rtmRedistRowStatus              RowStatus,
         rtmRedistAdminStat              AdminStatus,
         rtmRedistPriority               Integer32,
         rtmRedistInfoSrc                InfoSourceDest,
         rtmRedistSrcInstFlt             TruthValue,
         rtmRedistSrcInst                FteIndex,
         rtmRedistInfoDest               InfoSourceDest,
         rtmRedistDestInstFlt            TruthValue,
         rtmRedistDestInst               FteIndex,
         rtmRedistAddrFilterType         InetAddressType,
         rtmRedistAddrFilter             InetAddress,
         rtmRedistAddrFltLen             Integer32,
         rtmRedistHopFltValType          InetAddressType,
         rtmRedistHopFltVal              InetAddress,
         rtmRedistHopFltLen              Integer32,
         rtmRedistIfIndexFlt             TruthValue,
         rtmRedistIfIndex                Integer32,
         rtmRedistPathtypeFlt            TruthValue,
         rtmRedistPathType               PathType,
         rtmRedistOspfAreaFlt            TruthValue,
         rtmRedistOspfArea               IpAddress,
         rtmRedistOspfTagFlt             TruthValue,
         rtmRedistOspfTag                OspfTag,
         rtmRedistCommunityFlt           TruthValue,
         rtmRedistCommunity              BgpCommunity,
         rtmRedistExtCommFlt             TruthValue,
         rtmRedistExtComm                BgpExtendedCommunity,
         rtmRedistRedistFlag             TruthValue,
         rtmRedistMetricConv             MetricConversion,
         rtmRedistMetricValue            Unsigned32,
         rtmRedistNwPathType             PathType,
         rtmRedistNwOspfTag              OspfTag,
         rtmRedistOspfPropagate          TruthValue,
         rtmRedistAddCommunity           TruthValue,
         rtmRedistNwCommunity            BgpCommunity,
         rtmRedistAddExtComm             TruthValue,
         rtmRedistNwExtComm              BgpExtendedCommunity,
         rtmRedistNwOrigin               BgpOriginCode,
         rtmRedistAddMed                 TruthValue,
         rtmRedistNwMed                  Integer32,
         rtmRedistAddLocalPref           TruthValue,
         rtmRedistNwLocalPref            Integer32,
         rtmRedistSetListId              Unsigned32
       }

  rtmRedistFteIndex OBJECT-TYPE
       SYNTAX       FteIndex
       MAX-ACCESS   not-accessible
       STATUS       current
       DESCRIPTION
          "The HAF entity index identifying the instance of DC-RTM to which
          this redistribution table entry applies."
       ::= { rtmRedistEntry 1 }

  rtmRedistEntryId OBJECT-TYPE
       SYNTAX       Unsigned32
       MAX-ACCESS   not-accessible
       STATUS       current
       DESCRIPTION
          "The index of this DC-RTM redistribution table entry within the
          DC-RTM entity.  This is an arbitrarily selected identifier."
       ::= { rtmRedistEntry 2 }

  rtmRedistRowStatus OBJECT-TYPE
       SYNTAX       RowStatus
       MAX-ACCESS   read-create
       STATUS       current
       DESCRIPTION
          "Used to create and delete a DC-RTM redistribution table entry."
       ::= { rtmRedistEntry 3 }

  rtmRedistAdminStat OBJECT-TYPE
       SYNTAX       AdminStatus
       MAX-ACCESS   read-create
       STATUS       current
       DESCRIPTION
          "The administrative state of the redistribution table entry.
          The row status by itself does not indicate whether the restribution
          is currently active.  The row must be defined and the administrative
          status must be up.  This enables a MIB agent to turn off a
          particular redistribution without deleting it from the table
          altogether."
       DEFVAL { adminStatusDown }
       ::= { rtmRedistEntry 4 }

  rtmRedistPriority OBJECT-TYPE
       SYNTAX       Integer32
       MAX-ACCESS   read-create
       STATUS       current
       DESCRIPTION
          "The priority assigned to this table entry.  The lower this value
          takes, the higher the priority of the entry.

          The priority takes effect when there is more than one entry in the
          table whose filters match a pairing of routing information and
          destination RPM."
       DEFVAL { '7FFFFFFF'h }
       ::= { rtmRedistEntry 5 }

  rtmRedistInfoSrc OBJECT-TYPE
       SYNTAX       InfoSourceDest
       MAX-ACCESS   read-create
       STATUS       current
       DESCRIPTION
          "The source of the routing information.  This is one of:

          -  an RPM, joined to DC-RTM on the Routing Protocol Input
             interface

          -  statically defined routes, defined in the static routes table

          -  all, meaning that this entry applies to all routing
             information sources."
       DEFVAL       { infoSourceAll }
       ::= { rtmRedistEntry 6 }

  rtmRedistSrcInstFlt OBJECT-TYPE
       SYNTAX       TruthValue
       MAX-ACCESS   read-create
       STATUS       current
       DESCRIPTION
          "Specifies whether or not a source instance filter is in use.  If
          it is not in use then this entry applies to all instances of the
          source RPM.

          The purpose of this filter is to allow an entry to apply to only one
          instance of the source RPM if more than one instance is active.

          The filter must always be off if the routing information
          source is set to 'all'."
       DEFVAL       { false }
       ::= { rtmRedistEntry 7 }

  rtmRedistSrcInst OBJECT-TYPE
       SYNTAX       FteIndex
       MAX-ACCESS   read-create
       STATUS       current
       DESCRIPTION
          "Value of the source instance filter, if in use.  If the filter
          is in use then do not match the source routing information to
          this entry if this filter value does not match the fault tolerant
          entity index of the RPM instance specified as the
          routing information source."
       DEFVAL { 0 }
       ::= { rtmRedistEntry 8 }

  rtmRedistInfoDest OBJECT-TYPE
       SYNTAX       InfoSourceDest
       MAX-ACCESS   read-create
       STATUS       current
       DESCRIPTION
          "The destination of the routing information.  This is usually an
          RPM, joined to DC-RTM on the Routing Protocol Input
          interface.  It can also be set to 'all', meaning that this
          entry applies to all routing information destinations."
       DEFVAL       { infoSourceAll }
       ::= { rtmRedistEntry 9 }

  rtmRedistDestInstFlt OBJECT-TYPE
       SYNTAX       TruthValue
       MAX-ACCESS   read-create
       STATUS       current
       DESCRIPTION
          "Specifies whether or not a destination instance filter is in use.
          If it is not in use then this entry applies to all instances of the
          destination RPM.

          The purpose of this filter is to allow an entry to apply to only one
          instance of the destination RPM if more than one instance is active.

          The filter must always be off if the routing information
          destination is 'all'."
       DEFVAL       { false }
       ::= { rtmRedistEntry 10 }

  rtmRedistDestInst OBJECT-TYPE
       SYNTAX       FteIndex
       MAX-ACCESS   read-create
       STATUS       current
       DESCRIPTION
          "Value of the destination instance filter, if in use.  If the filter
          is in use then do not redistribute this routing information to a
          given instance of an RPM if this filter value does not
          match the fault tolerant entity index of the RPM instance."
       DEFVAL { 0 }
       ::= { rtmRedistEntry 11 }

  rtmRedistAddrFilterType OBJECT-TYPE
       SYNTAX       InetAddressType
       MAX-ACCESS   read-create
       STATUS       current
       DESCRIPTION
          "The type of the address used as the destination address
           filter."
       DEFVAL { ipv4 }
       ::= { rtmRedistEntry 12 }

  rtmRedistAddrFilter OBJECT-TYPE
       SYNTAX       InetAddress (SIZE(4|16))
       MAX-ACCESS   read-create
       STATUS       current
       DESCRIPTION
          "Destination IP address filter.  Do not match the source routing
          information to this entry if one of these fails:

          -  the destination IP address in the source routing information,
             with the IP address filter prefix length applied, matches the
             IP address filter with the IP address filter prefix length
             applied

          -  the destination IP address prefix length is greater than or equal
             to the IP address filter prefix length.

          If the IP address filter prefix length is L, then applying the
          length to an address means taking the first L bits of the address.

          To avoid having any destination IP address filtering, set the IP
          address filter to all zeroes and the IP address filter prefix length
          to zero."
       DEFVAL { '00000000'H }
       ::= { rtmRedistEntry 13 }

  rtmRedistAddrFltLen OBJECT-TYPE
       SYNTAX       Integer32
       MAX-ACCESS   read-create
       STATUS       current
       DESCRIPTION
          "Destination IP address filter prefix length (in bits).  Do not
          match the source routing information to this entry if one of these
          fails:

          -  the destination IP address in the source routing information,
             with the IP address filter prefix length applied, matches the
             IP address filter with the IP address filter prefix length
             applied

          -  the destination IP address prefix length is greater than or equal
             to the IP address filter prefix length.

          If the IP address filter prefix length is L, then applying the
          length to an address means taking the first L bits of the address.

          To avoid having any destination IP address filtering, set the IP
          address filter to all zeroes and the IP address filter prefix length
          to zero."
       DEFVAL { 0 }
       ::= { rtmRedistEntry 14 }

  rtmRedistHopFltValType OBJECT-TYPE
       SYNTAX       InetAddressType
       MAX-ACCESS   read-create
       STATUS       current
       DESCRIPTION
          "The type of the address used as the next hop address
           filter."
       DEFVAL { ipv4 }
       ::= { rtmRedistEntry 15 }

  rtmRedistHopFltVal OBJECT-TYPE
       SYNTAX       InetAddress (SIZE(4|16))
       MAX-ACCESS   read-create
       STATUS       current
       DESCRIPTION
          "Value of next hop filter.  Do not match the source routing
          information to this entry if none of the next hop values in the
          source routing information, with the next hop filter prefix length
          applied, matches the next hop filter value with the next hop filter
          prefix length applied.

          If the next hop filter prefix length is L, then applying the
          length to an address means taking the first L bits of the address.

          To avoid having any next hop filtering, set the next hop filter to
          all zeroes and the next hop filter prefix length to zero."
       DEFVAL { '00000000'H }
       ::= { rtmRedistEntry 16 }

  rtmRedistHopFltLen OBJECT-TYPE
       SYNTAX       Integer32
       MAX-ACCESS   read-create
       STATUS       current
       DESCRIPTION
          "Next hop filter prefix length.  Do not match the source routing
          information to this entry if none of the next hop values in the
          source routing information, with the next hop filter prefix length
          applied, matches the next hop filter value with the next hop filter
          prefix length applied.

          If the next hop filter prefix length is L, then applying the
          length to an address means taking the first L bits of the address.

          To avoid having any next hop filtering, set the next hop filter to
          all zeroes and the next hop filter prefix length to zero."
       DEFVAL { 0 }
       ::= { rtmRedistEntry 17 }

  rtmRedistIfIndexFlt OBJECT-TYPE
       SYNTAX       TruthValue
       MAX-ACCESS   read-create
       STATUS       current
       DESCRIPTION
          "Specifies whether or not an output network interface index filter
          is in use."
       DEFVAL       { false }
       ::= { rtmRedistEntry 18 }

  rtmRedistIfIndex OBJECT-TYPE
       SYNTAX       Integer32
       MAX-ACCESS   read-create
       STATUS       current
       DESCRIPTION
          "Value of output network interface index filter, if in use.
          If the filter is in use then do not match the source routing
          information to this entry if none of the output network interface
          indexes in the source routing information matches this filter value."
       DEFVAL { 0 }
       ::= { rtmRedistEntry 19 }

  rtmRedistPathtypeFlt OBJECT-TYPE
       SYNTAX       TruthValue
       MAX-ACCESS   read-create
       STATUS       current
       DESCRIPTION
          "Specifies whether or not a path type filter is in use.  If it is
          not in use then this entry applies to all path type values.   A path
          type filter can only be used if the routing information source filter
          _info_src_ is not set to 'all'. The value of the path type filter,
          if used, must be one of the path types which matches the routing
          information source. For example, a path type filter of 'OSPF
          external type 1' can only be used if the routing information source
          filter is set to OSPF."
       DEFVAL       { false }
       ::= { rtmRedistEntry 20 }

  rtmRedistPathType OBJECT-TYPE
       SYNTAX       PathType
       MAX-ACCESS   read-create
       STATUS       current
       DESCRIPTION
          "Value of path type filter, if in use.  If the filter is in use
          then do not match the source routing information to this entry
          if the path type in the source routing information does not
          match this filter value.  A path type filter can only be used if the
          routing information source filter _info_src_ is not set to 'all'.
          The value of the path type filter, if used, must be one of the path
          types which matches the routing information source. For example, a
          path type filter of 'OSPF external type 1' can only be used if the
          routing information source filter is set to OSPF."
       DEFVAL { pathTypeNone }
       ::= { rtmRedistEntry 21 }

  rtmRedistOspfAreaFlt OBJECT-TYPE
       SYNTAX       TruthValue
       MAX-ACCESS   read-create
       STATUS       current
       DESCRIPTION
          "Specifies whether or not an OSPF area filter is in use.
          The filter can only be on if the routing information source
          field is OSPF."
       DEFVAL       { false }
       ::= { rtmRedistEntry 22 }

  rtmRedistOspfArea OBJECT-TYPE
       SYNTAX       IpAddress
       MAX-ACCESS   read-create
       STATUS       current
       DESCRIPTION
          "Value of OSPF area filter, if in use.  If the filter is in use
          then do not match the source routing information to this entry
          if the OSPF area ID in the information does not match this area ID."
       DEFVAL { '00000000'H }  -- 0.0.0.0
       ::= { rtmRedistEntry 23 }

  rtmRedistOspfTagFlt  OBJECT-TYPE
       SYNTAX       TruthValue
       MAX-ACCESS   read-create
       STATUS       current
       DESCRIPTION
          "Specifies whether or not an OSPF tag filter is in use.
          The filter can only be on if the routing information source
          field is OSPF."
       DEFVAL       { false }
       ::= { rtmRedistEntry 24 }

  rtmRedistOspfTag OBJECT-TYPE
       SYNTAX       OspfTag
       MAX-ACCESS   read-create
       STATUS       current
       DESCRIPTION
          "Value of OSPF tag filter, if in use.  If the filter is in use
          then do not match the source routing information to this entry
          if the tag in the information does not match this tag."
       DEFVAL { 0 }
       ::= { rtmRedistEntry 25 }

  rtmRedistCommunityFlt OBJECT-TYPE
       SYNTAX       TruthValue
       MAX-ACCESS   read-create
       STATUS       current
       DESCRIPTION
          "Specifies whether or not a BGP community number filter is in use.
          The filter can only be on if the routing information source
          field is BGP."
       DEFVAL       { false }
       ::= { rtmRedistEntry 26 }

  rtmRedistCommunity OBJECT-TYPE
       SYNTAX       BgpCommunity
       MAX-ACCESS   read-create
       STATUS       current
       DESCRIPTION
          "Value of BGP community number filter, if in use.  If the filter
          is in use then do not match the source routing information to this
          entry if there is no match between one of the community numbers
          in the source routing information and the value of this filter."
       DEFVAL { '00000000'h }
       ::= { rtmRedistEntry 27 }

  rtmRedistExtCommFlt OBJECT-TYPE
       SYNTAX       TruthValue
       MAX-ACCESS   read-create
       STATUS       current
       DESCRIPTION
          "Specifies whether or not a BGP extended community number filter
          is in use.  The filter can only be on if the routing information
          source field is BGP."
       DEFVAL       { false }
       ::= { rtmRedistEntry 28 }

  rtmRedistExtComm OBJECT-TYPE
       SYNTAX       BgpExtendedCommunity
       MAX-ACCESS   read-create
       STATUS       current
       DESCRIPTION
          "Value of BGP extended community number filter, if in use.  If
          the filter is in use then do not match the source routing
          information to this entry if there is no match between one of the
          extended community numbers in the source routing information and
          the value of this filter."
       DEFVAL { '0000000000000000'h }
       ::= { rtmRedistEntry 29 }

  rtmRedistRedistFlag OBJECT-TYPE
       SYNTAX       TruthValue
       MAX-ACCESS   read-create
       STATUS       current
       DESCRIPTION
          "Flag determining whether or not DC-RTM redistributes routing
          information from the given source to the given destination."
       DEFVAL       { false }
       ::= { rtmRedistEntry 30 }

  rtmRedistMetricConv OBJECT-TYPE
       SYNTAX       MetricConversion
       MAX-ACCESS   read-create
       STATUS       current
       DESCRIPTION
          "How to act on the value of the metric in the routing information
          received from the source to create a value for the metric in the
          routing information sent to the destination.

          This field is only defined if the redistribution flag is TRUE."
       DEFVAL { metricConvSame }
       ::= { rtmRedistEntry 31 }

  rtmRedistMetricValue OBJECT-TYPE
       SYNTAX       Unsigned32
       MAX-ACCESS   read-create
       STATUS       current
       DESCRIPTION
          "Numerical parameter to use when creating a value for the metric
          in the routing information sent to the destination based on the
          supplied metric in the routing information received from the source.

          This field is only defined if the redistribution flag is TRUE
          and the metric conversion field is set to 'constant', 'scale up',
          'scale down' or 'truncate'.

          If the metric conversion field is 'constant' then the new metric
          value is just the value of the numerical parameter.

          If the metric conversion field is 'scale up' then the new metric
          value is the supplied metric multiplied by the value of the
          numerical parameter (or 0xffffffff if this is smaller).

          If the metric conversion method is 'scale down' then the new metric
          value is the supplied metric divided by the value of the
          numerical parameter (rounded down to the next integer).  The
          numerical parameter cannot be zero in this case.

          If the metric conversion field is 'truncate' then the new metric
          value is the lower value of the supplied metric value and the
          numerical parameter."
       DEFVAL { 1 }
       ::= { rtmRedistEntry 32 }

  rtmRedistNwPathType OBJECT-TYPE
       SYNTAX       PathType
       MAX-ACCESS   read-create
       STATUS       current
       DESCRIPTION
          "Type of path to set in routing information sent to
          destination.

          This field is only defined if the redistribution flag is TRUE.

          If the information destination filter _info_dest_ is set to 'all',
          the new path type must be set to 'none'. Otherwise it must be set
          either to 'none' or to a path type which matches the routing
          information destination filter. For example, a new path type of
          'OSPF external type 1' can only be used if the routing information
          destination filter is set to OSPF."
       DEFVAL { pathTypeNone }
       ::= { rtmRedistEntry 33 }

  rtmRedistNwOspfTag OBJECT-TYPE
       SYNTAX       OspfTag
       MAX-ACCESS   read-create
       STATUS       current
       DESCRIPTION
          "Value of OSPF tag to set in routing information sent to
          destination.

          This field is only defined if the redistribution flag is TRUE and
          the destination for the routing information is OSPF or 'all'."
       DEFVAL { 0 }
       ::= { rtmRedistEntry 34 }

  rtmRedistOspfPropagate OBJECT-TYPE
       SYNTAX       TruthValue
       MAX-ACCESS   read-create
       STATUS       current
       DESCRIPTION
          "Value of OSPF propagate flag to set in routing information
          sent to destination.

          This field is only defined if the redistribution flag is TRUE and
          the destination for the routing information is OSPF or 'all'."
       DEFVAL       { true }
       ::= { rtmRedistEntry 35 }

  rtmRedistAddCommunity OBJECT-TYPE
       SYNTAX       TruthValue
       MAX-ACCESS   read-create
       STATUS       obsolete
       DESCRIPTION
          "Flag determining whether or not DC-RTM adds a BGP community value
          in routing information sent to the destination.

          This field is only defined if the redistribution flag is TRUE and
          the destination for the routing information is BGP or 'all'."
       DEFVAL       { false }
       ::= { rtmRedistEntry 36 }

  rtmRedistNwCommunity OBJECT-TYPE
       SYNTAX       BgpCommunity
       MAX-ACCESS   read-create
       STATUS       obsolete
       DESCRIPTION
          "Value to use for BGP community number in routing information
           sent to the destination if the add community flag is TRUE.

          This field is only defined if the redistribution flag is TRUE and
          the destination for the routing information is BGP or 'all'."
       DEFVAL { '00000000'h }
       ::= { rtmRedistEntry 37 }

  rtmRedistAddExtComm OBJECT-TYPE
       SYNTAX       TruthValue
       MAX-ACCESS   read-create
       STATUS       obsolete
       DESCRIPTION
          "Flag determining whether or not DC-RTM adds a BGP extended
          community value in routing information sent to the destination.

          This field is only defined if the redistribution flag is TRUE and
          the destination for the routing information is BGP or 'all'."
       DEFVAL       { false }
       ::= { rtmRedistEntry 38 }

  rtmRedistNwExtComm OBJECT-TYPE
       SYNTAX       BgpExtendedCommunity
       MAX-ACCESS   read-create
       STATUS       obsolete
       DESCRIPTION
          "Value to use for BGP extended community number in routing
          information sent to destination if the add extended community
          flag is TRUE.

          This field is only defined if the redistribution flag is TRUE and
          the destination for the routing information is BGP or 'all'."
       DEFVAL { '0000000000000000'h }
       ::= { rtmRedistEntry 39 }

  rtmRedistNwOrigin OBJECT-TYPE
       SYNTAX       BgpOriginCode
       MAX-ACCESS   read-create
       STATUS       current
       DESCRIPTION
          "Value to use for the BGP origin code in the routing information
          sent to the destination.

          This field is only defined if the redistribution flag is TRUE and
          the destination for the routing information is BGP or 'all'."
       DEFVAL { bgpOriginIncomplete }
       ::= { rtmRedistEntry 40 }

  rtmRedistAddMed OBJECT-TYPE
       SYNTAX       TruthValue
       MAX-ACCESS   read-create
       STATUS       current
       DESCRIPTION
          "Flag determining whether or not DC-RTM adds a BGP Multi-Exit
          Discriminator value in routing information sent to the destination.

          This field is only defined if the redistribution flag is TRUE and
          the destination for the routing information is BGP or 'all'."
       DEFVAL       { false }
       ::= { rtmRedistEntry 41 }

  rtmRedistNwMed OBJECT-TYPE
       SYNTAX       Integer32
       MAX-ACCESS   read-create
       STATUS       current
       DESCRIPTION
          "Value to use for the BGP Multi-Exit Discriminator in the routing
          information sent to the destination of the add MED flag is TRUE.

          This field is only defined if the redistribution flag is TRUE and
          the destination for the routing information is BGP or 'all'."
       DEFVAL { 0 }
       ::= { rtmRedistEntry 42 }

  rtmRedistAddLocalPref OBJECT-TYPE
       SYNTAX       TruthValue
       MAX-ACCESS   read-create
       STATUS       current
       DESCRIPTION
          "Flag determining whether or not DC-RTM adds a BGP Local Preference
          value in routing information sent to the destination.

          This field is only defined if the redistribution flag is TRUE and
          the destination for the routing information is BGP or 'all'."
       DEFVAL       { false }
       ::= { rtmRedistEntry 43 }

  rtmRedistNwLocalPref OBJECT-TYPE
       SYNTAX       Integer32
       MAX-ACCESS   read-create
       STATUS       current
       DESCRIPTION
          "Value to use for the BGP Local Preference in the routing
          information sent to the destination if the add local pref flag is
          TRUE.

          This field is only defined if the redistribution flag is TRUE and
          the destination for the routing information is BGP or 'all'."
       DEFVAL { 0 }
       ::= { rtmRedistEntry 44 }

  rtmRedistSetListId OBJECT-TYPE
       SYNTAX       Unsigned32
       MAX-ACCESS   read-create
       STATUS       current
       DESCRIPTION
          "List identifier for the list of set actions to apply.  The list
           of set actions are defined in the rtmRdstSetFieldTable, and are
           the group of entries in that table with the
           rtmRdstSetFieldListId field equal to the list identifier
           specified here.

           This field is only defined if the redistribution flag is TRUE.
           A value of 0 indicates no list is specified."
       DEFVAL { 0 }
       ::= { rtmRedistEntry 45 }

-------------------------------------------------------------------------------

-- DC-RTM Static routes Table
-- This table is used to create and manage DC-RTM static routes.

  rtmStaticRtTable OBJECT-TYPE
  -- FAMILY-SHORT-NAME qcr_strt
       SYNTAX      SEQUENCE OF RtmStaticRtEntry
       MAX-ACCESS  not-accessible
       STATUS      current
       DESCRIPTION
          "The table of DC-RTM static routes."
       ::= { rtmObjects 3 }

  rtmStaticRtEntry OBJECT-TYPE
       SYNTAX      RtmStaticRtEntry
       MAX-ACCESS  not-accessible
       STATUS      current
       DESCRIPTION
          "Information about static routes, containing next hop information
          or instruction to discard/reject matching packets."
        INDEX {
           rtmStaticRtFteIndex,
           rtmStaticRtDestAddrType,
           rtmStaticRtDestAddr,
           rtmStaticRtDestLen,
           rtmStaticRtNextHopType,
           rtmStaticRtNextHop,
	   rtmStaticRtIfIndex
           }
       ::= { rtmStaticRtTable 1 }

  RtmStaticRtEntry ::= SEQUENCE {
         rtmStaticRtFteIndex       FteIndex,
         rtmStaticRtDestAddrType   InetAddressType,
         rtmStaticRtDestAddr       InetAddress,
         rtmStaticRtDestLen        Integer32,
         rtmStaticRtNextHopType    InetAddressType,
         rtmStaticRtNextHop        InetAddress,
         rtmStaticRtIfIndex        Integer32,
         rtmStaticRtOutIfIndex     Integer32,
         rtmStaticRtRowStatus      RowStatus,
         rtmStaticRtAdminStat      AdminStatus,
         rtmStaticRtOverride       TruthValue,
         rtmStaticRtAdminDist      AdminDistance,
         rtmStaticRtAction         RouteAction,
         rtmStaticRtFwdAddrType    InetAddressType,
         rtmStaticRtForwardingAddr InetAddress,
         rtmStaticRtPathType       PathType,
         rtmStaticRtCostMetric     CostMetric
       }

  rtmStaticRtFteIndex OBJECT-TYPE
       SYNTAX       FteIndex
       MAX-ACCESS   not-accessible
       STATUS       current
       DESCRIPTION
          "The HAF entity index identifying the instance of DC-RTM to which
          this static route entry applies."
       ::= { rtmStaticRtEntry 1 }

  rtmStaticRtDestAddrType OBJECT-TYPE
       SYNTAX       InetAddressType
       MAX-ACCESS   not-accessible
       STATUS       current
       DESCRIPTION
          "The type of the address used as the destination
           internetwork address or subnet address."
       ::= { rtmStaticRtEntry 2 }

  rtmStaticRtDestAddr OBJECT-TYPE
       SYNTAX       InetAddress (SIZE(4|16))
       MAX-ACCESS   not-accessible
       STATUS       current
       DESCRIPTION
          "Destination internetwork address or subnet address.  The
          destination prefix length is applied to this value, and to a
          particular destination address, to determine whether the route
          applies to the particular address.

          If the prefix length is L, then applying the length to an address
          means taking the first L bits of the address."
       ::= { rtmStaticRtEntry 3 }

  rtmStaticRtDestLen OBJECT-TYPE
       SYNTAX       Integer32 (0..128)
       MAX-ACCESS   not-accessible
       STATUS       current
       DESCRIPTION
          "Prefix length (in bits) to apply to the destination internetwork
          address or subnet address, to obtain the set of addresses to which
          this route applies.

          If the prefix length is L, then applying the length to an address
          means taking the first L bits of the address."
       ::= { rtmStaticRtEntry 4 }

  rtmStaticRtNextHopType OBJECT-TYPE
       SYNTAX       InetAddressType
       MAX-ACCESS   not-accessible
       STATUS       current
       DESCRIPTION
          "The type of the address used as the next-hop address
           for this route."
       ::= { rtmStaticRtEntry 5 }

  rtmStaticRtNextHop OBJECT-TYPE
      SYNTAX        InetAddress (SIZE(4|16))
       MAX-ACCESS   not-accessible
       STATUS       current
       DESCRIPTION
          "If the action to perform is to forward the packet, this field
          contains the next-hop address, if any.  It is not defined for other
          action values.  It is also possible to specify only an output
          network interface index for forwarding and set this address to
          zero."
       ::= { rtmStaticRtEntry 6 }

  rtmStaticRtIfIndex OBJECT-TYPE
       SYNTAX       Integer32 (0..2147483647)
       MAX-ACCESS   not-accessible
       STATUS       current
       DESCRIPTION
          "This field contains the network interface index of the
           interface configured to reach the next hop. If 0, then
           the rtmStaticRtOutIfIndex is determined by a subnet match
           of the configured next hop IP address. Otherwise, the
           rtmStaticRtOutIfIndex is equal to this value."
       ::= { rtmStaticRtEntry 7 }

  rtmStaticRtOutIfIndex OBJECT-TYPE
       SYNTAX       Integer32 (0..2147483647)
       MAX-ACCESS   read-only
       STATUS       current
       DESCRIPTION
          "If the action to perform is to forward the packet, this field
          contains the network interface index of the output network
          interface used to reach the next hop.  It is not defined for other
          action values."
       ::= { rtmStaticRtEntry 8 }

  rtmStaticRtRowStatus OBJECT-TYPE
       SYNTAX       RowStatus
       MAX-ACCESS   read-create
       STATUS       current
       DESCRIPTION
          "Used to create and delete a DC-RTM static route."
       ::= { rtmStaticRtEntry 9 }

  rtmStaticRtAdminStat OBJECT-TYPE
       SYNTAX       AdminStatus
       MAX-ACCESS   read-create
       STATUS       current
       DESCRIPTION
          "The administrative state of the static route.  The row status by
          itself does not indicate whether the static route definition
          is currently active.  The row must be defined and the administrative
          status must be up.  This enables a MIB agent to turn off a
          particular static route without deleting it from the table
          altogether."
       DEFVAL { adminStatusDown }
       ::= { rtmStaticRtEntry 10 }

  rtmStaticRtOverride OBJECT-TYPE
       SYNTAX       TruthValue
       MAX-ACCESS   read-create
       STATUS       current
       DESCRIPTION
          "The administrative distance for this route is by default taken to be
           the administrative distance configured in the DC-RTM entity table
           associated with the route's path type (rtmStaticRtPathType).  If
           rtmStaticRtOverride is set to AMB_TRUE, this admin distance is
           overridden and we use the rtmStaticRtAdminDist instead.

           The lower the administrative distance for a given route, the
           more likely that route is to be used by DC-RTM as the active
           route for the given destination."
       DEFVAL { false }
       ::= { rtmStaticRtEntry 11 }

  rtmStaticRtAdminDist OBJECT-TYPE
       SYNTAX       AdminDistance
       MAX-ACCESS   read-create
       STATUS       current
       DESCRIPTION
          "Administrative distance for static route, if overriding the
           default administrative distance for this route given in the
           DC-RTM entity table.  This field is not defined if overriding is
           not being performed.

           The lower the administrative distance for a given route, the
           more likely that route is to be used by DC-RTM as the active
           route for the given destination."
       DEFVAL { 1 }
       ::= { rtmStaticRtEntry 12 }

  rtmStaticRtAction OBJECT-TYPE
       SYNTAX       RouteAction
       MAX-ACCESS   read-create
       STATUS       current
       DESCRIPTION
          "Action to perform on receipt of a packet to the specified
          destination."
       DEFVAL { routeActionForward }
       ::= { rtmStaticRtEntry 13 }

  rtmStaticRtFwdAddrType OBJECT-TYPE
       SYNTAX       InetAddressType
       MAX-ACCESS   read-create
       STATUS       current
       DESCRIPTION
          "The type of the address used as the forwarding address
           for this route."
       DEFVAL { ipv4 }
       ::= { rtmStaticRtEntry 14 }

  rtmStaticRtForwardingAddr OBJECT-TYPE
      SYNTAX        InetAddress (SIZE(4|16))
       MAX-ACCESS   read-create
       STATUS       current
       DESCRIPTION
          "Forwarding address to advertise for this route."
       DEFVAL { '00000000'H }
       ::= { rtmStaticRtEntry 15 }

  rtmStaticRtPathType OBJECT-TYPE
       SYNTAX       PathType
       MAX-ACCESS   read-create
       STATUS       current
       DESCRIPTION
          "Type of path associated with this route."
       DEFVAL { pathTypeStatic }
       ::= { rtmStaticRtEntry 16 }

  rtmStaticRtCostMetric OBJECT-TYPE
       SYNTAX       CostMetric
       MAX-ACCESS   read-create
       STATUS       current
       DESCRIPTION
          "Cost metric for static route. The cost metric is the value used
          in determining whether to give this route to the forwarding table
          in preference to other routes to the same destination (the lower the better)."
       DEFVAL { 0 }
       ::= { rtmStaticRtEntry 17 }

-------------------------------------------------------------------------------

--
-- DC-RTM Master Join Table.
--
-- This table determines which master joins a DC-RTM entity makes.
-- There is a table entry for each slave entity to which an instance of DC-RTM
-- should join.  At present, there are two distinct types of slave entity.
-- Forwarding stub entities such as the IP Forwarding Stub, the Labelled
-- Data Forwarding Stub and the Route Selection Manager receive route
-- updates over the Active Routes Interface.  The second type of entity
-- are Routing Protocol Managers who use the ARI for querying routing
-- information, and this includes BGP and PIM.
--

  rtmMjTable OBJECT-TYPE
  -- FAMILY-SHORT-NAME qrpm_mj
       SYNTAX      SEQUENCE OF RtmMjEntry
       MAX-ACCESS  not-accessible
       STATUS      current
       DESCRIPTION
              "This table controls which entities DC-RTM should join to as
              master.  Each join is represented by a row in this table.
              The status of each join is represented by a read-only object
              within each row."
       ::= { rtmObjects 4 }

  rtmMjEntry OBJECT-TYPE
       SYNTAX      RtmMjEntry
       MAX-ACCESS  not-accessible
       STATUS      current
       DESCRIPTION "Represents a join for which DC-RTM is master."
       INDEX {
       rtmMjRtmFteIndex,
       rtmMjSlaveFteId,
       rtmMjSlaveType
       }
       ::= { rtmMjTable 1 }

  RtmMjEntry ::= SEQUENCE {
      rtmMjRtmFteIndex              FteIndex,
      rtmMjSlaveFteId               FteIndex,
      rtmMjSlaveType                AriPrtnrType,
      rtmMjIfType                   InterfaceType,
      rtmMjRowStatus                RowStatus,
      rtmMjAdminStatus              AdminStatus,
      rtmMjOperStatus               OperStatus,
      rtmMjJoinStatus               MjStatus
    }

  rtmMjRtmFteIndex OBJECT-TYPE
       SYNTAX      FteIndex
       MAX-ACCESS  not-accessible
       STATUS      current
       DESCRIPTION
          "The HAF entity index identifying the instance of DC-RTM to which
          this master join table entry applies."
       ::= { rtmMjEntry 1 }

  rtmMjSlaveFteId OBJECT-TYPE
       SYNTAX      FteIndex
       MAX-ACCESS  not-accessible
       STATUS      current
       DESCRIPTION
          "The HAF entity index identifying the instance of the slave entity
          to which this master join table entry applies.

          This index is used in the join user data, to enable FTI-specific
          code within System Manager to select a suitable slave entity
          instance."
       ::= { rtmMjEntry 2 }

  rtmMjSlaveType OBJECT-TYPE
       SYNTAX      AriPrtnrType
       MAX-ACCESS  not-accessible
       STATUS      current
       DESCRIPTION
          "The type of entity which the slave side of this join should be.

           This value is used in the join user data, to enable
           FTI-specific code within System Manager to select a suitable
           slave entity instance."
       ::= {rtmMjEntry 8 }

  rtmMjIfType OBJECT-TYPE
       SYNTAX      InterfaceType
       MAX-ACCESS  read-create
       STATUS      current
       DESCRIPTION "Identifies the interface type for this master join."
       DEFVAL { ifActiveRoutes }
       ::= { rtmMjEntry 3 }

  rtmMjRowStatus OBJECT-TYPE
       SYNTAX      RowStatus
       MAX-ACCESS  read-create
       STATUS      current
       DESCRIPTION
            "The row status for this DC-RTM master join table
            entry, used to create and destroy table entries."
       ::= { rtmMjEntry 4 }

  rtmMjAdminStatus OBJECT-TYPE
       SYNTAX      AdminStatus
       MAX-ACCESS  read-create
       STATUS      current
       DESCRIPTION
            "The administrative status of this master join, used to start
            and stop the join."
       DEFVAL { adminStatusUp }
       ::= { rtmMjEntry 5 }

  rtmMjOperStatus OBJECT-TYPE
       SYNTAX      OperStatus
       MAX-ACCESS  read-only
       STATUS      current
       DESCRIPTION "The current operational status of this master join."
       ::= { rtmMjEntry 6 }

  rtmMjJoinStatus OBJECT-TYPE
       SYNTAX      MjStatus
       MAX-ACCESS  read-only
       STATUS      current
       DESCRIPTION "The status of the master join."
       ::= { rtmMjEntry 7 }

-------------------------------------------------------------------------------

--
-- DC-RTM Slave Join Table.
--
-- This is a read-only table.  It contains information on joins for which
-- DC-RTM entities are acting as slaves.  Each row in this table
-- represents one slave join in a particular DC-RTM entity.  At present
-- the partner (master) entity on any slave join is a Routing Protocol
-- Manager entity, and the interface is the Routing Protocol Input interface.
--

  rtmSjTable OBJECT-TYPE
  -- FAMILY-SHORT-NAME qrpm_sj
       SYNTAX      SEQUENCE OF RtmSjEntry
       MAX-ACCESS  not-accessible
       STATUS      current
       DESCRIPTION
       "This table contains information on joins for which DC-RTM
       entities are acting as slaves.  Each row in this table
       represents one slave join in a particular DC-RTM entity."
       ::= { rtmObjects 5 }

  rtmSjEntry OBJECT-TYPE
       SYNTAX      RtmSjEntry
       MAX-ACCESS  not-accessible
       STATUS      current
       DESCRIPTION "Represents a join for which DC-RTM is slave."
       INDEX {
          rtmSjRtmFteIndex,
          rtmSjRtmRpmIndex
       }
       ::= { rtmSjTable 1 }

  RtmSjEntry ::= SEQUENCE {
      rtmSjRtmFteIndex            FteIndex,
      rtmSjRtmRpmIndex            Integer32,
      rtmSjIfType                 InterfaceType,
      rtmSjMastFteType            Integer32,
      rtmSjMastFteId              FteIndex,
      rtmSjJoinStatus             SjStatus
    }

  rtmSjRtmFteIndex OBJECT-TYPE
       SYNTAX      FteIndex
       MAX-ACCESS  not-accessible
       STATUS      current
       DESCRIPTION
          "The HAF entity index identifying the instance of DC-RTM to which
          this slave join table entry applies."
       ::= { rtmSjEntry 1 }

  rtmSjRtmRpmIndex OBJECT-TYPE
       SYNTAX      Integer32 (0..2147483647)
       MAX-ACCESS  not-accessible
       STATUS      current
       DESCRIPTION
          "Internal index used by DC-RTM for this RPM."
       ::= { rtmSjEntry 2 }

  rtmSjIfType OBJECT-TYPE
       SYNTAX      InterfaceType
       MAX-ACCESS  read-only
       STATUS      current
       DESCRIPTION "Identifies the interface type for this master join."
       ::= { rtmSjEntry 3 }

  rtmSjMastFteType OBJECT-TYPE
       SYNTAX      Integer32
       MAX-ACCESS  read-only
       STATUS      current
       DESCRIPTION
          "Additional information about the type of master entity which
          created the join, where this is not uniquely defined by the
          interface type.

          For joins to Routing Protocol Managers using the Routing Protocol
          Input interface, this field contains the routing protocol type."
       ::= { rtmSjEntry 4 }

  rtmSjMastFteId OBJECT-TYPE
       SYNTAX      FteIndex
       MAX-ACCESS  read-only
       STATUS      current
       DESCRIPTION
          "The HAF entity index identifying the instance of the master
          entity to which this slave join table entry applies."
       ::= { rtmSjEntry 5 }

  rtmSjJoinStatus OBJECT-TYPE
       SYNTAX      SjStatus
       MAX-ACCESS  read-only
       STATUS      current
       DESCRIPTION "The status of the slave join."
       ::= { rtmSjEntry 6 }

-------------------------------------------------------------------------------

--  DC-RTM IP CIDR Route Table.  Based on IP CIDR Route Table from RFC 2096.

  rtmRouteTable OBJECT-TYPE
      SYNTAX   SEQUENCE OF RtmRouteEntry
      MAX-ACCESS not-accessible
      STATUS   current
      DESCRIPTION
         "This entity's IP Routing table."
      REFERENCE
         "RFC 1213 Section 6.6, The IP Group"
      ::= { rtmObjects 6 }

  rtmRouteEntry OBJECT-TYPE
      SYNTAX   RtmRouteEntry
      MAX-ACCESS not-accessible
      STATUS   current
      DESCRIPTION
         "A particular route to  a  particular  destina-
         tion, under a particular policy."
      INDEX {
          rtmRouteFteIndex,
          rtmRouteDestType,
          rtmRouteDest,
          rtmRouteDestLen,
          rtmRouteTos,
          rtmRouteNextHopType,
          rtmRouteNextHop,
          rtmRouteIfIndex
          }
      ::= { rtmRouteTable 1 }

  RtmRouteEntry ::= SEQUENCE {
          rtmRouteFteIndex        FteIndex,
          rtmRouteStatus          RowStatus,
          rtmRouteDestType        InetAddressType,
          rtmRouteDest            InetAddress,
          rtmRouteDestLen         Integer32,
          rtmRouteTos             Integer32,
          rtmRouteNextHopType     InetAddressType,
          rtmRouteNextHop         InetAddress,
          rtmRouteIfIndex         Integer32,
          rtmRouteType            RouteType,
          rtmRouteProto           IANAipRouteProtocol,
          rtmRouteAge             Integer32,
          rtmRouteInfo            RouteInfo,
          rtmRouteNextHopAS       Integer32,
          rtmRouteMetric1         Integer32,
          rtmRouteMetric2         Integer32,
          rtmRouteMetric3         Integer32,
          rtmRouteMetric4         Integer32,
          rtmRouteMetric5         Integer32
      }

  rtmRouteFteIndex OBJECT-TYPE
       SYNTAX      FteIndex
       MAX-ACCESS  not-accessible
       STATUS      current
       DESCRIPTION
          "The HAF entity index identifying the instance of DC-RTM to which
          this static route entry applies."
       ::= { rtmRouteEntry 1 }

  rtmRouteStatus OBJECT-TYPE
      SYNTAX      RowStatus
      MAX-ACCESS  read-only
      STATUS      current
      DESCRIPTION
         "The row status variable, used according to
         row installation and removal conventions."
      ::= { rtmRouteEntry 2 }

  rtmRouteDestType OBJECT-TYPE
      SYNTAX       InetAddressType
      MAX-ACCESS   not-accessible
      STATUS       current
      DESCRIPTION
         "The type of the address used as the destination IP address
          for this route."
      ::= { rtmRouteEntry 3 }

  rtmRouteDest OBJECT-TYPE
      SYNTAX      InetAddress (SIZE(4|16))
      MAX-ACCESS  not-accessible
      STATUS      current
      DESCRIPTION
         "The destination IP address of this route.

         This object may not take a Multicast (Class  D)
         address value.

         Any assignment (implicit or  otherwise)  of  an
         instance  of  this  object to a value x must be
         rejected if the bitwise logical-AND of  x  with
         the  value of the corresponding instance of the
         rtmRouteMask object is not equal to x."
      ::= { rtmRouteEntry 4 }

  rtmRouteDestLen OBJECT-TYPE
      SYNTAX   Integer32  (0..128)
      MAX-ACCESS not-accessible
      STATUS   current
      DESCRIPTION
         "Indicate the mask length (in bits) to be logical-ANDed with the
         destination address before being compared to
         the value in the rtmRouteDest field.  For
         those systems that do not support arbitrary
         subnet masks, an agent constructs the value of
         the rtmRouteMask by reference to the IP Address
         Class."

      ::= { rtmRouteEntry 5 }

  -- The following convention is included for specification
  -- of TOS Field contents.  At this time, the Host Requirements
  -- and the Router Requirements documents disagree on the width
  -- of the TOS field.  This mapping describes the Router
  -- Requirements mapping, and leaves room to widen the TOS field
  -- without impact to fielded systems.

  rtmRouteTos OBJECT-TYPE
      SYNTAX   Integer32 (0..15)
      MAX-ACCESS not-accessible
      STATUS   current
      DESCRIPTION
         "The policy specifier is the IP TOS Field.  The encoding
         of IP TOS is as specified by the following convention.
         Zero indicates the default path if no more specific
         policy applies.

         +-----+-----+-----+-----+-----+-----+-----+-----+
         |                 |                       |     |
         |   PRECEDENCE    |    TYPE OF SERVICE    |  0  |
         |                 |                       |     |
         +-----+-----+-----+-----+-----+-----+-----+-----+

                  IP TOS                IP TOS
             Field     Policy      Field     Policy
             Contents    Code      Contents    Code
             0 0 0 0  ==>   0      0 0 0 1  ==>   2
             0 0 1 0  ==>   4      0 0 1 1  ==>   6
             0 1 0 0  ==>   8      0 1 0 1  ==>  10
             0 1 1 0  ==>  12      0 1 1 1  ==>  14
             1 0 0 0  ==>  16      1 0 0 1  ==>  18
             1 0 1 0  ==>  20      1 0 1 1  ==>  22
             1 1 0 0  ==>  24      1 1 0 1  ==>  26
             1 1 1 0  ==>  28      1 1 1 1  ==>  30

         RTM always returns a default value of 0 for this field."
      ::= { rtmRouteEntry 6 }

  rtmRouteNextHopType OBJECT-TYPE
      SYNTAX      InetAddressType
      MAX-ACCESS  not-accessible
      STATUS      current
      DESCRIPTION
         "The type of the address used as the next-hop address
          for this route."
      ::= { rtmRouteEntry 7 }

  rtmRouteNextHop OBJECT-TYPE
      SYNTAX     InetAddress (SIZE(4|16))
      MAX-ACCESS not-accessible
      STATUS     current
      DESCRIPTION
         "On remote routes, the address of the next system en route;
         Otherwise, zero."
      ::= { rtmRouteEntry 8 }

  rtmRouteIfIndex OBJECT-TYPE
      SYNTAX   Integer32 (0..2147483647)
      MAX-ACCESS not-accessible
      STATUS   current
      DESCRIPTION
         "The ifIndex value which identifies the local
         interface through which the next hop of this
         route should be reached."
      ::= { rtmRouteEntry 9 }

  rtmRouteType OBJECT-TYPE
      SYNTAX   RouteType
      MAX-ACCESS read-only
      STATUS   current
      DESCRIPTION
         "The type of route.  local(3) refers
         to a route for which the next hop is the final
         destination.  remote(4) refers to a route for
         which the next hop is not the final destination.

         Routes which do not result in traffic forwarding or
         rejection should not be displayed even if the
         implementation keeps them stored internally.


         reject (2) refers to a route which, if matched, discards
         the message as unreachable. This is used in some
         protocols as a means of correctly aggregating routes."
      ::= { rtmRouteEntry 10 }

  rtmRouteProto OBJECT-TYPE
      SYNTAX   IANAipRouteProtocol
      MAX-ACCESS read-only
      STATUS   current
      DESCRIPTION
         "The routing mechanism via which this route was learned.  Inclusion
         of values for gateway routing protocols is not intended to imply that
         hosts should support those protocols."
      ::= { rtmRouteEntry 11 }

  rtmRouteAge OBJECT-TYPE
      SYNTAX   Integer32
      MAX-ACCESS read-only
      STATUS   current
      DESCRIPTION
         "The number of seconds since this route was last updated or otherwise
         determined to be correct.  Note that no semantics of `too old' can
         be implied except through knowledge of the routing protocol by which
         the route was learned.

         This age is only accurate for entries which are less that 49 days
         old."
      DEFVAL  { 0 }
      ::= { rtmRouteEntry 12 }

  rtmRouteInfo OBJECT-TYPE
      SYNTAX   RouteInfo
      MAX-ACCESS read-only
      STATUS   current
      DESCRIPTION
         "A reference to MIB definitions specific to the particular routing
         protocol which is responsible for this route, as determined by the
         value specified  in the route's ipCidrRouteProto value.

         RTM returns an integer representation of the OID defined in RFC
         2096."
      DEFVAL { none }
      ::= { rtmRouteEntry 13 }

  rtmRouteNextHopAS OBJECT-TYPE
      SYNTAX   Integer32
      MAX-ACCESS read-only
      STATUS   current
      DESCRIPTION
         "The Autonomous System Number of the Next Hop.
         The semantics of this object are determined by
         the routing-protocol specified in the route's
         rtmRouteProto value. When this object is
         unknown or not relevant its value should be set
         to zero."
      DEFVAL { 0 }
      ::= { rtmRouteEntry 14 }

  rtmRouteMetric1 OBJECT-TYPE
      SYNTAX   Integer32
      MAX-ACCESS read-only
      STATUS   current
      DESCRIPTION
         "The primary routing metric for this route.
         The semantics of this metric are determined by
         the routing-protocol specified in the route's
         rtmRouteProto value.  If this metric is not
         used, its value should be set to -1."
      DEFVAL { -1 }
      ::= { rtmRouteEntry 15 }

  rtmRouteMetric2 OBJECT-TYPE
      SYNTAX   Integer32
      MAX-ACCESS read-only
      STATUS   current
      DESCRIPTION
         "An alternate routing metric for this route.
         The semantics of this metric are determined by
         the routing-protocol specified in the route's
         rtmRouteProto value.  If this metric is not
         used, its value should be set to -1."
      DEFVAL { -1 }
      ::= { rtmRouteEntry 16 }

  rtmRouteMetric3 OBJECT-TYPE
      SYNTAX   Integer32
      MAX-ACCESS read-only
      STATUS   current
      DESCRIPTION
         "An alternate routing metric for this route.
         The semantics of this metric are determined by
         the routing-protocol specified in the route's
         rtmRouteProto value.  If this metric is not
         used, its value should be set to -1."
      DEFVAL { -1 }
      ::= { rtmRouteEntry 17 }

  rtmRouteMetric4 OBJECT-TYPE
      SYNTAX   Integer32
      MAX-ACCESS read-only
      STATUS   current
      DESCRIPTION
         "An alternate routing metric for this route.
         The semantics of this metric are determined by
         the routing-protocol specified in the route's
         rtmRouteProto value.  If this metric is not
         used, its value should be set to -1."
      DEFVAL { -1 }
      ::= { rtmRouteEntry 18 }

  rtmRouteMetric5 OBJECT-TYPE
      SYNTAX   Integer32
      MAX-ACCESS read-only
      STATUS   current
      DESCRIPTION
         "An alternate routing metric for this route.
         The semantics of this metric are determined by
         the routing-protocol specified in the route's
         rtmRouteProto value.  If this metric is not
         used, its value should be set to -1."
      DEFVAL { -1 }
      ::= { rtmRouteEntry 19 }

-------------------------------------------------------------------------------

--  DC-RTM RIB Table.
--  This table is used to examine the routes known to DC-RTM.

  rtmRibTable OBJECT-TYPE
      SYNTAX   SEQUENCE OF RtmRibEntry
      MAX-ACCESS not-accessible
      STATUS   current
      DESCRIPTION
         "Read-only copy of this entity's Routing Information Base.
         This is the complete set of routes known by DC-RTM and is a
         superset of the routes accessible through the rtmRouteMib
         (which accesses only the active routes from the Forwarding
         Information Base)."
      ::= { rtmObjects 7 }

  rtmRibEntry OBJECT-TYPE
      SYNTAX   RtmRibEntry
      MAX-ACCESS not-accessible
      STATUS   current
      DESCRIPTION
         "A particular entry in the Routing Information Base."
      INDEX {
          rtmRibFteIndex,
          rtmRibDestType,
          rtmRibDest,
          rtmRibDestLen,
          rtmRibTos,
          rtmRibNextHopType,
          rtmRibNextHop,
          rtmRibIfIndex,
          rtmRibProto,
          rtmRibRpmIndex
          }
      ::= { rtmRibTable 1 }

  RtmRibEntry ::= SEQUENCE {
          rtmRibFteIndex          FteIndex,
          rtmRibStatus            RowStatus,
          rtmRibDestType          InetAddressType,
          rtmRibDest              InetAddress,
          rtmRibDestLen           Integer32,
          rtmRibTos               Integer32,
          rtmRibNextHopType       InetAddressType,
          rtmRibNextHop           InetAddress,
          rtmRibIfIndex           Integer32,
          rtmRibType              RouteType,
          rtmRibProto             IANAipRouteProtocol,
          rtmRibAge               Integer32,
          rtmRibInfo              RouteInfo,
          rtmRibNextHopAS         Integer32,
          rtmRibMetric1           Integer32,
          rtmRibMetric2           Integer32,
          rtmRibMetric3           Integer32,
          rtmRibMetric4           Integer32,
          rtmRibMetric5           Integer32,
          rtmRibFibRoute          TruthValue,
          rtmRibRpmIndex          Integer32
      }

  rtmRibFteIndex OBJECT-TYPE
       SYNTAX      FteIndex
       MAX-ACCESS  not-accessible
       STATUS      current
       DESCRIPTION
          "The HAF entity index identifying the instance of DC-RTM to which
          this RIB entry applies."
       ::= { rtmRibEntry 1 }

  rtmRibStatus OBJECT-TYPE
      SYNTAX   RowStatus
      MAX-ACCESS read-only
      STATUS   current
      DESCRIPTION
         "The row status variable, used according to
         row installation and removal conventions."
      ::= { rtmRibEntry 2 }

  rtmRibDestType OBJECT-TYPE
      SYNTAX      InetAddressType
      MAX-ACCESS  not-accessible
      STATUS      current
      DESCRIPTION
         "The type of the address used as the destination IP address
          for this route."
      ::= { rtmRibEntry 3 }

  rtmRibDest OBJECT-TYPE
      SYNTAX      InetAddress (SIZE(4|16))
      MAX-ACCESS  not-accessible
      STATUS      current
      DESCRIPTION
         "The destination IP address of this route."
      ::= { rtmRibEntry 4 }

  rtmRibDestLen OBJECT-TYPE
      SYNTAX   Integer32  (0..128)
      MAX-ACCESS not-accessible
      STATUS   current
      DESCRIPTION
         "Indicate the mask length (in bits) to be logical-ANDed with the
         destination address before being compared to
         the value in the rtmRibDest field.  For those
         systems that do not support arbitrary subnet
         masks, an agent constructs the value of the
         rtmRibMask by reference to the IP Address
         Class."
      ::= { rtmRibEntry 5 }

  -- The following convention is included for specification
  -- of TOS Field contents.  At this time, the Host Requirements
  -- and the Router Requirements documents disagree on the width
  -- of the TOS field.  This mapping describes the Router
  -- Requirements mapping, and leaves room to widen the TOS field
  -- without impact to fielded systems.

  rtmRibTos OBJECT-TYPE
      SYNTAX   Integer32 (0..15)
      MAX-ACCESS not-accessible
      STATUS   current
      DESCRIPTION
         "The policy specifier is the IP TOS Field.  The encoding
         of IP TOS is as specified by the following convention.
         Zero indicates the default path if no more specific
         policy applies.

         +-----+-----+-----+-----+-----+-----+-----+-----+
         |                 |                       |     |
         |   PRECEDENCE    |    TYPE OF SERVICE    |  0  |
         |                 |                       |     |
         +-----+-----+-----+-----+-----+-----+-----+-----+

                  IP TOS                IP TOS
             Field     Policy      Field     Policy
             Contents    Code      Contents    Code
             0 0 0 0  ==>   0      0 0 0 1  ==>   2
             0 0 1 0  ==>   4      0 0 1 1  ==>   6
             0 1 0 0  ==>   8      0 1 0 1  ==>  10
             0 1 1 0  ==>  12      0 1 1 1  ==>  14
             1 0 0 0  ==>  16      1 0 0 1  ==>  18
             1 0 1 0  ==>  20      1 0 1 1  ==>  22
             1 1 0 0  ==>  24      1 1 0 1  ==>  26
             1 1 1 0  ==>  28      1 1 1 1  ==>  30

         RTM always returns a default value of 0 for this field."
      ::= { rtmRibEntry 6 }

  rtmRibNextHopType OBJECT-TYPE
      SYNTAX     InetAddressType
      MAX-ACCESS not-accessible
      STATUS     current
      DESCRIPTION
         "The type of the address used as the next-hop address
          for this route."
      ::= { rtmRibEntry 7 }

  rtmRibNextHop OBJECT-TYPE
      SYNTAX     InetAddress (SIZE(4|16))
      MAX-ACCESS not-accessible
      STATUS     current
      DESCRIPTION
         "On remote routes, the address of the next system en route;
         Otherwise, zero."
      ::= { rtmRibEntry 8 }

  rtmRibIfIndex OBJECT-TYPE
      SYNTAX   Integer32 (0..2147483647)
      MAX-ACCESS not-accessible
      STATUS   current
      DESCRIPTION
         "The ifIndex value which identifies the local
         interface through which the next hop of this
         route should be reached."
      ::= { rtmRibEntry 9 }

  rtmRibType OBJECT-TYPE
      SYNTAX   RouteType
      MAX-ACCESS read-only
      STATUS   current
      DESCRIPTION
         "The type of route.  local(3) refers
         to a route for which the next hop is the final
         destination.   remote(4) refers to a route for
         which the next hop is not the final destination.

         Routes which do not result in traffic forwarding or
         rejection should not be displayed even if the
         implementation keeps them stored internally.


         reject (2) refers to a route which, if matched, discards
         the message as unreachable. This is used in some
         protocols as a means of correctly aggregating routes."
      ::= { rtmRibEntry 10 }

  rtmRibProto OBJECT-TYPE
      SYNTAX   IANAipRouteProtocol
      MAX-ACCESS not-accessible
      STATUS   current
      DESCRIPTION
         "The routing mechanism via which this route was learned.  Inclusion
         of values for gateway routing protocols is not intended to imply that
         hosts should support those protocols."
      ::= { rtmRibEntry 11 }

  rtmRibAge OBJECT-TYPE
      SYNTAX   Integer32
      MAX-ACCESS read-only
      STATUS   current
      DESCRIPTION
         "The number of seconds since this route was last updated or otherwise
         determined to be correct.  Note that no semantics of `too old' can
         be implied except through knowledge of the routing protocol by which
         the route was learned.

         This age is only accurate for entries which are less that 49 days
         old."
      DEFVAL  { 0 }
      ::= { rtmRibEntry 12 }

  rtmRibInfo OBJECT-TYPE
      SYNTAX   RouteInfo
      MAX-ACCESS read-only
      STATUS   current
      DESCRIPTION
         "A reference to MIB definitions specific to the particular routing
         protocol which is responsible for this route, as determined by the
         value specified  in the route's rtmRibProto value.

         RTM returns an integer representation of the OID defined in RFC
         2096."
      DEFVAL { none }
      ::= { rtmRibEntry 13 }

  rtmRibNextHopAS OBJECT-TYPE
      SYNTAX   Integer32
      MAX-ACCESS read-only
      STATUS   current
      DESCRIPTION
         "The Autonomous System Number of the Next Hop.
         The semantics of this object are determined by
         the routing-protocol specified in the route's
         rtmRibProto value. When this object is unknown
         or not relevant its value is returned as zero."
      DEFVAL { 0 }
      ::= { rtmRibEntry 14 }

  rtmRibMetric1 OBJECT-TYPE
      SYNTAX   Integer32
      MAX-ACCESS read-only
      STATUS   current
      DESCRIPTION
         "The primary routing metric for this route.
         The semantics of this metric are determined by
         the routing-protocol specified in the route's
         rtmRibProto value.  If this metric is not used,
         its value is returned as -1."
      DEFVAL { -1 }
      ::= { rtmRibEntry 15 }

  rtmRibMetric2 OBJECT-TYPE
      SYNTAX   Integer32
      MAX-ACCESS read-only
      STATUS   current
      DESCRIPTION
         "An alternate routing metric for this route.
         The semantics of this metric are determined by
         the routing-protocol specified in the route's
         rtmRibProto value.  If this metric is not used,
         its value is returned as -1."
      DEFVAL { -1 }
      ::= { rtmRibEntry 16 }

  rtmRibMetric3 OBJECT-TYPE
      SYNTAX   Integer32
      MAX-ACCESS read-only
      STATUS   current
      DESCRIPTION
         "An alternate routing metric for this route.
         The semantics of this metric are determined by
         the routing-protocol specified in the route's
         rtmRibProto value.  If this metric is not used,
         its value is returned as -1."
      DEFVAL { -1 }
      ::= { rtmRibEntry 17 }

  rtmRibMetric4 OBJECT-TYPE
      SYNTAX   Integer32
      MAX-ACCESS read-only
      STATUS   current
      DESCRIPTION
         "An alternate routing metric for this route.
         The semantics of this metric are determined by
         the routing-protocol specified in the route's
         rtmRibProto value.  If this metric is not used,
         its value is returned as -1."
      DEFVAL { -1 }
      ::= { rtmRibEntry 18 }

  rtmRibMetric5 OBJECT-TYPE
      SYNTAX   Integer32
      MAX-ACCESS read-only
      STATUS   current
      DESCRIPTION
         "An alternate routing metric for this route.
         The semantics of this metric are determined by
         the routing-protocol specified in the route's
         rtmRibProto value.  If this metric is not used,
         its value is returned as -1."
      DEFVAL { -1 }
      ::= { rtmRibEntry 19 }

  rtmRibFibRoute OBJECT-TYPE
    SYNTAX      TruthValue
    MAX-ACCESS  read-only
    STATUS      current
    DESCRIPTION "Indicates whether this route is present in the Forwarding
                Information Base (AMB_TRUE) or not (AMB_FALSE)."
    ::= { rtmRibEntry 20 }

  rtmRibRpmIndex OBJECT-TYPE
    SYNTAX      Integer32 (0..2147483647)
    MAX-ACCESS  not-accessible
    STATUS      current
    DESCRIPTION "The HAF entity index for the RPM that supplied this route,
                or zero for static routes.  This is used to distinguish routes
                in the system where multiple copies of a given protocol (for
                example BGP) are providing routes to DC-RTM."
    ::= { rtmRibEntry 21 }

-------------------------------------------------------------------------------

--  DC-RTM Redist Set Field Table.
--  Table of actions which set fields for routes being redistributed.

  rtmRdstSetFieldTable OBJECT-TYPE
      SYNTAX   SEQUENCE OF RtmRdstSetFieldEntry
      MAX-ACCESS not-accessible
      STATUS   current
      DESCRIPTION "This table defines route attributes which are to be set
                   by redistribution filters.
                   A list of set actions is made up of one or more entries
                   in this table with the same list_id.  Actions in a list
                   are applied in increasing set_number order.  Each list
                   may be referenced by 0, 1 or more redistribution
                   entries.  Only actions which are active at the point
                   where the redistribution entry is being evaluated (i.e.
                   at the point where the route is actually being
                   redistributed) are applied.  Also, only those set
                   actions which are relevant to the route being
                   redistributed are applied, so BGP attributes will not
                   be set for a route being redistributed to OSPF."
      ::= { rtmObjects 8 }

  rtmRdstSetFieldEntry OBJECT-TYPE
      SYNTAX   RtmRdstSetFieldEntry
      MAX-ACCESS not-accessible
      STATUS   current
      DESCRIPTION
         "A particular entry in the Redistribution Set Field table."
      INDEX {
          rtmRdstSetFieldFteIndex,
          rtmRdstSetFieldListId,
          rtmRdstSetFieldNumber
          }
      ::= { rtmRdstSetFieldTable 1 }

  RtmRdstSetFieldEntry ::= SEQUENCE {
          rtmRdstSetFieldFteIndex          FteIndex,
          rtmRdstSetFieldListId            Unsigned32,
          rtmRdstSetFieldNumber            Unsigned32,
          rtmRdstSetFieldRowStatus         RowStatus,
          rtmRdstSetFieldType              RdstSetFieldType,
          rtmRdstSetFieldValue             OCTET STRING
      }

  rtmRdstSetFieldFteIndex OBJECT-TYPE
      SYNTAX      FteIndex
      MAX-ACCESS  not-accessible
      STATUS      current
      DESCRIPTION
         "The HAF entity index identifying the instance of DC-RTM to
          which this set field entry applies."
      ::= { rtmRdstSetFieldEntry 1 }

  rtmRdstSetFieldListId OBJECT-TYPE
      SYNTAX      Unsigned32 (1..4294967295)
      MAX-ACCESS  not-accessible
      STATUS      current
      DESCRIPTION
         "The index of the list of set actions which this action belongs
          to.  It is this identifier which is referenced by the
          redistribution table entry.  A value of 0 is not permitted."
      ::= { rtmRdstSetFieldEntry 2 }

  rtmRdstSetFieldNumber OBJECT-TYPE
      SYNTAX      Unsigned32 (1..4294967295)
      MAX-ACCESS  not-accessible
      STATUS      current
      DESCRIPTION
         "Identifies this set field entry's position in the list of set
          field entries with the same list identifier."
      ::= { rtmRdstSetFieldEntry 3 }

  rtmRdstSetFieldRowStatus OBJECT-TYPE
      SYNTAX   RowStatus
      MAX-ACCESS read-create
      STATUS   current
      DESCRIPTION
         "Used to create and delete a DC-RTM set field table entry."
      ::= { rtmRdstSetFieldEntry 4 }

  rtmRdstSetFieldType OBJECT-TYPE
      SYNTAX   RdstSetFieldType
      MAX-ACCESS read-create
      STATUS   current
      DESCRIPTION
         "The type of field set by this set field entry."
      ::= { rtmRdstSetFieldEntry 5 }

  rtmRdstSetFieldValue OBJECT-TYPE
	  SYNTAX OCTET STRING (SIZE(0..8))
      MAX-ACCESS read-create
      STATUS   current
      DESCRIPTION
         "The value set by this set field entry."
      ::= { rtmRdstSetFieldEntry 6 }

-- Conformance Information.

  rtmConformance  OBJECT IDENTIFIER ::= { rtmMib 2 }

  rtmCompliances  OBJECT IDENTIFIER ::= { rtmConformance 1 }
  rtmGroups       OBJECT IDENTIFIER ::= { rtmConformance 2 }

  rtmCompliance MODULE-COMPLIANCE
    STATUS current
    DESCRIPTION
        "The compliance statement for the DC-RTM module."
    MODULE

    MANDATORY-GROUPS    {
       rtmEntityMandatoryGroup,
       rtmRedistMandatoryGroup,
       rtmStaticRtMandatoryGroup,
       rtmMjMandatoryGroup,
       rtmSjMandatoryGroup,
       rtmRdstSetFieldMandatoryGroup
    }

    GROUP rtmEntityGroup
    DESCRIPTION
        "Optional objects for rtmEntityTable."

    GROUP rtmRedistGroup
    DESCRIPTION
        "Optional objects for rtmRedistTable."

    GROUP rtmStaticRtGroup
    DESCRIPTION
        "Optional objects for rtmStaticRtTable."

    GROUP rtmMjGroup
    DESCRIPTION
        "Optional objects for rtmMjTable."

    GROUP rtmSjGroup
    DESCRIPTION
        "Optional objects for rtmSjTable."

    GROUP rtmRouteGroup
    DESCRIPTION
        "Optional objects for rtmRouteTable."

    GROUP rtmRibGroup
    DESCRIPTION
        "Optional objects for rtmRibTable."

    ::= { rtmCompliances 1 }

-- Units of conformance (Groups).

rtmEntityMandatoryGroup OBJECT-GROUP
    OBJECTS {
       rtmEntityRowStatus
    }
    STATUS  current
    DESCRIPTION
         "Mandatory objects for the rtmEntityTable."
    ::= { rtmGroups 1 }


rtmEntityGroup OBJECT-GROUP
    OBJECTS {
       rtmEntityAdminStat,
       rtmEntityOperStatus,
       rtmEntityDsConnctd,
       rtmEntityDsStatDf,
       rtmEntityDsOspfInt,
       rtmEntityDsOspfExt,
       rtmEntityDsIntBgp,
       rtmEntityDsExtBgp,
       rtmEntityDsIsisInt1,
       rtmEntityDsIsisInt2,
       rtmEntityDsIsisExt1,
       rtmEntityDsIsisExt2,
       rtmEntityDsRip,
       rtmEntityDsEgp,
       rtmEntityDsGgp,
       rtmEntityDsHello,
       rtmEntityDsEsis,
       rtmEntityDsBbnspfigp,
       rtmEntityDsIdpr,
       rtmEntityDsIgrp,
       rtmEntityDsEigrpSmm,
       rtmEntityDsIntEigrp,
       rtmEntityDsEigrpExt,
       rtmEntityDsUnknown,
       rtmEntityEqlCostOpt,
       rtmEntityDelDeadRte,
       rtmEntityDeadRpmTmr,
       rtmEntityRouteNumber,
       rtmEntityAddressFamily,
       rtmEntityDsDvmrp
    }
    STATUS  current
    DESCRIPTION
         "Optional objects for rtmEntityTable."
    ::= { rtmGroups 2 }

rtmRedistMandatoryGroup OBJECT-GROUP
    OBJECTS  {
         rtmRedistRowStatus
    }
    STATUS  current
    DESCRIPTION
         "Mandatory objects for rtmRedistTable."
    ::= { rtmGroups 3 }

rtmRedistGroup OBJECT-GROUP
    OBJECTS  {
         rtmRedistAdminStat,
         rtmRedistPriority,
         rtmRedistInfoSrc,
         rtmRedistSrcInstFlt,
         rtmRedistSrcInst,
         rtmRedistInfoDest,
         rtmRedistDestInstFlt,
         rtmRedistDestInst,
         rtmRedistAddrFilterType,
         rtmRedistAddrFilter,
         rtmRedistAddrFltLen,
         rtmRedistHopFltValType,
         rtmRedistHopFltVal,
         rtmRedistHopFltLen,
         rtmRedistIfIndexFlt,
         rtmRedistIfIndex,
         rtmRedistPathtypeFlt,
         rtmRedistPathType,
         rtmRedistOspfAreaFlt,
         rtmRedistOspfArea,
         rtmRedistOspfTagFlt,
         rtmRedistOspfTag,
         rtmRedistCommunityFlt,
         rtmRedistCommunity,
         rtmRedistExtCommFlt,
         rtmRedistExtComm,
         rtmRedistRedistFlag,
         rtmRedistMetricConv,
         rtmRedistMetricValue,
         rtmRedistNwPathType,
         rtmRedistNwOspfTag,
         rtmRedistOspfPropagate,
         rtmRedistNwOrigin,
         rtmRedistAddMed,
         rtmRedistNwMed,
         rtmRedistAddLocalPref,
         rtmRedistNwLocalPref,
         rtmRedistSetListId
    }
    STATUS  current
    DESCRIPTION
         "Optional objects for rtmRedistTable."
    ::= { rtmGroups 4 }

rtmStaticRtMandatoryGroup OBJECT-GROUP
    OBJECTS  {
         rtmStaticRtRowStatus
    }
    STATUS current
    DESCRIPTION
         "Mandatory objects for rtmStaticRtTable."
    ::= { rtmGroups 5 }

rtmStaticRtGroup OBJECT-GROUP
    OBJECTS  {
         rtmStaticRtAdminStat,
         rtmStaticRtOverride,
         rtmStaticRtAdminDist,
         rtmStaticRtAction,
         rtmStaticRtFwdAddrType,
         rtmStaticRtForwardingAddr,
         rtmStaticRtPathType
    }
    STATUS  current
    DESCRIPTION
         "Optional objects for rtmStaticRtTable."
    ::= { rtmGroups 6 }

rtmMjMandatoryGroup OBJECT-GROUP
    OBJECTS  {
      rtmMjRowStatus
    }
    STATUS  current
    DESCRIPTION
         "Mandatory objects for rtmMjTable."
    ::= { rtmGroups 7 }

rtmMjGroup OBJECT-GROUP
    OBJECTS  {
      rtmMjIfType,
      rtmMjAdminStatus,
      rtmMjOperStatus,
      rtmMjJoinStatus
    }
    STATUS  current
    DESCRIPTION
         "Optional objects for rtmMjTable."
    ::= { rtmGroups 8 }

rtmSjMandatoryGroup OBJECT-GROUP
    OBJECTS  {
      rtmSjIfType,
      rtmSjMastFteType,
      rtmSjMastFteId
    }
    STATUS  current
    DESCRIPTION
         "Mandatory objects for rtmSjTable."
    ::= { rtmGroups 9 }

rtmSjGroup OBJECT-GROUP
    OBJECTS  {
      rtmSjJoinStatus
    }
    STATUS  current
    DESCRIPTION
         "Optional objects for rtmSjTable."
    ::= { rtmGroups 10 }

rtmRouteGroup OBJECT-GROUP
    OBJECTS   {
          rtmRouteStatus,
          rtmRouteType,
          rtmRouteProto,
          rtmRouteAge,
          rtmRouteInfo,
          rtmRouteNextHopAS,
          rtmRouteMetric1,
          rtmRouteMetric2,
          rtmRouteMetric3,
          rtmRouteMetric4,
          rtmRouteMetric5
     }
     STATUS  current
     DESCRIPTION
          "Optional objects for rtmRouteTable."
     ::= { rtmGroups 11 }

rtmRibGroup OBJECT-GROUP
    OBJECTS   {
          rtmRibStatus,
          rtmRibType,
          rtmRibAge,
          rtmRibInfo,
          rtmRibNextHopAS,
          rtmRibMetric1,
          rtmRibMetric2,
          rtmRibMetric3,
          rtmRibMetric4,
          rtmRibMetric5,
          rtmRibFibRoute
     }
     STATUS  current
     DESCRIPTION
          "Optional objects for rtmRibTable."
     ::= { rtmGroups 12 }

rtmObsoleteGroup OBJECT-GROUP
     OBJECTS  {
          rtmRedistAddCommunity,
          rtmRedistNwCommunity,
          rtmRedistAddExtComm,
          rtmRedistNwExtComm
     }
     STATUS obsolete
     DESCRIPTION
          "This group contains obsolete objects."
     ::= { rtmGroups 13 }

rtmRdstSetFieldMandatoryGroup OBJECT-GROUP
    OBJECTS  {
         rtmRdstSetFieldRowStatus,
         rtmRdstSetFieldType,
         rtmRdstSetFieldValue
    }
    STATUS  current
    DESCRIPTION
         "Mandatory objects for rtmRdstSetFieldTable."
    ::= { rtmGroups 14 }

END
