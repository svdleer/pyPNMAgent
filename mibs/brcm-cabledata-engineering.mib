--**************************************************************************
--                                                                          
--    Copyright 2002 Broadcom Corporation                                   
--    All Rights Reserved                                                   
--    No portions of this material may be reproduced in any form without the
--    written permission of:                                                
--             Broadcom Corporation                                         
--             16251 Laguna Canyon Road                                     
--             Irvine, California  92618                                    
--    All information contained in this document is Broadcom Corporation    
--    company private, proprietary, and trade secret.                       
--                                                                          
--                                                                          
--                                                                          
--**************************************************************************
--    Filename: brcm-cabledata-engineering.mib
--    Author:   Kevin O'Neal
--    Creation Date: 22-october-2002
--
--**************************************************************************
--    Description:
--
--		engineering MIB for cabledata
--		
--**************************************************************************
--    Revision History:
--
--**************************************************************************

BRCM-CABLEDATA-ENGINEERING-MIB DEFINITIONS ::= BEGIN

IMPORTS
    MODULE-IDENTITY,
    OBJECT-TYPE,
    Unsigned32,
    Integer32,
    IpAddress
        FROM SNMPv2-SMI
    TruthValue,
    DisplayString,
    MacAddress
        FROM SNMPv2-TC
    cableDataPrivateMIBObjects
        FROM BRCM-CABLEDATA-PRIVATE-MIB;
                
cableDataEngineering MODULE-IDENTITY
    LAST-UPDATED "200210220000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadcom cabledata factory MIB"
    REVISION      "200206040000Z"
    DESCRIPTION
            "Initial version of this MIB module."
    ::= { cableDataPrivateMIBObjects 3 }

cableDataEngineeringBase OBJECT IDENTIFIER ::= { cableDataEngineering 1 }

cdEngrMemAccessAddress OBJECT-TYPE
    SYNTAX      Unsigned32
    MAX-ACCESS  read-write
    STATUS      current
    DESCRIPTION
        "The memory address to access when executing a cdEngrMemAccessCommand 
         operation."
    ::= { cableDataEngineeringBase 1 }
    
cdEngrMemAccessNumBytes OBJECT-TYPE
    SYNTAX      Unsigned32 (1..4)
    MAX-ACCESS  read-write
    STATUS      current
    DESCRIPTION
        "The number of bytes to read or write when executing a 
         cdEngrMemAccessCommand operation."
    ::= { cableDataEngineeringBase 2 }
    
cdEngrMemAccessData OBJECT-TYPE
    SYNTAX      Unsigned32
    MAX-ACCESS  read-write
    STATUS      current
    DESCRIPTION
        "The data read from or to be written to the device when executing a 
         cdEngrMemAccessCommand operation."
    ::= { cableDataEngineeringBase 3 }
    
cdEngrMemAccessCommand OBJECT-TYPE
    SYNTAX      INTEGER {
                read(0),
                write(1)
    }
    MAX-ACCESS  read-write
    STATUS      current
    DESCRIPTION
        "Setting this value to read(0) will cause the number of bytes specified
         in cdEngrMemAccessNumBytes to be read from the address specified by
         cdEngrMemAccessAddress, and the resulting data will be available
         in cdEngrMemAccessData.  Setting this value to write(1) will cause the
         number of bytes specified in cdEngrMemAccessNumBytes to be written to 
         the memory address specified in cdEngrMemAccessAddress, using the data
         specified in cdEngrMemAccessData."
    ::= { cableDataEngineeringBase 4 }
    
END
