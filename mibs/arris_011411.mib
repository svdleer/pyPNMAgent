ARRIS-MIB DEFINITIONS ::= BEGIN

IMPORTS
    MODULE-IDENTITY, enterprises
            FROM SNMPv2-SMI;

arris MODULE-IDENTITY
    LAST-UPDATED    "201101140000Z" -- January 14, 2011
    ORGANIZATION    "Arris Interactive"
    CONTACT-INFO   
        "Chris Hare
         Postal: Arris Interactive
                 3871 Lakefield Drive
                 Suite 300
                 Suwanee, GA 30024-1242
                 U.S.A.
                 Phone:  +1 770 473 5165
                 E-mail: chris.hare@arrisi.com"
   
    DESCRIPTION
        "This is a header for the Arris Docsis 3.0 enterprise MIB.  All objects appear
         elsewhere."        
                  
-- Revision history 
	REVISION "201101140000Z" -- January 14, 2011
         DESCRIPTION
             "Reserver .50->.59 for FMC"      
	REVISION "201101130000Z" -- January 13, 2011
         DESCRIPTION
             "Renumbered arrisProIdRouter and arrisProdIdMoxi and reserved OID ranges for other products i.e. ServAssure, and OnDemand"      
      REVISION "201002230000Z" -- February 23, 2010
         DESCRIPTION
             "Added arrisProIdRouter and arrisProdIdMoxi and fixed minor validation errors"      
    ::= { enterprises 4115 }

arrisProducts OBJECT IDENTIFIER ::= { arris 1 }   

-- Arris Product Lines
packetport       OBJECT IDENTIFIER ::= { arrisProducts 1 }
cm110            OBJECT IDENTIFIER ::= { arrisProducts 2 }  
arrisProdIdCM    OBJECT IDENTIFIER ::= { arrisProducts 3 }  -- Cable Modem
arrisProdIdCMTS  OBJECT IDENTIFIER ::= { arrisProducts 4 }  -- Cable Modem Termination System
arrisProdIdMRC   OBJECT IDENTIFIER ::= { arrisProducts 5 }  -- Modular Redundant Chassis
arrisProdIdGlobalAccess  OBJECT IDENTIFIER ::= { arrisProducts 6 }  -- Global Access (Fiber) products
arrisTools			OBJECT IDENTIFIER ::= { arrisProducts 7 }  -- Arris Tools
arrisProdIdVideo  OBJECT IDENTIFIER ::= { arrisProducts 8 }  -- Video Products (D5 et al)

-- Arris E6 reserved arrisProducts 9 ?



-- Arris eRouter and Video products
-- Reserved OIDs [20..29]
arrisProdIdRouter	OBJECT IDENTIFIER ::= { arrisProducts 20 }  -- Arris Router/Gateway products (non-video)
arrisProdIdMG		OBJECT IDENTIFIER ::= { arrisProducts 25 }  -- Arris Multimedia Gateway and IP STB Products


-- Arris Assurance products
-- Reserved OIDs [30..39]
arrisProdIdAssurance       OBJECT IDENTIFIER ::= { arrisProducts 30 }  -- Arris Assurance products


-- Arris OnDemand products - i.e. Video Server, Ad Insertion, CMM
-- Reserved OIDs [40..49]

-- Arris FMC products
-- Reserved OIDs [50..59]



-- Product Identifiers for the CM product line
tcm             OBJECT IDENTIFIER ::= { arrisProdIdCM 8 }      -- Touchstone Cable Modem
ttm             OBJECT IDENTIFIER ::= { arrisProdIdCM 9 }      -- Touchstone Telephony Modem 
ttp             OBJECT IDENTIFIER ::= { arrisProdIdCM 10 }     -- Touchstone Telephony Port

-- Product Identifiers for the CMTS product line (br-032712 added 3,4,5)
cmtsMSAS OBJECT IDENTIFIER ::= { arrisProdIdCMTS 1 } -- CMTS MultiService Access System    
cmtsC3   OBJECT IDENTIFIER ::= { arrisProdIdCMTS 3 } -- C3 CMTS  
cmtsC4   OBJECT IDENTIFIER ::= { arrisProdIdCMTS 4 } -- C4 CMTS  
cmtsCommon   OBJECT IDENTIFIER ::= { arrisProdIdCMTS 5 } -- all CX CMTS  

-- Product Identifiers for the MRC product line
mrcController OBJECT IDENTIFIER ::= { arrisProdIdMRC 1 } -- MRC Controller
                    
-- Global Access products
arrisGlobalAccessMib OBJECT IDENTIFIER ::= { arrisProdIdGlobalAccess 1 }
       -- arrisUas FttH Universal Access Switch is arrisGlobalAccessMib.1. See ARRIS-UAS-MIB

-- add Global Access sysObjectId values here.
arrisGlobalAccessProductUas OBJECT IDENTIFIER ::= { arrisProdIdGlobalAccess 2 } -- FttH Universal Access Switch



END
