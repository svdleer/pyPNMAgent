--**************************************************************************
--    Description:
--
--		private MIB for runtime (not factory) CM management
--		
--**************************************************************************
--    Revision History:
--
--**************************************************************************

UBEE-CM-MGMT-EXT-MIB DEFINITIONS ::= BEGIN

IMPORTS
    MODULE-IDENTITY,
    OBJECT-TYPE,
    Integer32
        FROM SNMPv2-SMI
    ubeeCableDataMgmt
        FROM UBEE-CABLEDATA-MGMT-MIB;
                
cmMgmtExt MODULE-IDENTITY
    LAST-UPDATED "200702050000Z"
    ORGANIZATION "Ubee Interactive Corporation"
    CONTACT-INFO
        "	Ubee Interactive Global Headquarters

        Postal: 6F-9, No.38, Taiyuan St.
        		Jhubei City Hsinchu County 302
        		Taiwan, R.O.C.

           Tel: +886-3-560-0010

        E-mail: asupport@ubeeinteractive.com"
    DESCRIPTION
        "Ubee CM management extension MIB.  This MIB is supported only for 
         products implementing the Ubee CM vendor extension."
    ::= { ubeeCableDataMgmt 2 }
    
cmMgmtExtBase OBJECT IDENTIFIER ::= { cmMgmtExt 1 }
    
cmMgmtExtScan OBJECT IDENTIFIER ::= { cmMgmtExt 2 }

cmScanPushFrequency OBJECT-TYPE
    SYNTAX      Integer32 (0..1000000000)
    UNITS       "hertz"
    MAX-ACCESS  read-write
    STATUS      current
    DESCRIPTION
        "Setting this object will add a new entry to the cmScanTable.  The new
         entry will have a cmScanFrequency value equal to the value set to
         this object.  The index (cmScanIndex) of the new entry will be 1.  
         Any existing entries will be re-indexed starting at 2.  If the table is 
         full, the last entry in the table will be dropped.  If the value set 
         here already exists in the table, it will be moved from its current 
         position in the table to become entry 1 (a duplicate entry will not be 
         added).   Setting this object to a value of 0  will flush the 
         cmScanTable.  When read, this object always returns 0."
    ::= { cmMgmtExtScan 1 }

cmScanTable  OBJECT-TYPE
    SYNTAX      SEQUENCE OF CmScanEntry
    MAX-ACCESS  not-accessible
    STATUS      current
    DESCRIPTION
        "A table of the most recent known good frequencies to which the CM
         has registered.  The most recent good frequency will be at index
         1, with subsequent entries being in chronological order from newest
         to oldest.  Note that the table will not grow unbounded.  Once the
         maximum number of entries is reached, the oldest entries will be
         discarded."
    ::= { cmMgmtExtScan 2 }
    
cmScanEntry OBJECT-TYPE
    SYNTAX      CmScanEntry
    MAX-ACCESS  not-accessible
    STATUS      current
    DESCRIPTION
        "An entry which identifies a downstream frequency to which the CM has
         recently successfully registered."
    INDEX   { cmScanIndex }
    ::= { cmScanTable 1 }
    
CmScanEntry ::= 
    SEQUENCE    {
                cmScanIndex     Integer32,
                cmScanFrequency Integer32
    }
    
cmScanIndex OBJECT-TYPE
    SYNTAX      Integer32 (1..128)
    MAX-ACCESS  not-accessible
    STATUS      current
    DESCRIPTION
        "Identifies the instance of this scan entry."
    ::= { cmScanEntry 1 }

cmScanFrequency OBJECT-TYPE
    SYNTAX      Integer32
    UNITS       "hertz"
    MAX-ACCESS  read-only
    STATUS      current
    DESCRIPTION
        "A downstream frequency to which the CM has recently successfully 
         registered, or which has been provisioned by way of a set to
         cmScanPushFrequency."
    REFERENCE 
         "docsIfDownChannelFrequency from DOCS-IF-MIB" 
    ::= { cmScanEntry 2 }
    
     
cmMgmtExtBaseStandbySwitchStatus OBJECT-TYPE
    SYNTAX      INTEGER {						
                on(1),
                off(2)
    }
    MAX-ACCESS  read-write
    STATUS      current
    DESCRIPTION
        "Reports/Sets the position of the standby switch. 
          
         A GET on this object returns the current state of the standby switch.
         
         A SET to a value of 'on(1)'  enables standby mode for the device.
         A SET to a value of 'off(2)' disables standby mode for the device.
	  
         When standby-mode is enabled 'on(1)', the device blocks WAN data traffic
         to/from the CPEs."  
    ::= { cmMgmtExtBase 1 }

        
END
