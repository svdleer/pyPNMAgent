SEM-MIB DEFINITIONS ::= BEGIN


IMPORTS
        MODULE-IDENTITY,
        IpAddress,
        TimeTicks,
        OBJECT-TYPE,
        NOTIFICATION-TYPE,
        Counter32,
        Unsigned32,
        Integer32
                                FROM SNMPv2-SMI

        DisplayString           FROM SNMPv2-TC

        giproducts              FROM BCS-IDENT-MIB

        trapIdentifier,
        trapSequenceId,
        trapNetworkElemModelNumber,
        trapNetworkElemSerialNum,
        trapPerceivedSeverity,
        trapNetworkElemOperState,
        trapNetworkElemAlarmStatus,
        trapNetworkElemAdminState,
        trapNetworkElemAvailStatus,
        trapText,
        trapNETrapLastTrapTimeStamp,
        trapChangedObjectId,
        trapAdditionalInfoInteger1,
        trapAdditionalInfoInteger2,
        trapAdditionalInfoInteger3,
        trapChangedValueDisplayString,
        trapChangedValueOID,
        trapChangedValueIpAddress,
        trapChangedValueInteger
                                FROM BCS-TRAPS-MIB;

-- ------------------------------------------------------------------------------

sem     MODULE-IDENTITY
        LAST-UPDATED "200608250000Z"

        ORGANIZATION "Motorola Connected Home Solutions"
        CONTACT-INFO "Motorola Technical Response Center
                      Inside USA     1-888-944-HELP (1-888-944-4357)
                      Outside USA    1-215-323-0044
                      TRC Hours:
                      Monday through Friday 8am - 7pm Eastern Standard Time
                      Saturdays            10am - 5pm Eastern Standard Time"

        DESCRIPTION  "The MIB module for the SEM."

        REVISION     "200608250000Z"
        DESCRIPTION
                     "Version 1.13:

                      August 25, 2006
                      - Changed descriptions of trapHardwareFault, trapLossOfPhysicalInput,
                        and trapOtsUtilizationFault to indicate that the additional info
                        fields are not used.

                      August 21, 2006
                      - Changed description of semUtcOffset to indicate that at the
                        value is not configurable when time source is Input Stream.

                      August 16, 2006
                      - Changed SYNTAX of semOutputStreamErrorTimeLogged and
                        semGbeInputUdpErrorTimeLogged from TimeTicks to Integer32.

                      August 14, 2006
                      - Corrected Number of Programs column of table in
                        description of semOutTransPidsPerProgram.

                      August 08, 2006
                      - Corrected semGbeInputUdpError Count descriptions
                        to use Data and Transport Stream.

                      July 06, 2006
                      - Updated organization and contact information.

                      June 23, 2006
                      - Added semGbeStatInUdpHighBitRateAlarm, semIsaSdv
                        group, semAlarmGbeInputStreamHighBitRate,
                        semConfAlarmEnableGbeInHighBitRate, and
                        trapGbeInputStreamHighBitRate.
                      - Changed semGbeInUdpConfAlarmBitRate to
                        semGbeInUdpConfLowAlarmBitRate.

                      June 20, 2006
                      - Added semInsertQueSubqueueSlotNumber,
                        semGbeInUdpConfRedundForceToSecondary, and
                        semGbeInUdpConfRedundForceToPrimary.

                      June 6, 2006
                      - Added semCurrentDeviceOperatingMode.

                      June 5, 2006
                      - Added isaSdv operating mode enumeration.

                      May 18, 2006
                      - Added semOutputProgramInputPort.

                      April 15, 2006
                      - Added semAutoRebootEnable, semBootReason,
                        and semGbeStatusInputUdpUpdateInterval.

                      April 10, 2006
                      - Removed semGbeStatCommUdpState.
                      - Changed semPidRemappingEnabled, semPidsPerService,
                        semPidMaskingEnabled, and semNumOutputProgramsPerTS to obsolete.
                      - Added semOutTransPidRemappingTable and semOutTransStatusProgramsPerTs.
                      - Added SDM annotations to all read-write parameter descriptions
                        (or to the Table description for the parameter as appropriate).
                      - Corrected descriptions for reboot required, apply, and saving as needed.

                      March 30, 2006
                      - Changed semGbeMulticastRcvApplyChange to obsolete.
                      - Changed entire semGbeMulticastRcvTable to obsolete.
                      - Added entries for configuration and status of Gigabit
                        Ethernet Input UDP Port and MPTS Redundancy:
                        MptsRedundancySelectionTYPE, MulticastJoinTYPE,
                        RateComparisonTYPE, SuspendTYPE, UdpPortStateTYPE,
                        semGbeInputUdpConfig, semGbeInputUdpConfigGeneral,
                        semGbeInputUdpConfigApplyChange, semGbeInUdpConfMptsRedundMonPeriod,
                        semGbeInUdpConfMptsRedundSwitchTime, semGbeInputUdpConfigTable,
                        semGbeInputUdpConfigMptsRedundTable, semGbeStatusInputUdp,
                        semGbeStatusInputUdpGeneral, semGbeStatusInputUdpTable,
                        semGbeStatusCommandedInputUdpTable, semAlarmGbeInputStreamLowBitRate,
                        semAlarmGbeMptsRedundPrimaryThreshold, semAlarmGbeMptsRedundFailOver,
                        semOutputStreamErrorTable, semGbeInputUdpErrorTable,
                        semConfAlarmClearGbeInStreamLowBitRate,
                        semConfAlarmClearGbeMptsRedundThreshold,
                        semConfAlarmClearGbeMptsRedundFailOver, trapGbeInputStreamLowBitRate,
                        trapGbeMptsRedundPrimaryThreshold, and trapGbeMptsRedundFailOver.
                      - Modified descriptions of Gigabit Ethernet Interface Redundancy
                        related entries to indicate that they only apply to Interface
                        Redundancy: semGbeRedunModeEnabled, semGbeRedunModeThreshold,
                        semGbeRedunModeMonPeriod, semGbeRedunModePrimaryPort,
                        semGbeRedunModeSuspend, semGbeRedunModeForceFailOver,
                        semGbeRedunModeClearFailOverAlarm, semGbeRedunSelectCounting,
                        semGbeRedunModeCurPortInUse, semAlarmGigeFailOver,
                        and semAlarmGigeRedundantModeThreshold.
                      - Changed semHwErrorTable to max of 20 rows.
                      - Changed semHwErrorTimeLogged to be GPS (semSystemTime).
                      - Changed semInvalidInitDataTable to indicate max of 100 rows.
                      - Updated the contact info in the module identity of this mib.

                      February 14, 2006
                      - Changed description of semIceCciLevelSource to include
                        APS and CIT."

        REVISION     "200511290000Z"
        DESCRIPTION
                     "Version 1.12:

                      November 29, 2005
                      - Removed range from description of semGbeCfmInsertionPeriod.

                      November 15, 2005
                      - Added semUpConvStatusStartDigAtten,
                        semUpConvStatusCurrentDigAtten,
                        semUpConvStatusCurrentAgc, and
                        semUpConvStatusCurrentAgcLimit.

                      November 14, 2005
                      - Added semConfAlarmEnableLossOfPhysIn and
                        semConfAlarmClearInvalInitData.  Changed descriptions
                        of semAlarmInvalidInitData and semAlarmLossOfPhysicalInput
                        to reflect these new entries.

                      November 08, 2005
                      - Added semPsiDetectionEnabled and semPsiDetectionTimeout
                        parameters.

                      November 04, 2005
                      - Added semMultiControllerEnable to enable/disable
                        multi-controller mode.
                      - Added table semMultiControllerHistoryTable to store
                        the history of the last 48 local controller for use in
                        multi-controller mode.
                      - Added semEventNewControllerObserved and
                        trapEmNewControllerObserved.

                      October 27, 2005
                      - Added semHostIpMulticastApplyChange and
                        semGbeMulticastRcvApplyChange.  Updated descriptions of
                        Host and GBE multicast receive tables to note that
                        changes are now dynamic (reboot is not required).

                      October 6, 2005
                      - Added semAsiStatusNumOutputStreams, semGbeStatusNumOutputStreams,
                        semQamStatusNumOutputStreams, semOutTransStatusInterface
                      - Added semGbeVlanCfmConfig group for VLAN and CFM configuration
                      - Added semGbeStatusVlanCfm for VLAN and CFM status.
                      - Obsoleted semGbeStatusOutTransStreamTable.

                      September 20, 2005
                      - Changed description of semGbeJitterAbsorption to reflect
                        new minimum of 0 and new increment of 5.
                      - Changed description of semGbeMaxInputDataRate.
                      - Added semGbeBufferOverflowLevel.

                      September 9, 2005
                      - Added semGbeFrameBufferConfig, semGbeResetBufferLimit,
                        semGbeBufferCurrMsLevel, semGbeBufferCurrPercentFull,
                        semGbeStatusFrameBufferTable, semAlarmGbeBufferFullness,
                        semEventGbeBufferReset, trapGbeBufferFullness.

                      July 25, 2005
                      - Added semGbeStatusFrameCounterTable:
                        semGbeTotalRxSinglecastFrames, semGbeTotalRxMulticastFrames,
                        semGbeTotalRxBroadcastFrames, semGbeTotalRxErrorFrames,
                        semGbeTotalRxFrames, semGbeTotalTxGoodFrames,
                        semGbeTotalTxErrorFrames, semGbeTotalTxFrames,
                        semGbeRxBroadcastFrames, semGbeRxMulticastFrames,
                        semGbeRxBroadcastFrames, semGbeRxErrorFrames, semGbeRxFrames,
                        semGbeTxGoodFrames, semGbeTxErrorFrames, semGbeTxFrames,
                        semGbeFrameCounterReset.
                      - Added semGbeCurrNumOpenInputUdpPorts to semGbeStatusGeneral.
                      - Added semGbeStatusFrameCounterResetAll.
                      - Changed entire semGbeStatusPacketCounterTable to obsolete.
                      - Changed semGbeConfigIgmpVersion to include staticIgmpV1,
                        staticIgmpV2, staticIgmpV3.

                      July 12, 2005
                      - Added Host and Data IP Ethernet Status items;
                        Port Speed, Duplex Mode, and Auto-Negotiation setting

                      June 27, 2005
                      - Changed descriptions of semQamStatusError,
                        semQamStatusPortError, and semUpConvStatusUpConvError.

                      June 17, 2005
                      - Added semUserSuppliedTime.

                      May 25, 2005
                      - Added semOutTransStatusIpAddr and semOutTransStatusUdpPort."

        REVISION     "200505130000Z"
        DESCRIPTION
                     "Version 1.11:

                      May 13, 2005
                      - Changed descriptions of semQamStatusError,
                        semQamStatusPortError, and semUpConvStatusUpConvError."

        REVISION     "200504120000Z"
        DESCRIPTION
                     "Version 1.10:

                      April 12, 2005
                      - Changed descriptions of semQamStatusError,
                        semUpConvStatusUpConvError, semAlarmQamFault, and
                        semAlarmUpconverterFault.

                      April 8, 2005
                      - Added semQamStatusPortError, semQamStatusPortFault,
                        semAlarmQamPortFault, and trapQamPortFault.
                      - Changed descriptions of semTimeSource,
                        semQamConfigInterleaverDepth, semQamConfigSymbolRate,
                        semQamConfigRfGainLevel, semUpConvConfigEiaChanNumQamA,
                        semUdpMapConfigBaseUdpOffset, semUdpMapConfigTsIdOffset,
                        semUdpMapConfigModeBits, and semUpConvConfigRfChanSpacing."

        REVISION     "200502190000Z"
        DESCRIPTION
                     "Version 1.9:

                      February 19, 2005
                      - Changed SYNTAX of semIceEmmStatusTblAcpUnitAddress from
                        'OCTET STRING' to 'DisplayString' to match SYNTAX of
                        semAcpUnitAddress.
                      - Changed descriptions of semIceEmmStatusTblAcpUnitAddress
                        and semAcpUnitAddress for consistency and clarification.
                      - Changed description of semIceEmmLastRolloverTime for
                        clarification (is start of last rollover, not end).

                      February 11, 2005
                      - Changed descriptions of semIceEmmPollTimeout and
                        semIceEmmPollRetryCount.

                      February 7, 2005
                      - Changed ACCESS of semGbeStatusIgmpVersion from read-write
                        to read-only
                      - Corrected 655535 to 65535 in several descriptions.
                      - Changed descriptions of semOutTransStatusCorrupted,
                        semIceEmmSetDefault, and semIceEmmPollTimeout.
                      - Changed range and description of semIceEmmPollRandomization.
                      - Added the range in the description of semIceEmmServerTcpPort.
                      - Changed SemIceStatusEncryptionModeEntry to
                        SemIceStatusEncryptionModeEntry.

                      January 24, 2005
                      - Added semGbeConfigIgmpVersion and semGbeStatusIgmpVersion.
                      - Added semOutputProgramInputPreEncrypted,
                        semOutTransStatusCorrupted and
                        semIceCommonTierEncryptionEnable.
                      - Replaced semIceEmmServerErrorAlarmClear with
                        semIceEmmServerCommAlarmClear and
                        semIceEmmServerInvalRespAlarmClear.
                      - Added noEmm enumeration to semIceStatusEncryptionModeReason.
                      - Changed descriptions of semIceEmmSetDefault and
                        semIceEmmServerIpAddr to indicate IP address not changed
                        when setting parameters to default.
                      - Changed description of semLoadDeviceReceivePort to indicate
                        reboot required on change.
                      - Enhanced various descriptions for ICE config and status.
                      - Changed semIceEmmStatusTblServerError SYNTAX from enumerated
                        to Unsigned32.

                      January 17, 2005
                      - Changed description of semAlarmHardwareFault.

                      December 17, 2004
                      - Added semOperationalTime.
                      - Added semGbeMulticastRcvIncludeIpAddr.
                      - Added semUdpMapConfigModeBits.
                      - Added Internal Control of Encryption (ICE) status parameters.
                      - Added Internal Control of Encryption (ICE) Alarms and Traps.
                      - Changed semOutTransUtilHistIndex SYNTAX to correct the range.
                      - Changed description of semOutTransUtilHistIndex.

                      December 7, 2004
                      - Added Internal Control of Encryption (ICE) configuration parameters.
                      - Changed description of semDeviceOperatingMode to elaborate on 'internal'
                        and 'external' modes.
                      - Changed descriptions of semGbeDynamicArpTimeout and
                        semGbeDynamicArpRetryInterval to indicate semGbeDynamicArpRetryInterval
                        value must be written before semGbeDynamicArpTimeout.
                      - Added hrcFrequency enumeration to semUpConvConfigTuningMode.
                      - Changed description of semUpConvConfigRfFreqQamA to indicate 100 Hz step.
                      - Changed descriptions of semMaxInternalServiceMappings and
                        semMaxInternalPidMappings to refer to description of semDeviceOperatingMode
                        for internal/external mode information."

        REVISION     "200409170000Z"
        DESCRIPTION
                     "Version 1.8:

                      September 24, 2004
                      - Added semMainBoardType and semAsiMonitorPortEncryption.

                      September 17, 2004
                      - Added semGbeRedunSelectCounting.
                        Changed semGbeStatusTotOutputPackets and
                        semGbeStatusNumOutputPackets from Integer32
                        to Counter32."

        REVISION     "200408110000Z"
        DESCRIPTION
                     "Version 1.7:

                      August 11, 2004
                      - Updated description of semAlarmUpconverterFault
                        to indicate that semUpConvStatusRfOutLevelError
                        'highError' is a 'critical' error.

                      August 9, 2004
                      - Updated various descriptions for clarity.

                      July 27, 2004
                      - Added semCommandErrorTable.

                      July 23, 2004
                      - Added semFanSpeedLeftCenter, semFanSpeedRightCenter,
                        and semAcpReProgramControlFpga.

                      July 7, 2004
                      - Added semUdpMapConfigTsIdOffset.

                      June 29, 2004
                      - Added semUpConvModuleStatusTable.

                      June 15, 2004
                      - Added semProductType and semGbeStatusOutputPacketTable.
                      - Changed description of semGbeConfigNumInStreams.
                      - Changed range of semManRemuxMapIndex.

                      June 15, 2004
                      - Added standardizedUdpMapping enumeration to
                        semDeviceOperatingMode.
                      - Added semAsiStatusGeneral, semAsiPortsCount, semGbePortsCount,
                        semGbeMaxInputUdpPorts, semHostIpMaxInputUdpPorts,
                        semRemuxStatusGeneral, semMaxInternalServiceMappings,
                        semMaxInternalPidMappings, and semPsipInputCount.
                      - Changed descriptions of semOutTransStreamPhysOutPort, and
                        semOutTransStreamPhysOutType.
                      - Changed STATUS of semGbeLoadBinaryType to obsolete.
                      - Changed index sizes of QAM and Upconverter entries
                        for v12 sizing."

        REVISION     "200405040000Z"
        DESCRIPTION
                     "Version 1.6:

                      May 07, 2004
                      - Changed descriptions of semOutTransUtilizationHistoryTable,
                        semAlarmMissingTimeUpdate, semAlarmCommandTableEmpty,
                        semAlarmCommandTableNearFull, semAlarmServiceInError,
                        semAlarmWaitingForExtractedMessage, and
                        semAlarmServiceNotAuthorized to match SEM.

                      May 04, 2004
                      - Added semQamStatusError, semQamStatusFault,
                        and semUpConvStatusFault.

                      May 03, 2004
                      - Added trapQamFault, trapUpconverterFault,
                        trapOtsHostIpOverflow, and trapOtsOverflow.

                      April 29, 2004
                      - Added semPidMapInvalidApplyText, semAlarmQamFault,
                        semAlarmUpconverterFault, semAlarmOtsHostIpOverflow,
                        and semAlarmOtsOverflow.

                      April 27, 2004
                      - Added semInsertQueFirstTimeInserted, semHostIpPacketStatNumDiscardPkts,
                        semHostIpPacketStatTotDiscardPkts, semIpInsertPacketStatTotDiscardPkts,
                        semIpInsertPacketStatNumDiscardPkts, semOutTransStatusTable,
                        semUdpMapInvalidApplyText, semManRemuxMapInvalidApplyText,
                        semManRemuxOutTsInvalidApplyText, and semAsiDemuxInvalidApplyText
                      - Changed semUpConvStatusIfLevelError, semManRemuxMapInputPid, and
                        semManRemuxMapOutputPid to 'obsolete'.
                      - Changed descriptions for semUpConvStatusIfLevelError,
                        semManRemuxMapInputPid, semManRemuxMapOutputPid,
                        semQamStatusMpegFecSyncLock, semUpConvStatusRfOutLevelError,
                        semUpConvStatusUpConvError, semHostIpPacketStatNumRcvPkts,
                        semHostIpPacketStatNumInsPkts, semHostIpPacketStatTotRcvPkts,
                        semHostIpPacketStatTotInsPkts, semOutTransUtilMonAlarmThreshold,
                        semOutTransUtilMonSetAlarmDelay, semOutTransUtilMonClearAlarmDelay,
                        and semAlarmOtsUtilizationFault.

                      March 30, 2004
                      - Added semPidMapConfig"

        REVISION     "200403290000Z"
        DESCRIPTION
                     "Version 1.5:

                      March 29, 2004
                      - Added 1 enumeration to PsipState for Error Condition"

        REVISION     "200402240000Z"
        DESCRIPTION
                     "Version 1.4:

                      February 24, 2004
                      - Added semEntTransEncryptMcDes.
                      - Changed descriptions of semEntTransEncryptCsaV1,
                        semEntControlWordSharing, semEntControlWordClear,
                        and semQamConfigRfGainLevel.

                      February 18, 2004
                      - Added semDvs208EasMulticastRcvIpAddr.
                      - Changed description of semHostIpRoutingApplyChange to
                        indicate that it is not currently used.

                      February 10, 2004
                      - Modified semOutputProgramState enumerations for clarity.
                      - Added semOutputProgramPsipState.

                      February 04, 2004
                      - Added semEntitlements, semEntTransportEncrypt,
                        semEntControlWordDelivery, semEntTransEncryptCsaV1,
                        semEntControlWordClear, and EntitlementTYPE
                      - restored semSimInstalled.

                      February 03, 2004
                      - Added semDvs208EasNumRcvMsgs and semDvs208EasNumInvalRcvMsgs.
                      - Corrected syntax and oid of semEventOtsUtilizationError.

                      January 26, 2004
                      - Added semSimIpInterfaceSelect,
                        semOutputProgramSimScsProgramIndex,
                        semAlarmSimulcryptCommunicationFault,
                        and trapSimulcryptCommunicationFault.
                      - Added semQamConfigIfFreq and semQamConfigIfGainLevel
                        to semQamConfigTable for SEM v4.
                      - Changed descriptions to indicate how SEM v4 is supported.
                      - Added simulcrypt1 to semDeviceOperatingMode.
                      - Added ranges to PSIP entries.

                      January 14, 2004
                      - Updated description to support semInsertModeEntry.

                      December 16, 2003
                      - Added SemHostEnetTYPE.
                      - Added semPsip group and entries.
                      - Added semDvs208Eas group and entries."

        REVISION     "200312090000Z"
        DESCRIPTION
                     "Version 1.3:

                      December 9, 2003
                      - Added Gigabit Ethernet MAC Address status table.

                      November 21, 2003
                      - Added enabledLoopThroughTerminator enumeration to
                        semGbeConfigEnable.

                      November 13, 2003
                      - Added hostEnet enumeration to semManRemuxMapPhysInType.
                      - Changed descriptions for semFanSpeedLeft, semFanSpeedCenter,
                        semFanSpeedRight, semUpConvConfigRfFreqQamA,
                        semUpConvConfigRfChanSpacing, semAlarmTemperatureFault,
                        and semAlarmFanFault.

                      October 31, 2003
                      - Changed description of semGbeDynamicArpTimeout to indicate
                        value must be greater than semGbeDynamicArpRetryInterval.

                      October 22, 2003
                      - Rearranged revision history in module-identity clause.

                      October 13, 2003
                      - Changed description of semOutTransUtilizationError to indicate
                        field is reset when monitoring disabled.

                      October 10, 2003
                      - Added semAlarmGigeRedundantModeThreshold and
                        trapGigeRedundantModeThreshold;
                      - Changed descriptions and ranges for semUpConvConfigRfFreqQamA
                        and semUpConvConfigRfChanSpacing;
                      - Changed descriptions for semGbeRedunModeForceFailOver,
                        semGbeRedunModeApplyChange, semGbeRedunModeSuspend,
                        semGbeRedunModeClearFailOverAlarm and trapOtsUtilizationFault.

                      September 29, 2003
                      - Add new mib leaf parameters for Up-Converter MCN and board revision.

                      September 11, 2003
                      - Added semSimulcryptEnabled, semSimulcryptInstalled.
                      - Changed semSimulCrypt => semSimulcrypt.
                      - Changed semSimulCryptConfig => semSimulcryptConfig.
                      - Changed semSimulCryptStatus => semSimulcryptStatus."

        REVISION     "200309040000Z"
        DESCRIPTION
                     "Version 1.2:

                      September 4, 2003
                      - Added semGbeLoadBinaryType.

                      August 21, 2003
                      - Added semAlarmOtsUtilizationFault, semEventOtsUtilizationError,
                        trapOtsUtilizationFault, and trapOtsUtilizationError.

                      August 20, 2003
                      - Added ClearAlarmTYPE, semGbeRedunModeClearFailOverAlarm,
                        semIpConfigInsertionRateTable, semIpInsertPacketStatisticsTable,
                        semAlarmGigeFailOver, and trapGigeFailOver.
                      - Removed completeNoTimeSource and incompleteNoTimeSource from
                        UtilizationSamplingTYPE.
                      - Revised descriptions for OTS Rate Utilization related entries.

                      August 18, 2003
                      - Expanded QAM / Up-Converter configuration. This includes:
                        Expansion of Tuning Mode for support of HRC Frequency selection,
                        increase range for RF Output Level, and change units
                        for frequency from MHz to Hertz.

                      August 07, 2003
                      - Added GBE Redundancy Mode, GBE Multicast, OAMP Multicast,
                        and DataIp Multicast entries.

                      July 25, 2003
                      - Modified Output Transport Stream Utilization Monitoring
                        configuration entries.

                      July 18, 2003
                      - Added Output Transport Stream Utilization Monitoring
                        and Utilization statistics related entries.
                      - Added FlushTYPE, UtilizationSamplingTYPE, and
                        UtilizationErrorTYPE."

        REVISION     "200307100000Z"
        DESCRIPTION
                     "Version 1.1:

                      July 10, 2003
                      - Modified descriptions of the following parameters
                        to reflect their behavior when changes are made or
                        to make corrections for typographical errors:
                        semGbeDynamicArpTimeout,
                        semGbeDynamicArpRetryInterval,
                        semGbeDynamicOutputTsArpTimeoutEnable,
                        semOutTransHighLowSpeedMode,
                        semOutputClockConfigRate,
                        semUdpMapConfigGbePort,
                        semUdpMapConfigBaseUdpOffset,
                        semUdpMapConfigInSvcPreEncryption,
                        semManRemuxMapInSvcPreEncryption,
                        semAsiDemuxConfigInSvcPreEncryption,
                        semAlarmCommandTableEmpty,
                        semAlarmCommandTableNearFull,
                        semAlarmServiceInError,
                        semAlarmWaitingForExtractedMessage, and
                        semAlarmServiceNotAuthorized."

        REVISION     "200306240000Z"
        DESCRIPTION
                     "Version 1.0:

                      June 24, 2003
                      - Initial Revision."

         ::= {giproducts 70}



-- ------------------------------------------------------------------------------
-- REUSABLE TYPE DEFINITIONS
--

OutputMuteTYPE ::=  INTEGER
   {
    unmute (1),
    mute   (2)
   }

EnableDisableTYPE ::=  INTEGER
   {
    disabled (1),
    enabled  (2)
   }

InstalledTYPE ::=  INTEGER
   {
    notInstalled (1),
    installed    (2)
   }

ActiveTYPE ::=  INTEGER
   {
    notActive (1),
    active    (2)
   }

PllErrorTYPE ::= INTEGER
   {
    clockpllError  (1),
    ok             (2)
   }

ApplyDataToDeviceTYPE ::= INTEGER
   {
    applyNotInProgress            (1),
    apply                         (2),
    applyNotInProgressValidData   (3),
    applyNotInProgressInvalidData (4)
   }

UpdateStatusTYPE ::= INTEGER
   {
    updateNotInProgress (1),
    update              (2)
   }

ResetStatisticsTYPE ::= INTEGER
   {
    resetNotInProgress (1),
    reset              (2)
   }

ClearAlarmTYPE ::= INTEGER
   {
    clearAlarmNotInProgress (1),
    clearAlarm              (2)
   }

FlushTYPE ::= INTEGER
   {
    flushNotInProgress (1),
    flush              (2)
   }

EncryptedTYPE ::= INTEGER
   {
    clear     (1),
    encrypted (2)
   }

UtilizationSamplingTYPE ::= INTEGER
   {
    samplingComplete       (1),
    samplingIncomplete     (2)
   }

UtilizationErrorTYPE ::= INTEGER
   {
    noError               (1),
    alarmThresholdReached (2),
    overflow              (3)
   }

SemHostEnetTYPE ::= INTEGER
   {
    hostEnet1 (1),
    hostEnet2 (2)
   }

EntitlementTYPE ::=  INTEGER
   {
    notEntitled (1),
    entitled    (2)
   }

RedundancySelectionTYPE ::=  INTEGER
   {
    notApplicable (0),
    primary       (1),
    secondary     (2)
   }

MulticastJoinTYPE ::=  INTEGER
   {
    notApplicable   (0),
    noJoinOnOpen    (1),
    joinOnOpen      (2)
   }

RateComparisonTYPE ::=  INTEGER
   {
    notApplicable       (0),
    dataRate            (1),
    transportStreamRate (2)
   }

SuspendTYPE ::=  INTEGER
   {
    notApplicable   (0),
    notSuspended    (1),
    suspended       (2)
   }

UdpPortStateTYPE ::=  INTEGER
   {
    closed              (0),
    openedInUse         (1),
    openedBackup        (2),
    openedTransToBackup (3),
    openedTransToInUse  (4)
   }



--
-- SEM MIB STRUCTURE
--
-- The following duplicates the structure and entries in the SEM MIB.
-- Object identifiers for groups are defined here.
--
   semSys                                                 OBJECT IDENTIFIER ::= {sem 1}
      semSysConfig                                        OBJECT IDENTIFIER ::= {semSys 1}
         semSysConfigGeneral                              OBJECT IDENTIFIER ::= {semSysConfig 1}
--          semSaveConfig                                                       {semSysConfigGeneral 1}
--          semProductName                                                      {semSysConfigGeneral 2}
--          semDeviceOperatingMode                                              {semSysConfigGeneral 3}
--          semCommandRetryPeriod                                               {semSysConfigGeneral 4}
--          semInsertModeEntry                                                  {semSysConfigGeneral 5}
--          semBootMethod                                                       {semSysConfigGeneral 6}
--          semPsiDetectionEnabled                                              {semSysConfigGeneral 7}
--          semPsiDetectionTimeout                                              {semSysConfigGeneral 8}
--          semAutoRebootEnable                                                 {semSysConfigGeneral 9}
         semSysConfigTime                                 OBJECT IDENTIFIER ::= {semSysConfig 2}
--          semTimeSource                                                       {semSysConfigTime 1}
--          semUtcOffset                                                        {semSysConfigTime 2}
--          semTimeSourceInputPort                                              {semSysConfigTime 3}
--          semTimeSourceSntpServerSpecified                                    {semSysConfigTime 4}
--          semTimeSourceSntpServerIP                                           {semSysConfigTime 5}
--          semUserSuppliedTime                                                 {semSysConfigTime 6}
         semSysConfigController                           OBJECT IDENTIFIER ::= {semSysConfig 3}
--          semControllerIP                                                     {semSysConfigController 1}
--          semControllerPort                                                   {semSysConfigController 2}
--          semLoadDeviceReceivePort                                            {semSysConfigController 3}
--          semRetryTimeout                                                     {semSysConfigController 4}
--          semNumRetries                                                       {semSysConfigController 5}
--          semMultiControllerEnable                                            {semSysConfigController 6}
         semSysConfigPidRemapping                         OBJECT IDENTIFIER ::= {semSysConfig 4}
--          semPidRemappingEnabled       [obsolete]                             {semSysConfigPidRemapping 1}
--          semPidsPerService            [obsolete]                             {semSysConfigPidRemapping 2}
--          semPidMaskingEnabled         [obsolete]                             {semSysConfigPidRemapping 3}
         semSysConfigElementManagerLogin                  OBJECT IDENTIFIER ::= {semSysConfig 5}
--          semUserName                  [obsolete]                             {semSysConfigElementManagerLogin 1}
--          semUserPassword              [obsolete]                             {semSysConfigElementManagerLogin 2}
      semSysStatus                                        OBJECT IDENTIFIER ::= {semSys 2}
         semSysStatusGeneral                              OBJECT IDENTIFIER ::= {semSysStatus 1}
--          semSystemTime                                                       {semSysStatusGeneral 1}
--          semHostProcessorBootCodeVersion                                     {semSysStatusGeneral 2}
--          semMuxFpgaVersion                                                   {semSysStatusGeneral 3}
--          semMainBoardVersion                                                 {semSysStatusGeneral 4}
--          semHostApplicationDate                                              {semSysStatusGeneral 5}
--          semProductType                                                      {semSysStatusGeneral 6}
--          semMainBoardType                                                    {semSysStatusGeneral 7}
--          semOperationalTime                                                  {semSysStatusGeneral 8}
--          semBootReason                                                       {semSysStatusGeneral 9}
--          semCurrentDeviceOperatingMode                                       {semSysStatusGeneral 10}
         semSysStatusEnvironment                          OBJECT IDENTIFIER ::= {semSysStatus 2}
--          semTemperatureCenter                                                {semSysStatusEnvironment 1}
--          semTemperatureRight                                                 {semSysStatusEnvironment 2}
--          semFanSpeedLeft                                                     {semSysStatusEnvironment 3}
--          semFanSpeedCenter                                                   {semSysStatusEnvironment 4}
--          semFanSpeedRight                                                    {semSysStatusEnvironment 5}
--          semFanSpeedLeftCenter                                               {semSysStatusEnvironment 6}
--          semFanSpeedRightCenter                                              {semSysStatusEnvironment 7}
         semSysStatusCommands                             OBJECT IDENTIFIER ::= {semSysStatus 3}
            semCommandsGeneral                            OBJECT IDENTIFIER ::= {semSysStatusCommands 1}
--             semCommandsActive                                                {semCommandsGeneral 1}
--             semCommandsWaiting                                               {semCommandsGeneral 2}
--             semExtractCommandsWaiting                                        {semCommandsGeneral 3}
--             semBlocksAvailable                                               {semCommandsGeneral 4}
--             semBlocksTotal                                                   {semCommandsGeneral 5}
--          semLoadSemTable                                                     {semSysStatusCommands 2}
--             semLoadSemEntry                                                  {semLoadSemTable 1}
--                semLoadSemIndex                                               {semLoadSemEntry 1}
--                semLoadSemLevel                                               {semLoadSemEntry 2}
--                semLoadSemState                                               {semLoadSemEntry 3}
--                semLoadSemSubState                                            {semLoadSemEntry 4}
--                semLoadSemSequenceNumber                                      {semLoadSemEntry 5}
--                semLoadSemSubcommandId                                        {semLoadSemEntry 6}
--                semLoadSemSubcommandErrorCode                                 {semLoadSemEntry 7}
--                semLoadSemSubcommandRetryCount                                {semLoadSemEntry 8}
--                semLoadSemCommandBlock1                                       {semLoadSemEntry 9}
--          semInsertQueTable                                                   {semSysStatusCommands 3}
--             semInsertQueEntry                                                {semInsertQueTable 1}
--                semInsertQueSubqueueOutputId                                  {semInsertQueEntry 1}
--                semInsertQueSubqueueIndex                                     {semInsertQueEntry 2}
--                semInsertQueMessageType                                       {semInsertQueEntry 3}
--                semInsertQueInsLoadSemSeqNum                                  {semInsertQueEntry 4}
--                semInsertQuePid                                               {semInsertQueEntry 5}
--                semInsertQueProgramNumber                                     {semInsertQueEntry 6}
--                semInsertQueStartTime                                         {semInsertQueEntry 7}
--                semInsertQueStopTime                                          {semInsertQueEntry 8}
--                semInsertQueFirstTimeInserted                                 {semInsertQueEntry 9}
--          semOutputProgramTable                                               {semSysStatusCommands 5}
--             semOutputProgramEntry                                            {semOutputProgramTable 1}
--                semOutputProgramOutputId                                      {semOutputProgramEntry 1}
--                semOutputProgramOutputProgNum                                 {semOutputProgramEntry 2}
--                semOutputProgramInputId                                       {semOutputProgramEntry 3}
--                semOutputProgramInputProgNum                                  {semOutputProgramEntry 4}
--                semOutputProgramState                                         {semOutputProgramEntry 5}
--                semOutputProgramDsSeqNum                                      {semOutputProgramEntry 6}
--                semOutputProgramRcvUdpPort                                    {semOutputProgramEntry 7}
--                semOutputProgramAcpIndex                                      {semOutputProgramEntry 8}
--                semOutputProgramServiceIndex                                  {semOutputProgramEntry 9}
--                semOutputProgramPsipState                                     {semOutputProgramEntry 10}
--                semOutputProgramSimScsProgramIndex                            {semOutputProgramEntry 11}
--                semOutputProgramInputPreEncrypted                             {semOutputProgramEntry 12}
--                semOutputProgramInputPort                                     {semOutputProgramEntry 13}
         semSysStatusMultiController                      OBJECT IDENTIFIER ::= {semSysStatus 4}
--          semMultiControllerHistoryTable                                      {semSysStatusMultiController 1}
--             semMultiControllerHistoryEntry                                   {semMultiControllerHistoryTable 1}
--                semMultiControllerHistoryIndex                                {semMultiControllerHistoryEntry 1}
--                semMultiControllerHistoryTime                                 {semMultiControllerHistoryEntry 2}
--                semMultiControllerHistoryIPaddr                               {semMultiControllerHistoryEntry 3}
--                semMultiControllerHistoryIPport                               {semMultiControllerHistoryEntry 4}
   semAsi                                                 OBJECT IDENTIFIER ::= {sem 2}
      semAsiConfig                                        OBJECT IDENTIFIER ::= {semAsi 1}
--       semAsiConfigTable                                                      {semAsiConfig 1}
--          semAsiConfigEntry                                                   {semAsiConfigTable 1}
--             semAsiConfigPortNum                                              {semAsiConfigEntry 1}
--             semAsiConfigEnable                                               {semAsiConfigEntry 2}
--             semAsiConfigOutPacketSize [not currently supported]              {semAsiConfigEntry 3}
         semAsiMonitorPortConfig                          OBJECT IDENTIFIER ::= {semAsiConfig 2}
--          semAsiMonitorPortOutTransStreamNum                                  {semAsiMonitorPortConfig 1}
--                The following parameter is not supported.
--          semAsiMonitorPortOutPacketSize [not currently supported]            {semAsiMonitorPortConfig 2}
--          semAsiMonitorPortEncryption                                         {semAsiMonitorPortConfig 3}
      semAsiStatus                                        OBJECT IDENTIFIER ::= {semAsi 2}
--       semAsiStatusTable                                                      {semAsiStatus 1}
--          semAsiStatusEntry                                                   {semAsiStatusTable 1}
--             semAsiStatusPortNum                                              {semAsiStatusEntry 1}
--             semAsiStatusInputActive                                          {semAsiStatusEntry 2}
--             semAsiStatusOutTransStreamNum                                    {semAsiStatusEntry 3}
         semAsiStatusGeneral                              OBJECT IDENTIFIER ::= {semAsiStatus 2}
--          semAsiPortsCount                                                    {semAsiStatusGeneral 1}
--          semAsiStatusNumOutputStreams                                        {semAsiStatusGeneral 2}
   semGbe                                                 OBJECT IDENTIFIER ::= {sem 3}
      semGbeConfig                                        OBJECT IDENTIFIER ::= {semGbe 1}
         semGbeConfigGeneral                              OBJECT IDENTIFIER ::= {semGbeConfig 1}
--          semGbeDefaultGateway                                                {semGbeConfigGeneral 1}
--          semGbeRoutingApplyChange                                            {semGbeConfigGeneral 2}
--          semGbeLoadBinaryType          [obsolete]                            {semGbeConfigGeneral 3}
--          semGbeJitterAbsorption                                              {semGbeConfigGeneral 4}
--          semGbeMulticastRcvApplyChange [obsolete]                            {semGbeConfigGeneral 5}
--       semGbeConfigTable                                                      {semGbeConfig 2}
--          semGbeConfigEntry                                                   {semGbeConfigTable 1}
--             semGbeConfigPortNum                                              {semGbeConfigEntry 1}
--             semGbeConfigEnable                                               {semGbeConfigEntry 2}
--             semGbeConfigNumInStreams                                         {semGbeConfigEntry 3}
--             semGbeConfigAutoNegotiateEnable                                  {semGbeConfigEntry 4}
--             semGbeConfigIgmpVersion                                          {semGbeConfigEntry 5}
--       semGbeConfigIpTable                                                    {semGbeConfig 3}
--          semGbeConfigIpEntry                                                 {semGbeConfigIpTable 1}
--             semGbeConfigIpPortNum                                            {semGbeConfigIpEntry 1}
--             semGbeConfigIpAddr                                               {semGbeConfigIpEntry 2}
--             semGbeConfigIpSubnetMask                                         {semGbeConfigIpEntry 3}
--       semGbeRoutingTable                                                     {semGbeConfig 4}
--          semGbeRoutingEntry                                                  {semGbeRoutingTable 1}
--             semGbeRoutingIndex                                               {semGbeRoutingEntry 1}
--             semGbeRoutingDestIpAddr                                          {semGbeRoutingEntry 2}
--             semGbeRoutingGateIpAddr                                          {semGbeRoutingEntry 3}
--             semGbeRoutingSubnetMask                                          {semGbeRoutingEntry 4}
         semGbeConfigArp                                  OBJECT IDENTIFIER ::= {semGbeConfig 5}
--          semGbeStaticArpApplyChange                                          {semGbeConfigArp 1}
--          semGbeDeleteArpApplyChange                                          {semGbeConfigArp 2}
--          semGbeUpdateStatusArpTable                                          {semGbeConfigArp 3}
--          semGbeDynamicArpTimeout                                             {semGbeConfigArp 4}
--          semGbeDynamicArpRetryInterval                                       {semGbeConfigArp 5}
--          semGbeDynamicOutputTsArpTimeoutEnable                               {semGbeConfigArp 6}
--          semGbeDynamicArpFlush                                               {semGbeConfigArp 7}
--       semGbeStaticArpTable                                                   {semGbeConfig 6}
--          semGbeStaticArpEntry                                                {semGbeStaticArpTable 1}
--             semGbeStaticArpIndex                                             {semGbeStaticArpEntry 1}
--             semGbeStaticArpIpAddr                                            {semGbeStaticArpEntry 2}
--             semGbeStaticArpMacAddr                                           {semGbeStaticArpEntry 3}
--       semGbeDeleteArpTable                                                   {semGbeConfig 7}
--          semGbeDeleteArpEntry                                                {semGbeDeleteArpTable 1}
--             semGbeDeleteArpIndex                                             {semGbeDeleteArpEntry 1}
--             semGbeDeleteArpIpAddr                                            {semGbeDeleteArpEntry 2}
         semGbeRedundantModeConfig                        OBJECT IDENTIFIER ::= {semGbeConfig 8}
--          semGbeRedunModeEnabled                                              {semGbeRedundantModeConfig 1}
--          semGbeRedunModeApplyChange                                          {semGbeRedundantModeConfig 2}
--          semGbeRedunModeThreshold                                            {semGbeRedundantModeConfig 3}
--          semGbeRedunModeMonPeriod                                            {semGbeRedundantModeConfig 4}
--          semGbeRedunModePrimaryPort                                          {semGbeRedundantModeConfig 5}
--          semGbeRedunModeSuspend                                              {semGbeRedundantModeConfig 6}
--          semGbeRedunModeForceFailOver                                        {semGbeRedundantModeConfig 7}
--          semGbeRedunModeClearFailOverAlarm                                   {semGbeRedundantModeConfig 8}
--          semGbeRedunSelectCounting                                           {semGbeRedundantModeConfig 9}
--       semGbeMulticastRcvTable                   [obsolete]                   {semGbeConfig 9}
--          semGbeMulticastRcvEntry                [obsolete]                   {semGbeMulticastRcvTable 1}
--             semGbeMulticastRcvIndex             [obsolete]                   {semGbeMulticastRcvEntry 1}
--             semGbeMulticastRcvPortNum           [obsolete]                   {semGbeMulticastRcvEntry 2}
--             semGbeMulticastRcvIpAddr            [obsolete]                   {semGbeMulticastRcvEntry 3}
--             semGbeMulticastRcvUdpPort           [obsolete]                   {semGbeMulticastRcvEntry 4}
--             semGbeMulticastRcvIncludeIpAddr     [obsolete]                   {semGbeMulticastRcvEntry 5}
         semGbeMulticastTransmit                          OBJECT IDENTIFIER ::= {semGbeConfig 10}
            semGbeMulticastTxGeneral                      OBJECT IDENTIFIER ::= {semGbeMulticastTransmit 1}
--             semGbeMulticastTxTimeToLive                                      {semGbeMulticastTxGeneral 1}
--          semGbeMulticastTxTable                                              {semGbeMulticastTransmit 2}
--             semGbeMulticastTxEntry                                           {semGbeMulticastTxTable 1}
--                semGbeMulticastTxOutTransStreamNum                            {semGbeMulticastTxEntry 1}
--                semGbeMulticastTxPhysPort                                     {semGbeMulticastTxEntry 1}
         semGbeFrameBufferConfig                          OBJECT IDENTIFIER ::= {semGbeConfig 11}
--           semGbeMaxInputDataRate                                             {semGbeFrameBufferConfig 1}
--           semGbeBufferAlarmThreshold                                         {semGbeFrameBufferConfig 2}
         semGbeVlanCfmConfig                              OBJECT IDENTIFIER ::= {semGbeConfig 12}
--           semGbeVlanCfmApplyChange                                           {semGbeVlanCfmConfig 1}
--           semGbeVlanTaggingEnabled                                           {semGbeVlanCfmConfig 2}
--           semGbeVlanTaggingPriority                                          {semGbeVlanCfmConfig 3}
--           semGbeVlanTaggingVidTable                                          {semGbeVlanCfmConfig 4}
--              semGbeVlanTaggingVidEntry                                       {semGbeVlanTaggingVidEntry 1}
--                 semGbeVlanTaggingStreamNum                                   {semGbeVlanTaggingVidEntry 1}
--                 semGbeVlanTaggingVidType                                     {semGbeVlanTaggingVidEntry 1}
--                 semGbeVlanTaggingUserVid                                     {semGbeVlanTaggingVidEntry 2}
--           semGbeCfmInsertionEnabled                                          {semGbeVlanCfmConfig 5}
--           semGbeCfmInsertionPeriod                                           {semGbeVlanCfmConfig 6}
--           semGbeCfmInsertionMacAddress                                       {semGbeVlanCfmConfig 7}
         semGbeInputUdpConfig                             OBJECT IDENTIFIER ::= {semGbeConfig 13}
            semGbeInputUdpConfigGeneral                   OBJECT IDENTIFIER ::= {semGbeInputUdpConfig 1}
--             semGbeInputUdpConfigApplyChange                                  {semGbeInputUdpConfigGeneral 1}
--             semGbeInUdpConfMptsRedundMonPeriod                               {semGbeInputUdpConfigGeneral 2}
--             semGbeInUdpConfMptsRedundSwitchTime                              {semGbeInputUdpConfigGeneral 3}
--             semGbeInUdpConfRedundForceToSecondary                            {semGbeInputUdpConfigGeneral 4}
--             semGbeInUdpConfRedundForceToPrimary                              {semGbeInputUdpConfigGeneral 5}
--          semGbeInputUdpConfigTable                                           {semGbeInputUdpConfig 2}
--             semGbeInputUdpConfigEntry                                        {semGbeInputUdpConfigTable 1}
--                semGbeInUdpConfIndex                                          {semGbeInputUdpConfigEntry 1}
--                semGbeInUdpConfGbePort                                        {semGbeInputUdpConfigEntry 2}
--                semGbeInUdpConfUdpPort                                        {semGbeInputUdpConfigEntry 3}
--                semGbeInUdpConfMulticastIpAddr                                {semGbeInputUdpConfigEntry 4}
--                semGbeInUdpConfSourceIpAddr                                   {semGbeInputUdpConfigEntry 5}
--                semGbeInUdpConfLowAlarmBitRate                                {semGbeInputUdpConfigEntry 6}
--                semGbeInUdpConfRateCompareType                                {semGbeInputUdpConfigEntry 7}
--                semGbeInUdpConfMptsRedundSelection                            {semGbeInputUdpConfigEntry 8}
--                semGbeInUdpConfMptsRedundMcJoin                               {semGbeInputUdpConfigEntry 9}
--                semGbeInUdpConfMptsRedundThreshold                            {semGbeInputUdpConfigEntry 10}
--                semGbeInUdpConfMptsRedundSuspend                              {semGbeInputUdpConfigEntry 11}
--          semGbeInputUdpConfigMptsRedundTable                                 {semGbeInputUdpConfig 3}
--             semGbeInputUdpConfigMptsRedundEntry                              {semGbeInputUdpConfigMptsRedundTable 1}
--                semGbeInUdpConfMptsRedundIndex                                {semGbeInputUdpConfigMptsRedundEntry 1}
--                semGbeInUdpConfMptsRedundForceSwitch                          {semGbeInputUdpConfigMptsRedundEntry 2}
      semGbeStatus                                        OBJECT IDENTIFIER ::= {semGbe 2}
         semGbeStatusGeneral                              OBJECT IDENTIFIER ::= {semGbeStatus 1}
--          semGbeBootCodeVersion                                               {semGbeStatusGeneral 1}
--          semGbeApplicationCodeVersion                                        {semGbeStatusGeneral 2}
--          semGbeRedunModeCurPortInUse                                         {semGbeStatusGeneral 3}
--          semGbePortsCount                                                    {semGbeStatusGeneral 4}
--          semGbeMaxInputUdpPorts                                              {semGbeStatusGeneral 5}
--          semGbeCurrNumOpenInputUdpPorts                                      {semGbeStatusGeneral 6}
--          semGbeResetBufferLevelLimit                                         {semGbeStatusGeneral 7}
--          semGbeBufferCurrMsLevel                                             {semGbeStatusGeneral 8}
--          semGbeBufferCurrPercentFull                                         {semGbeStatusGeneral 9}
--          semGbeBufferOverflowLevel                                           {semGbeStatusGeneral 10}
--          semGbeStatusNumOutputStreams                                        {semGbeStatusGeneral 11}
--       semGbeStatusTable                                                      {semGbeStatus 2}
--          semGbeStatusEntry                                                   {semGbeStatusTable 1}
--             semGbeStatusPortNum                                              {semGbeStatusEntry 1}
--             semGbeStatusMacAddr                                              {semGbeStatusEntry 2}
--             semGbeStatusLinkActive                                           {semGbeStatusEntry 3}
--             semGbeStatusIgmpVersion                                          {semGbeStatusEntry 4}
--       semGbeStatusOutTransStreamTable         [obsolete]                     {semGbeStatus 3}
--          semGbeStatusOutTransStreamEntry      [obsolete]                     {semGbeStatusOutTransStreamTable 1}
--             semGbeStatusOutTransStreamPortNum [obsolete]                     {semGbeStatusOutTransStreamEntry 1}
--             semGbeStatusOutTransStreamIndex   [obsolete]                     {semGbeStatusOutTransStreamEntry 2}
--             semGbeStatusOutTransStreamNum     [obsolete]                     {semGbeStatusOutTransStreamEntry 3}
--       semGbeStatusPacketCounterTable          [obsolete]                     {semGbeStatus 4}
--          semGbeStatusPacketCounterEntry       [obsolete]                     {semGbeStatusPacketCounterTable 1}
--             semGbePacketCounterIndex          [obsolete]                     {semGbeStatusPacketCounterEntry 1}
--             semGbePacketCounterResetTotals    [obsolete]                     {semGbeStatusPacketCounterEntry 2}
--             semGbeTotalRxSinglecastPackets    [obsolete]                     {semGbeStatusPacketCounterEntry 3}
--             semGbeTotalRxBroadcastPackets     [obsolete]                     {semGbeStatusPacketCounterEntry 4}
--             semGbeTotalTxPackets              [obsolete]                     {semGbeStatusPacketCounterEntry 5}
--             semGbeTotalCollisions             [obsolete]                     {semGbeStatusPacketCounterEntry 6}
--             semGbeTotalRuntJumboFrames        [obsolete]                     {semGbeStatusPacketCounterEntry 7}
--             semGbeTotalPacketsInError         [obsolete]                     {semGbeStatusPacketCounterEntry 8}
--             semGbeCurrentNumOpenInputUdpPorts [obsolete]                     {semGbeStatusPacketCounterEntry 9}
--             semGbeRxSinglecastPackets         [obsolete]                     {semGbeStatusPacketCounterEntry 10}
--             semGbeRxBroadcastPackets          [obsolete]                     {semGbeStatusPacketCounterEntry 11}
--             semGbeTxPackets                   [obsolete]                     {semGbeStatusPacketCounterEntry 12}
--             semGbeCollisions                  [obsolete]                     {semGbeStatusPacketCounterEntry 13}
--             semGbeRuntJumboFrames             [obsolete]                     {semGbeStatusPacketCounterEntry 14}
--             semGbePacketsInError              [obsolete]                     {semGbeStatusPacketCounterEntry 15}
--       semGbeStatusRoutingTable                                               {semGbeStatus 5}
--          semGbeStatusRoutingEntry                                            {semGbeStatusRoutingTable 1}
--             semGbeStatusRoutingIndex                                         {semGbeStatusRoutingEntry 1}
--             semGbeStatusRoutingDestIpAddr                                    {semGbeStatusRoutingEntry 2}
--             semGbeStatusRoutingGateIpAddr                                    {semGbeStatusRoutingEntry 3}
--             semGbeStatusRoutingSubnetMask                                    {semGbeStatusRoutingEntry 4}
--             semGbeStatusRoutingGbePort                                       {semGbeStatusRoutingEntry 5}
--             semGbeStatusRoutingFlags                                         {semGbeStatusRoutingEntry 6}
--       semGbeStatusArpTable                                                   {semGbeStatus 6}
--          semGbeStatusArpEntry                                                {semGbeStatusArpTable 1}
--             semGbeStatusArpIndex                                             {semGbeStatusArpEntry 1}
--             semGbeStatusArpIpAddr                                            {semGbeStatusArpEntry 2}
--             semGbeStatusArpMacAddr                                           {semGbeStatusArpEntry 3}
--             semGbeStatusArpGbePort                                           {semGbeStatusArpEntry 4}
--             semGbeStatusArpFlags                                             {semGbeStatusArpEntry 5}
--       semGbeStatusLoopTerminatorTable                                        {semGbeStatus 7}
--          semGbeStatusLoopTerminatorEntry                                     {semGbeStatusLoopTerminatorTable 1}
--             semGbeStatusLoopTerminatorPortNum                                {semGbeStatusLoopTerminatorEntry 1}
--             semGbeStatusLoopTerminatorIndex                                  {semGbeStatusLoopTerminatorEntry 2}
--             semGbeStatusLoopTerminatorMacAddr                                {semGbeStatusLoopTerminatorEntry 3}
--       semGbeStatusOutputPacketTable                                          {semGbeStatus 8}
--          semGbeStatusOutputPacketEntry                                       {semGbeStatusOutputPacketTable 1}
--             semGbeStatusOutputPacketIndex                                    {semGbeStatusOutputPacketEntry 1}
--             semGbeStatusTotOutputPackets                                     {semGbeStatusOutputPacketEntry 2}
--             semGbeStatusNumOutputPackets                                     {semGbeStatusOutputPacketEntry 3}
--       semGbeStatusFrameCounterTableResetAll                                  {semGbeStatus 9}
--       semGbeStatusFrameCounterTable                                          {semGbeStatus 10}
--          semGbeStatusFrameCounterEntry                                       {semGbeStatusFrameCounterTable 1}
--             semGbeFrameCounterPortNum                                        {semGbeStatusFrameCounterEntry 1}
--             semGbeFrameCounterReset                                          {semGbeStatusFrameCounterEntry 2}
--             semGbeTotalRxSinglecastFrames                                    {semGbeStatusFrameCounterEntry 3}
--             semGbeTotalRxMulticastFrames                                     {semGbeStatusFrameCounterEntry 4}
--             semGbeTotalRxBroadcastFrames                                     {semGbeStatusFrameCounterEntry 5}
--             semGbeTotalRxErrorFrames                                         {semGbeStatusFrameCounterEntry 6}
--             semGbeTotalRxFrames                                              {semGbeStatusFrameCounterEntry 7}
--             semGbeTotalTxGoodFrames                                          {semGbeStatusFrameCounterEntry 8}
--             semGbeTotalTxErrorFrames                                         {semGbeStatusFrameCounterEntry 9}
--             semGbeTotalTxFrames                                              {semGbeStatusFrameCounterEntry 10}
--             semGbeRxSinglecastFrames                                         {semGbeStatusFrameCounterEntry 11}
--             semGbeRxMulticastFrames                                          {semGbeStatusFrameCounterEntry 12}
--             semGbeRxBroadcastFrames                                          {semGbeStatusFrameCounterEntry 13}
--             semGbeRxErrorFrames                                              {semGbeStatusFrameCounterEntry 14}
--             semGbeRxFrames                                                   {semGbeStatusFrameCounterEntry 15}
--             semGbeTxGoodFrames                                               {semGbeStatusFrameCounterEntry 16}
--             semGbeTxErrorFrames                                              {semGbeStatusFrameCounterEntry 17}
--             semGbeTxFrames                                                   {semGbeStatusFrameCounterEntry 18}
--       semGbeStatusFrameBufferTable                                           {semGbeStatus 11}
--          semGbeStatusFrameBufferEntry                                        {semGbeStatusFrameBufferTable 1}
--             semGbeStatusFrameBufferInterface                                 {semGbeStatusFrameBufferEntry 1}
--             semGbeStatusFrameBufferUdpPort                                   {semGbeStatusFrameBufferEntry 2}
--             semGbeStatusFrameBufferMaxMsLevel                                {semGbeStatusFrameBufferEntry 3}
--             semGbeStatusFrameBufferMaxPercentFull                            {semGbeStatusFrameBufferEntry 4}
--             semGbeStatusFrameBufferGpsTime                                   {semGbeStatusFrameBufferEntry 5}
--             semGbeStatusFrameBufferOverflows                                 {semGbeStatusFrameBufferEntry 6}
--             semGbeStatusFrameBufferResets                                    {semGbeStatusFrameBufferEntry 7}
--       semGbeStatusVlanCfmTable                                               {semGbeStatus 12}
--          semGbeStatusVlanCfmEntry                                            {semGbeStatusVlanCfmTable 1}
--             semGbeStatusVlanCfmStreamNum                                     {semGbeStatusVlanCfmEntry 1}
--             semGbeVlanTaggingVidInUse                                        {semGbeStatusVlanCfmEntry 2}
--             semGbeCfmInsertionOpcode                                         {semGbeStatusVlanCfmEntry 3}
         semGbeStatusInputUdp                             OBJECT IDENTIFIER ::= {semGbeStatus 13}
            semGbeStatusInputUdpGeneral                   OBJECT IDENTIFIER ::= {semGbeStatusInputUdp 1}
--             semGbeStatusInputUdpUpdateInterval                               {semGbeStatusInputUdpGeneral 1}
--          semGbeStatusInputUdpTable                                           {semGbeStatusInputUdp 2}
--             semGbeStatusInputUdpEntry                                        {semGbeStatusInputUdpTable 1}
--                semGbeStatInUdpIndex                                          {semGbeStatusInputUdpEntry 1}
--                semGbeStatInUdpState                                          {semGbeStatusInputUdpEntry 2}
--                semGbeStatInUdpSamplingPeriod                                 {semGbeStatusInputUdpEntry 3}
--                semGbeStatInUdpCurDataCount                                   {semGbeStatusInputUdpEntry 4}
--                semGbeStatInUdpAvgDataCount                                   {semGbeStatusInputUdpEntry 5}
--                semGbeStatInUdpMinDataCount                                   {semGbeStatusInputUdpEntry 6}
--                semGbeStatInUdpPeakDataCount                                  {semGbeStatusInputUdpEntry 7}
--                semGbeStatInUdpCurTsCount                                     {semGbeStatusInputUdpEntry 8}
--                semGbeStatInUdpAvgTsCount                                     {semGbeStatusInputUdpEntry 9}
--                semGbeStatInUdpMinTsCount                                     {semGbeStatusInputUdpEntry 10}
--                semGbeStatInUdpPeakTsCount                                    {semGbeStatusInputUdpEntry 11}
--                semGbeStatInUdpAlarmSummary                                   {semGbeStatusInputUdpEntry 12}
--                semGbeStatInUdpLowBitRateAlarm                                {semGbeStatusInputUdpEntry 13}
--                semGbeStatInUdpMptsRedundPriAlarm                             {semGbeStatusInputUdpEntry 14}
--                semGbeStatInUdpMptsRedundFailAlarm                            {semGbeStatusInputUdpEntry 15}
--                semGbeStatInUdpHighBitRateAlarm                               {semGbeStatusInputUdpEntry 16}
--          semGbeStatusCommandedInputUdpTable                                  {semGbeStatusInputUdp 3}
--             semGbeStatusCommandedInputUdpEntry                               {semGbeStatusCommandedInputUdpTable 1}
--                semGbeStatCommUdpIndex                                        {semGbeStatusCommandedInputUdpEntry 1}
--                semGbeStatCommUdpGbePort                                      {semGbeStatusCommandedInputUdpEntry 2}
--                semGbeStatCommUdpPort                                         {semGbeStatusCommandedInputUdpEntry 3}
--                semGbeStatCommUdpSamplingPeriod                               {semGbeStatusCommandedInputUdpEntry 4}
--                semGbeStatCommUdpCurDataCount                                 {semGbeStatusCommandedInputUdpEntry 5}
--                semGbeStatCommUdpAvgDataCount                                 {semGbeStatusCommandedInputUdpEntry 6}
--                semGbeStatCommUdpMinDataCount                                 {semGbeStatusCommandedInputUdpEntry 7}
--                semGbeStatCommUdpPeakDataCount                                {semGbeStatusCommandedInputUdpEntry 8}
--                semGbeStatCommUdpCurTsCount                                   {semGbeStatusCommandedInputUdpEntry 9}
--                semGbeStatCommUdpAvgTsCount                                   {semGbeStatusCommandedInputUdpEntry 10}
--                semGbeStatCommUdpMinTsCount                                   {semGbeStatusCommandedInputUdpEntry 11}
--                semGbeStatCommUdpPeakTsCount                                  {semGbeStatusCommandedInputUdpEntry 12}
   semQam                                                 OBJECT IDENTIFIER ::= {sem 4}
      semQamConfig                                        OBJECT IDENTIFIER ::= {semQam 1}
         semQamConfigGeneral                              OBJECT IDENTIFIER ::= {semQamConfig 1}
--          semQamConfigTransmissionMode                                        {semQamConfigGeneral 1}
--       semQamConfigTable                                                      {semQamConfig 2}
--          semQamConfigEntry                                                   {semQamConfigTable 1}
--             semQamConfigPortNum                                              {semQamConfigEntry 1}
--             semQamConfigMute                                                 {semQamConfigEntry 2}
--             semQamConfigMode                                                 {semQamConfigEntry 3}
--             semQamConfigInterleaverDepth                                     {semQamConfigEntry 4}
--             semQamConfigSymbolRate                                           {semQamConfigEntry 5}
--             semQamConfigSpectrumInvert                                       {semQamConfigEntry 6}
--             semQamConfigTestMode                                             {semQamConfigEntry 7}
--             semQamConfigRfGainLevel                                          {semQamConfigEntry 8}
--             semQamConfigIfFreq                                               {semQamConfigEntry 9}
--             semQamConfigIfGainLevel                                          {semQamConfigEntry 10}
      semQamStatus                                        OBJECT IDENTIFIER ::= {semQam 2}
         semQamStatusGeneral                              OBJECT IDENTIFIER ::= {semQamStatus 1}
--          semQamModuleInstalled                                               {semQamStatusGeneral 1}
--          semQamModuleMcn                                                     {semQamStatusGeneral 2}
--          semQamModuleVersion                                                 {semQamStatusGeneral 3}
--          semQamModuleFirmwareVersion                                         {semQamStatusGeneral 4}
--          semQamStatusNumOutputStreams                                        {semQamStatusGeneral 5}
--       semQamStatusTable                                                      {semQamStatus 2}
--          semQamStatusEntry                                                   {semQamStatusTable 2}
--             semQamStatusPortNum                                              {semQamStatusEntry 1}
--             semQamStatusInfoRate                                             {semQamStatusEntry 2}
--             semQamStatusMpegFecSyncLock                                      {semQamStatusEntry 3}
--             semQamStatusAlpha                                                {semQamStatusEntry 4}
--             semQamStatusInputBufferError                                     {semQamStatusEntry 5}
--             semQamStatusOutputBufferError                                    {semQamStatusEntry 6}
--             semQamStatusOutTransStreamNum                                    {semQamStatusEntry 7}
--             semQamStatusModulatorRevision                                    {semQamStatusEntry 8}
--             semQamStatusPllStatus                                            {semQamStatusEntry 9}
--             semQamStatusError                                                {semQamStatusEntry 10}
--             semQamStatusFault                                                {semQamStatusEntry 11}
--             semQamStatusPortError                                            {semQamStatusEntry 12}
--             semQamStatusPortFault                                            {semQamStatusEntry 13}
      semUpConvConfig                                     OBJECT IDENTIFIER ::= {semQam 3}
--       semUpConvConfigTable                                                   {semUpConvConfig 1}
--          semUpConvConfigEntry                                                {semUpConvConfigTable 1}
--             semUpConvConfigOutputNumber                                      {semUpConvConfigEntry 1}
--             semUpConvConfigApplyChange                                       {semUpConvConfigEntry 2}
--             semUpConvConfigTuningMode                                        {semUpConvConfigEntry 3}
--             semUpConvConfigEiaChanNumQamA                                    {semUpConvConfigEntry 4}
--             semUpConvConfigRfFreqQamA                                        {semUpConvConfigEntry 5}
--             semUpConvConfigRfChanSpacing                                     {semUpConvConfigEntry 6}
      semUpConvStatus                                     OBJECT IDENTIFIER ::= {semQam 4}
         semUpConvStatusGeneral                           OBJECT IDENTIFIER ::= {semUpConvStatus 1}
--          semUpconverterModuleInstalled                                       {semUpConvStatusGeneral 1}
--          semUpconverterModulePldVersion                                      {semUpConvStatusGeneral 2}
--          semUpconverterModuleMCN                                             {semUpConvStatusGeneral 3}
--          semUpconverterModuleVersion                                         {semUpConvStatusGeneral 4}
--       semUpConvStatusTable                                                   {semUpConvStatus 2}
--          semUpConvStatusEntry                                                {semUpConvStatusTable 1}
--             semUpConvStatusOutputNumber                                      {semUpConvStatusEntry 1}
--             semUpConvStatusEiaChanNumQamB                                    {semUpConvStatusEntry 2}
--             semUpConvStatusRfFreqQamB                                        {semUpConvStatusEntry 3}
--             semUpConvStatusRfOutLevelError                                   {semUpConvStatusEntry 4}
--             semUpConvStatusIfLevelError [obsolete]                           {semUpConvStatusEntry 5}
--             semUpConvStatusUpConvError                                       {semUpConvStatusEntry 6}
--             semUpConvStatusTemperature                                       {semUpConvStatusEntry 7}
--             semUpConvStatusFault                                             {semUpConvStatusEntry 8}
--             semUpConvStatusStartDigAtten                                     {semUpConvStatusEntry 9}
--             semUpConvStatusCurrentDigAtten                                   {semUpConvStatusEntry 10}
--             semUpConvStatusCurrentAgc                                        {semUpConvStatusEntry 11}
--             semUpConvStatusCurrentAgcLimit                                   {semUpConvStatusEntry 12}
--       semUpConvModuleStatusTable                                             {semUpConvStatus 3}
--          semUpConvModuleStatusEntry                                          {semUpConvModuleStatusTable 1}
--             semUpConvModuleNumber                                            {semUpConvModuleStatusEntry 1}
--             semUpConvModuleInstalled                                         {semUpConvModuleStatusEntry 2}
--             semUpConvModulePldVersion                                        {semUpConvModuleStatusEntry 3}
--             semUpConvModuleMcn                                               {semUpConvModuleStatusEntry 4}
--             semUpConvModuleVersion                                           {semUpConvModuleStatusEntry 5}
   semHostIp                                              OBJECT IDENTIFIER ::= {sem 5}
      semHostIpConfig                                     OBJECT IDENTIFIER ::= {semHostIp 1}
         semHostIpConfigGeneral                           OBJECT IDENTIFIER ::= {semHostIpConfig 1}
--          semHostIpDefaultGateway                                             {semHostIpConfigGeneral 1}
--          semHostIpRoutingApplyChange [not currently supported]               {semHostIpConfigGeneral 2}
--          semHostIpMulticastApplyChange                                       {semHostIpConfigGeneral 3}
      semHostIpStatus                                     OBJECT IDENTIFIER ::= {semHostIp 2}
         semHostIpStatusGeneral                           OBJECT IDENTIFIER ::= {semHostIpStatus 1}
--          semHostIpMaxInputUdpPorts                                           {semHostIpStatusGeneral 1}
         semHostIpStatistics                              OBJECT IDENTIFIER ::= {semHostIpStatus 2}
--          semHostIpPacketStatisticsTable                                      {semHostIpStatistics 1}
--             semHostIpPacketStatisticsEntry                                   {semHostIpPacketStatisticsTable 1}
--                semHostIpPacketStatHostIpPortNum                              {semHostIpPacketStatisticsEntry 1}
--                semHostIpPacketStatNumRcvPkts                                 {semHostIpPacketStatisticsEntry 2}
--                semHostIpPacketStatNumInsPkts                                 {semHostIpPacketStatisticsEntry 3}
--                semHostIpPacketStatTotRcvPkts                                 {semHostIpPacketStatisticsEntry 4}
--                semHostIpPacketStatTotInsPkts                                 {semHostIpPacketStatisticsEntry 5}
--                semHostIpPacketStatNumDiscardPkts                             {semHostIpPacketStatisticsEntry 6}
--                semHostIpPacketStatTotDiscardPkts                             {semHostIpPacketStatisticsEntry 7}
      semOampConfig                                       OBJECT IDENTIFIER ::= {semHostIp 3}
         semOampConfigGeneral                             OBJECT IDENTIFIER ::= {semOampConfig 1}
--          semOampIpAddr                                                       {semOampConfigGeneral 1}
--          semOampSubnetMask                                                   {semOampConfigGeneral 2}
--       semOampMulticastRcvTable                                               {semOampConfig 2}
--          semOampMulticastRcvEntry                                            {semOampMulticastRcvTable 1}
--             semOampMulticastRcvIndex                                         {semOampMulticastRcvEntry 1}
--             semOampMulticastRcvIpAddr                                        {semOampMulticastRcvEntry 2}
--             semOampMulticastRcvUdpPort                                       {semOampMulticastRcvEntry 3}
      semOampStatus                                       OBJECT IDENTIFIER ::= {semHostIp 4}
         semOampStatusGeneral                             OBJECT IDENTIFIER ::= {semOampStatus 1}
--          semOampMacAddr                                                      {semOampStatusGeneral 1}
--          semOampNumberInputStreams                                           {semOampStatusGeneral 2}
--          semOampPortSpeed                                                    {semOampStatusGeneral 3}
--          semOampPortDuplexMode                                               {semOampStatusGeneral 4}
--          semOampAutoNegotiate                                                {semOampStatusGeneral 5}
         semOampStatistics                                OBJECT IDENTIFIER ::= {semOampStatus 2}
      semDataIpConfig                                     OBJECT IDENTIFIER ::= {semHostIp 5}
         semDataIpConfigGeneral                           OBJECT IDENTIFIER ::= {semDataIpConfig 1}
--          semDataIpAddr                                                       {semDataIpConfigGeneral 1}
--          semDataIpSubnetMask                                                 {semDataIpConfigGeneral 2}
--       semDataIpMulticastRcvTable                                             {semDataIpConfig 2}
--          semDataIpMulticastRcvEntry                                          {semDataIpMulticastRcvTable 1}
--             semDataIpMulticastRcvIndex                                       {semDataIpMulticastRcvEntry 1}
--             semDataIpMulticastRcvIpAddr                                      {semDataIpMulticastRcvEntry 2}
--             semDataIpMulticastRcvUdpPort                                     {semDataIpMulticastRcvEntry 3}
      semDataIpStatus                                     OBJECT IDENTIFIER ::= {semHostIp 6}
         semDataIpStatusGeneral                           OBJECT IDENTIFIER ::= {semDataIpStatus 1}
--          semDataIpMacAddr                                                    {semDataIpStatusGeneral 1}
--          semDataIpNumberInputStreams                                         {semDataIpStatusGeneral 2}
--          semDataIpPortSpeed                                                  {semDataIpStatusGeneral 3}
--          semDataIpPortDuplexMode                                             {semDataIpStatusGeneral 4}
--          semDataIpAutoNegotiate                                              {semDataIpStatusGeneral 5}
         semDataIpStatistics                              OBJECT IDENTIFIER ::= {semDataIpStatus 2}
   semAcp                                                 OBJECT IDENTIFIER ::= {sem 6}
      semAcpConfig                                        OBJECT IDENTIFIER ::= {semAcp 1}
         semAcpConfigGeneral                              OBJECT IDENTIFIER ::= {semAcpConfig 1}
--          semAcpEncryptAlgorithm                                              {semAcpConfigGeneral 1}
--          semAcpReProgramControlFpga                                          {semAcpConfigGeneral 2}
      semAcpStatus                                        OBJECT IDENTIFIER ::= {semAcp 2}
         semAcpStatusGeneral                              OBJECT IDENTIFIER ::= {semAcpStatus 1}
--          semAcpModuleInstalled                                               {semAcpStatusGeneral 1}
--          semAcpWkePeriod                                                     {semAcpStatusGeneral 2}
--          semAcpUnitCreatedAs                                                 {semAcpStatusGeneral 3}
         semAcpModule                                     OBJECT IDENTIFIER ::= {semAcpStatus 2}
--          semAcpBoardType                                                     {semAcpModule 1}
--          semAcpBoardVersion                                                  {semAcpModule 1}
--          semAcpFpgaVersion                                                   {semAcpModule 1}
--          semAcpCascadeUnitSize                                               {semAcpModule 1}
--          semAcpServicesPerCU                                                 {semAcpModule 1}
--          semAcpCascadeUnitCount                                              {semAcpModule 1}
--       semAcpStatusTransportTable                                             {semAcpStatus 3}
--          semAcpStatusTransportEntry                                          {semAcpStatusTransportTable 1}
--             semAcpTransportIndex                                             {semAcpStatusTransportEntry 1}
--             semAcpFirstAcpNumber                                             {semAcpStatusTransportEntry 2}
--             semAcpLastAcpNumber                                              {semAcpStatusTransportEntry 3}
--             semAcpServAuthFailedCount                                        {semAcpStatusTransportEntry 4}
--       semAcpStatusTable                                                      {semAcpStatus 4}
--          semAcpStatusEntry                                                   {semAcpStatusTable 1}
--             semAcpIndex                                                      {semAcpStatusEntry 1}
--             semAcpUnitAddress                                                {semAcpStatusEntry 2}
--             semAcpOutputTransport                                            {semAcpStatusEntry 3}
   semOutputTransport                                     OBJECT IDENTIFIER ::= {sem 7}
      semOutTransConfig                                   OBJECT IDENTIFIER ::= {semOutputTransport 1}
         semOutTransConfigGeneral                         OBJECT IDENTIFIER ::= {semOutTransConfig 1}
--          semPcrOffset                                                        {semOutTransConfigGeneral 1}
--          semOutTransHighLowSpeedMode                                         {semOutTransConfigGeneral 2}
--       semOutTransStreamTable                                                 {semOutTransConfig 2}
--          semOutTransStreamEntry                                              {semOutTransStreamTable 1}
--             semOutTransStreamStreamNum                                       {semOutTransStreamEntry 1}
--             semOutTransStreamEnable                                          {semOutTransStreamEntry 2}
--             semOutTransStreamPhysOutType                                     {semOutTransStreamEntry 3}
--             semOutTransStreamPhysOutPort                                     {semOutTransStreamEntry 4}
--             semOutTransStreamClockAssigned                                   {semOutTransStreamEntry 5}
--             semOutTransStreamNumEncryptPrograms                              {semOutTransStreamEntry 6}
--       semOutputClockConfigTable                                              {semOutTransConfig 3}
--          semOutputClockConfigEntry                                           {semOutputClockConfigTable 1}
--             semOutputClockConfigNum                                          {semOutputClockConfigEntry 1}
--             semOutputClockConfigRate                                         {semOutputClockConfigEntry 2}
         semOutTransUtilizationMonitoring                 OBJECT IDENTIFIER ::= {semOutTransConfig 4}
            semOutTransUtilizationMonitorGeneral          OBJECT IDENTIFIER ::= {semOutTransUtilizationMonitoring 1}
--             semOutTransUtilMonAlarmThreshold                                 {semOutTransUtilizationMonitorGeneral 1}
--             semOutTransUtilMonSetAlarmDelay                                  {semOutTransUtilizationMonitorGeneral 2}
--             semOutTransUtilMonClearAlarmDelay                                {semOutTransUtilizationMonitorGeneral 3}
--          semOutTransUtilizationMonitorTable                                  {semOutTransUtilizationMonitoring 2}
--             semOutTransUtilizationMonitorEntry                               {semOutTransUtilizationMonitorTable 1}
--                semOutTransUtilMonStreamNum                                   {semOutTransUtilizationMonitorEntry 1}
--                semOutTransUtilMonEnable                                      {semOutTransUtilizationMonitorEntry 2}
--                semOutTransUtilMonFlushHistory                                {semOutTransUtilizationMonitorEntry 3}
--                semOutTransUtilMonFlushStart                                  {semOutTransUtilizationMonitorEntry 4}
--                semOutTransUtilMonFlushEnd                                    {semOutTransUtilizationMonitorEntry 5}
--       semIpConfigInsertionRateTable                                          {semOutTransConfig 5}
--          semIpConfigInsertionRateEntry                                       {semIpConfigInsertionRateTable 1}
--             semIpConfigInsertionRateStreamNum                                {semIpConfigInsertionRateEntry 1}
--             semIpConfigInsertionRate                                         {semIpConfigInsertionRateEntry 2}
--       semOutTransPidRemappingTable                                           {semOutTransConfig 6}
--          semOutTransPidRemappingEntry                                        {semOutTransPidRemappingTable 1}
--             semOutTransPidRemappingStreamNum                                 {semOutTransPidRemappingEntry 1}
--             semOutTransPidRemapping                                          {semOutTransPidRemappingEntry 2}
--             semOutTransPidsPerProgram                                        {semOutTransPidRemappingEntry 3}
      semOutTransStatus                                   OBJECT IDENTIFIER ::= {semOutputTransport 2}
         semOutTransStatusGeneral                         OBJECT IDENTIFIER ::= {semOutTransStatus 1}
--          semNumOutputProgramsPerTS    [obsolete]                             {semOutTransStatusGeneral 1}
--       semOutputClockStatusTable                                              {semOutTransStatus 2}
--          semOutputClockStatusEntry                                           {semOutputClockStatusTable 1}
--             semOutputClockStatusNum                                          {semOutputClockStatusEntry 1}
--             semOutputClockStatusRate                                         {semOutputClockStatusEntry 2}
         semOutTransUtilization                           OBJECT IDENTIFIER ::= {semOutTransStatus 3}
            semOutTransUtilizationGeneral                 OBJECT IDENTIFIER ::= {semOutTransUtilization 1}
--             semOutTransUtilizationSamplePeriod                               {semOutTransUtilizationGeneral 1}
--             semOutTransUtilizationLastIndexWritten                           {semOutTransUtilizationGeneral 2}
--          semOutTransUtilizationTable                                         {semOutTransUtilization 2}
--             semOutTransUtilizationEntry                                      {semOutTransUtilizationTable 1}
--                semOutTransUtilizationStreamNum                               {semOutTransUtilizationEntry 1}
--                semOutTransUtilizationDataFlag                                {semOutTransUtilizationEntry 2}
--                semOutTransUtilizationNumSamples                              {semOutTransUtilizationEntry 3}
--                semOutTransUtilizationError                                   {semOutTransUtilizationEntry 4}
--                semOutTransUtilizationTime                                    {semOutTransUtilizationEntry 5}
--                semOutTransUtilizationPercent                                 {semOutTransUtilizationEntry 6}
--                semOutTransUtilizationAvgPercent                              {semOutTransUtilizationEntry 7}
--                semOutTransUtilizationPeakPercent                             {semOutTransUtilizationEntry 8}
--                semOutTransUtilizationMinPercent                              {semOutTransUtilizationEntry 9}
--                semOutTransUtilizationRate                                    {semOutTransUtilizationEntry 10}
--                semOutTransUtilizationAvgRate                                 {semOutTransUtilizationEntry 11}
--                semOutTransUtilizationPeakRate                                {semOutTransUtilizationEntry 12}
--                semOutTransUtilizationMinRate                                 {semOutTransUtilizationEntry 13}
--          semOutTransUtilizationHistoryTable                                  {semOutTransUtilization 3}
--             semOutTransUtilizationHistoryEntry                               {semOutTransUtilizationHistoryTable 1}
--                semOutTransUtilHistStreamNum                                  {semOutTransUtilizationHistoryEntry 1}
--                semOutTransUtilHistIndex                                      {semOutTransUtilizationHistoryEntry 2}
--                semOutTransUtilHistDataFlag                                   {semOutTransUtilizationHistoryEntry 3}
--                semOutTransUtilHistNumSamples                                 {semOutTransUtilizationHistoryEntry 4}
--                semOutTransUtilHistError                                      {semOutTransUtilizationHistoryEntry 5}
--                semOutTransUtilHistTime                                       {semOutTransUtilizationHistoryEntry 6}
--                semOutTransUtilHistAvgPercent                                 {semOutTransUtilizationHistoryEntry 7}
--                semOutTransUtilHistMinPercent                                 {semOutTransUtilizationHistoryEntry 8}
--                semOutTransUtilHistPeakPercent                                {semOutTransUtilizationHistoryEntry 9}
--                semOutTransUtilHistAvgRate                                    {semOutTransUtilizationHistoryEntry 10}
--                semOutTransUtilHistMinRate                                    {semOutTransUtilizationHistoryEntry 11}
--                semOutTransUtilHistPeakRate                                   {semOutTransUtilizationHistoryEntry 12}
         semOutTransStatistics                            OBJECT IDENTIFIER ::= {semOutTransStatus 4}
            semOutTransStatisticsGeneral                  OBJECT IDENTIFIER ::= {semOutTransStatistics 1}
--          semInsertPacketStatisticsTable                                      {semOutTransStatistics 2}
--             semInsertPacketStatisticsEntry                                   {semInsertPacketStatisticsTable 1}
--                semInsertPacketStatOutTransStreamNum                          {semInsertPacketStatisticsEntry 1}
--                semInsertPacketStatTotPkts                                    {semInsertPacketStatisticsEntry 2}
--                semInsertPacketStatNumPkts                                    {semInsertPacketStatisticsEntry 3}
--          semIpInsertPacketStatisticsTable                                    {semOutTransStatistics 3}
--             semIpInsertPacketStatisticsEntry                                 {semIpInsertPacketStatisticsTable 1}
--                semIpInsertPacketStatOutTransStreamNum                        {semIpInsertPacketStatisticsEntry 1}
--                semIpInsertPacketStatTotPkts                                  {semIpInsertPacketStatisticsEntry 2}
--                semIpInsertPacketStatNumPkts                                  {semIpInsertPacketStatisticsEntry 3}
--                semIpInsertPacketStatTotDiscardPkts                           {semIpInsertPacketStatisticsEntry 4}
--                semIpInsertPacketStatNumDiscardPkts                           {semIpInsertPacketStatisticsEntry 5}
--       semOutTransStatusTable                                                 {semOutTransStatus 5}
--          semOutTransStatusEntry                                              {semOutTransStatusTable 1}
--             semOutTransStatusStreamNum                                       {semOutTransStatusEntry 1}
--             semOutTransStatusFault                                           {semOutTransStatusEntry 2}
--             semOutTransStatusOverflow                                        {semOutTransStatusEntry 3}
--             semOutTransStatusCorrupted                                       {semOutTransStatusEntry 4}
--             semOutTransStatusIpAddr                                          {semOutTransStatusEntry 5}
--             semOutTransStatusUdpPort                                         {semOutTransStatusEntry 6}
--             semOutTransStatusInterface                                       {semOutTransStatusEntry 7}
--             semOutTransStatusProgramsPerTs                                   {semOutTransStatusEntry 8}
   semUdpMap                                              OBJECT IDENTIFIER ::= {sem 8}
      semUdpMapConfig                                     OBJECT IDENTIFIER ::= {semUdpMap 1}
         semUdpMapConfigGeneral                           OBJECT IDENTIFIER ::= {semUdpMapConfig 1}
--          semUdpMapConfigGbePort                                              {semUdpMapConfigGeneral 1}
--          semUdpMapConfigBaseUdpOffset                                        {semUdpMapConfigGeneral 2}
--          semUdpMapConfigInSvcPreEncryption                                   {semUdpMapConfigGeneral 3}
--          semUdpMapConfigTsIdOffset                                           {semUdpMapConfigGeneral 4}
--          semUdpMapConfigModeBits                                             {semUdpMapConfigGeneral 5}
--       semUdpMapConfigTable                                                   {semUdpMapConfig 2}
--          semUdpMapConfigEntry                                                {semUdpMapConfigTable 1}
--             semUdpMapConfigOutTransStreamNum                                 {semUdpMapConfigEntry 1}
--             semUdpMapConfigApplyChange                                       {semUdpMapConfigEntry 2}
--             semUdpMapConfigStartProgramNumber                                {semUdpMapConfigEntry 3}
--             semUdpMapConfigNumPrograms                                       {semUdpMapConfigEntry 4}
--             semUdpMapConfigOutPatTsId                                        {semUdpMapConfigEntry 5}
--             semUdpMapConfigOutIpAddr                                         {semUdpMapConfigEntry 6}
--             semUdpMapConfigOutUdpPort                                        {semUdpMapConfigEntry 7}
      semUdpMapStatus                                     OBJECT IDENTIFIER ::= {semUdpMap 2}
--       semUdpMapInvalidApplyText                                              {semUdpMapStatus 1}
   semSimulcrypt                                          OBJECT IDENTIFIER ::= {sem 9}
      semSimConfig                                        OBJECT IDENTIFIER ::= {semSimulcrypt 1}
         semSimConfigGeneral                              OBJECT IDENTIFIER ::= {semSimConfig 1}
--          semSimIpInterfaceSelect                                             {semSimConfigGeneral 1}
      semSimStatus                                        OBJECT IDENTIFIER ::= {semSimulcrypt 2}
         semSimStatusGeneral                              OBJECT IDENTIFIER ::= {semSimStatus 1}
   semRemuxStatus                                         OBJECT IDENTIFIER ::= {sem 10}
      semRemuxStatusTable                                 OBJECT IDENTIFIER ::= {semRemuxStatus 1}
--    semPsiTable                                                               {semRemuxStatus 2}
--       semPsiEntry                                                            {semPsiTable 1}
--          semPsiTableType                                                     {semPsiEntry 1}
--          semPsiId                                                            {semPsiEntry 2}
--          semPsiPid                                                           {semPsiEntry 3}
--          semPsiMessageType                                                   {semPsiEntry 4}
--          semPsiProgramNumber                                                 {semPsiEntry 5}
--          semPsiSegment                                                       {semPsiEntry 6}
--          semPsiPart                                                          {semPsiEntry 7}
--          semPsiBody                                                          {semPsiEntry 8}
      semManRemuxStatus                                   OBJECT IDENTIFIER ::= {semRemuxStatus 3}
--       semManRemuxMapInvalidApplyText                                         {semManRemuxStatus 1}
--       semManRemuxOutTsInvalidApplyText                                       {semManRemuxStatus 2}
      semRemuxStatusGeneral                               OBJECT IDENTIFIER ::= {semRemuxStatus 4}
--       semMaxInternalServiceMappings                                          {semRemuxStatusGeneral 1}
--       semMaxInternalPidMappings                                              {semRemuxStatusGeneral 2}
   semManRemuxConfig                                      OBJECT IDENTIFIER ::= {sem 11}
--    semManRemuxMapTable                                                       {semManRemuxConfig 1}
--       semManRemuxMapEntry                                                    {semManRemuxMapTable 1}
--          semManRemuxMapIndex                                                 {semManRemuxMapEntry 1}
--          semManRemuxMapApplyChange                                           {semManRemuxMapEntry 2}
--          semManRemuxMapEnable                                                {semManRemuxMapEntry 3}
--          semManRemuxMapPhysInType                                            {semManRemuxMapEntry 4}
--          semManRemuxMapPhysInPort                                            {semManRemuxMapEntry 5}
--          semManRemuxMapInputUdp                                              {semManRemuxMapEntry 6}
--          semManRemuxMapInputProgNum                                          {semManRemuxMapEntry 7}
--          semManRemuxMapInputPid [obsolete]                                   {semManRemuxMapEntry 8}
--          semManRemuxMapOutTransStreamNum                                     {semManRemuxMapEntry 9}
--          semManRemuxMapOutputProgNum                                         {semManRemuxMapEntry 10}
--          semManRemuxMapOutputPid [obsolete]                                  {semManRemuxMapEntry 11}
--          semManRemuxMapPassThrough                                           {semManRemuxMapEntry 12}
--          semManRemuxMapInSvcPreEncryption                                    {semManRemuxMapEntry 13}
--    semManRemuxOutTsTable                                                     {semManRemuxConfig 2}
--       semManRemuxOutTsEntry                                                  {semManRemuxOutTsTable 1}
--          semManRemuxOutTsOutTransStreamNum                                   {semManRemuxOutTsEntry 1}
--          semManRemuxOutTsApplyChange                                         {semManRemuxOutTsEntry 2}
--          semManRemuxOutTsPatTsId                                             {semManRemuxOutTsEntry 3}
--          semManRemuxOutputIpAddr                                             {semManRemuxOutTsEntry 4}
--          semManRemuxOutputUdpPort                                            {semManRemuxOutTsEntry 5}
   semAsiDemux                                            OBJECT IDENTIFIER ::= {sem 12}
      semAsiDemuxConfig                                   OBJECT IDENTIFIER ::= {semAsiDemux 1}
         semAsiDemuxConfigGeneral                         OBJECT IDENTIFIER ::= {semAsiDemuxConfig 1}
--          semAsiDemuxConfigInSvcPreEncryption                                 {semAsiDemuxConfigGeneral 1}
--       semAsiDemuxConfigTable                                                 {semAsiDemuxConfig 2}
--          semAsiDemuxConfigEntry                                              {semAsiDemuxConfigTable 1}
--             semAsiDemuxConfigOutTransStreamNum                               {semAsiDemuxConfigEntry 1}
--             semAsiDemuxConfigApplyChange                                     {semAsiDemuxConfigEntry 2}
--             semAsiDemuxConfigAsiInputPort                                    {semAsiDemuxConfigEntry 3}
--             semAsiDemuxConfigStartProgramNumber                              {semAsiDemuxConfigEntry 4}
--             semAsiDemuxConfigNumPrograms                                     {semAsiDemuxConfigEntry 5}
--             semAsiDemuxConfigOutPatTsId                                      {semAsiDemuxConfigEntry 6}
--             semAsiDemuxConfigOutIpAddr                                       {semAsiDemuxConfigEntry 7}
--             semAsiDemuxConfigOutUdpPort                                      {semAsiDemuxConfigEntry 8}
      semAsiDemuxStatus                                   OBJECT IDENTIFIER ::= {semAsiDemux 2}
--       semAsiDemuxInvalidApplyText                                            {semAsiDemuxStatus 1}
   semPsip                                                OBJECT IDENTIFIER ::= {sem 13}
      semPsipConfig                                       OBJECT IDENTIFIER ::= {semPsip 1}
         semPsipConfigGeneral                             OBJECT IDENTIFIER ::= {semPsipConfig 1}
--          semPsipMgtMsgInsertionPeriod                                        {semPsipConfigGeneral 1}
--          semPsipSttMsgInsertionPeriod                                        {semPsipConfigGeneral 2}
--          semPsipCvctMsgInsertionPeriod                                       {semPsipConfigGeneral 3}
--          semPsipRrtMsgInsertionPeriod                                        {semPsipConfigGeneral 4}
--          semPsipBasePidPacketInsertionPeriod                                 {semPsipConfigGeneral 5}
--          semPsipNumEitPerOutputStream                                        {semPsipConfigGeneral 6}
--       semPsipConfigTable                                                     {semPsipConfig 2}
--          semPsipConfigEntry                                                  {semPsipConfigTable 1}
--             semPsipConfigOutStreamNum                                        {semPsipConfigEntry 1}
--             semPsipConfigEnable                                              {semPsipConfigEntry 2}
--       semPsipEitConfigTable                                                  {semPsipConfig 3}
--          semPsipEitConfigEntry                                               {semPsipEitConfigTable 1}
--             semPsipEitConfigEitIndex                                         {semPsipEitConfigEntry 1}
--             semPsipEitConfigMsgInsertionPeriod                               {semPsipEitConfigEntry 2}
--             semPsipEitConfigPacketInsertionPeriod                            {semPsipEitConfigEntry 3}
      semPsipStatus                                       OBJECT IDENTIFIER ::= {semPsip 2}
         semPsipStatusGeneral                             OBJECT IDENTIFIER ::= {semPsipStatus 1}
--          semPsipInputCount                                                   {semPsipStatusGeneral 1}
   semDvs208Eas                                           OBJECT IDENTIFIER ::= {sem 14}
      semDvs208EasConfig                                  OBJECT IDENTIFIER ::= {semDvs208Eas 1}
         semDvs208EasConfigGeneral                        OBJECT IDENTIFIER ::= {semDvs208EasConfig 1}
--          semDvs208EasEnable                                                  {semDvs208EasConfigGeneral 1}
--          semDvs208EasHostEnet                                                {semDvs208EasConfigGeneral 2}
--          semDvs208EasUdpPort                                                 {semDvs208EasConfigGeneral 3}
--          semDvs208EasMulticastRcvIpAddr                                      {semDvs208EasConfigGeneral 4}
      semDvs208EasStatus                                  OBJECT IDENTIFIER ::= {semDvs208Eas 2}
         semDvs208EasStatusGeneral                        OBJECT IDENTIFIER ::= {semDvs208EasStatus 1}
--          semDvs208EasNumRcvMsgs                                              {semDvs208EasStatusGeneral 1}
--          semDvs208EasNumInvalRcvMsgs                                         {semDvs208EasStatusGeneral 2}
   semEntitlements                                        OBJECT IDENTIFIER ::= {sem 15}
         semEntTransportEncrypt                           OBJECT IDENTIFIER ::= {semEntitlements 1}
--          semEntTransEncryptMcDes                       OBJECT IDENTIFIER ::= {semEntTransportEncrypt 2}
--          semEntTransEncryptCsaV1                       OBJECT IDENTIFIER ::= {semEntTransportEncrypt 4}

         semEntControlWordDelivery                        OBJECT IDENTIFIER ::= {semEntitlements 2}
--          semEntControlWordSharing                      OBJECT IDENTIFIER ::= {semEntControlWordDelivery 1
--          semEntControlWordClear                        OBJECT IDENTIFIER ::= {semEntControlWordDelivery 2}
   semPidMapping                                          OBJECT IDENTIFIER ::= {sem 16}
      semPidMapConfig                                     OBJECT IDENTIFIER ::= {semPidMapping 1}
--       semPidMapTable                                                         {semPidMapConfig 1}
--          semPidMapEntry                                                      {semPidMapTable 1}
--             semPidMapIndex                                                   {semPidMapEntry 1}
--             semPidMapApplyChange                                             {semPidMapEntry 2}
--             semPidMapEnable                                                  {semPidMapEntry 3}
--             semPidMapPhysInType                                              {semPidMapEntry 4}
--             semPidMapPhysInPort                                              {semPidMapEntry 5}
--             semPidMapInputUdp                                                {semPidMapEntry 6}
--             semPidMapInputPid                                                {semPidMapEntry 7}
--             semPidMapOutTransStreamNum                                       {semPidMapEntry 8}
--             semPidMapOutputPid                                               {semPidMapEntry 9}
         semPidMapStatus                                  OBJECT IDENTIFIER ::= {semPidMapping 2}
--          semPidMapInvalidApplyText                                           {semPidMapStatus 1}
   semInternalControlOfEncryption                         OBJECT IDENTIFIER ::= {sem 17}
      semIceConfig                                        OBJECT IDENTIFIER ::= {semInternalControlOfEncryption 1}
         semIceConfigGeneral                              OBJECT IDENTIFIER ::= {semIceConfig 1}
         semIceProgramConfig                              OBJECT IDENTIFIER ::= {semIceConfig 2}
--          semIceProgramConfigApplyChange                                      {semIceProgramConfig 1}
--          semIceSetDefault                                                    {semIceProgramConfig 2}
--          semIceCommonTierEncryptionEnable                                    {semIceProgramConfig 3}
--          semIceEncryptionMode                                                {semIceProgramConfig 4}
--          semIceCciLevel                                                      {semIceProgramConfig 5}
--          semIceCciLevelSource                                                {semIceProgramConfig 6}
--          semIceApsLevel                                                      {semIceProgramConfig 7}
--          semIceTier                                                          {semIceProgramConfig 8}
--          semIceEpochDuration                                                 {semIceProgramConfig 9}
--          semIceConstrainedImageTrigger                                       {semIceProgramConfig 10}
         semIceEmmConfig                                  OBJECT IDENTIFIER ::= {semIceConfig 3}
--          semIceEmmConfigApplyChange                                          {semIceEmmConfig 1}
--          semIceEmmSetDefault                                                 {semIceEmmConfig 2}
--          semIceEmmPollInterval                                               {semIceEmmConfig 3}
--          semIceEmmPollRandomization                                          {semIceEmmConfig 4}
--          semIceEmmPollTimeout                                                {semIceEmmConfig 5}
--          semIceEmmPollRetryCount                                             {semIceEmmConfig 6}
--          semIceEmmRefresh                                                    {semIceEmmConfig 7}
--          semIceEmmFullEncryptExpirationTime                                  {semIceEmmConfig 8}
--          semIceEmmServerIpAddr                                               {semIceEmmConfig 9}
--          semIceEmmServerTcpPort                                              {semIceEmmConfig 10}
--          semIceEmmServerErrorCountReset                                      {semIceEmmConfig 11}
--          semIceEmmFullEncryptFailureCountReset                               {semIceEmmConfig 12}
--          semIceEmmServerCommAlarmClear                                       {semIceEmmConfig 13}
--          semIceEmmServerInvalRespAlarmClear                                  {semIceEmmConfig 14}
      semIceStatus                                        OBJECT IDENTIFIER ::= {semInternalControlOfEncryption 2}
         semIceStatusGeneral                              OBJECT IDENTIFIER ::= {semIceStatus 1}
         semIceProgramStatus                              OBJECT IDENTIFIER ::= {semIceStatus 2}
--          semIceCurrentEncryptionMode                                         {semIceProgramStatus 1}
--          semIceCurrentEpochNumber                                            {semIceProgramStatus 2}
--          semIceEpochExpirationTime                                           {semIceProgramStatus 3}
--          semIceEncryptionModeTableSize                                       {semIceProgramStatus 4}
--       semIceStatusEncryptionModeTable                                        {semIceStatus 3}
--          semIceStatusEncryptionModeEntry                                     {semIceStatusEncryptionModeTable 1}
--             semIceStatusEncryptionModeIndex                                  {semIceStatusEncryptionModeEntry 1}
--             semIceStatusEncryptionMode                                       {semIceStatusEncryptionModeEntry 2}
--             semIceStatusEncryptionModeTime                                   {semIceStatusEncryptionModeEntry 3}
--             semIceStatusEncryptionModeReason                                 {semIceStatusEncryptionModeEntry 4}
         semIceEmmStatus                                  OBJECT IDENTIFIER ::= {semIceStatus 4}
            semIceEmmStatusGeneral                        OBJECT IDENTIFIER ::= {semIceEmmStatus 1}
--             semIceEmmCurrentCsn                                              {semIceEmmStatusGeneral 1}
--             semIceEmmNextPollTime                                            {semIceEmmStatusGeneral 2}
--             semIceEmmFullEncryptStopTime                                     {semIceEmmStatusGeneral 3}
--             semIceEmmLastRolloverTime                                        {semIceEmmStatusGeneral 4}
--             semIceEmmServerCommErrorCount                                    {semIceEmmStatusGeneral 5}
--             semIceEmmServerInvalidResponseCount                              {semIceEmmStatusGeneral 6}
--             semIceEmmFullEncryptFailureCount                                 {semIceEmmStatusGeneral 7}
--             semIceEmmStatusTableSize                                         {semIceEmmStatusGeneral 8}
--          semIceEmmStatusTable                                                {semIceEmmStatus 2}
--             semIceEmmStatusEntry                                             {semIceEmmStatusTable 1}
--                semIceEmmStatusTblIndex                                       {semIceEmmStatusEntry 1}
--                semIceEmmStatusTblCsn                                         {semIceEmmStatusEntry 2}
--                semIceEmmStatusTblState                                       {semIceEmmStatusEntry 3}
--                semIceEmmStatusTblTime                                        {semIceEmmStatusEntry 4}
--                semIceEmmStatusTblServerError                                 {semIceEmmStatusEntry 5}
--                semIceEmmStatusTblAcpUnitAddress                              {semIceEmmStatusEntry 6}
   semIsaSdv                                              OBJECT IDENTIFIER ::= {sem 18}
      semIsaSdvConfig                                     OBJECT IDENTIFIER ::= {semIsaSdv 1}
         semIsaSdvConfigGeneral                           OBJECT IDENTIFIER ::= {semIsaSdvConfig 1}
--          semIsaSdvGbePort                                                    {semIsaSdvConfigGeneral 1}
--          semIsaSdvDataCarouselProgram                                        {semIsaSdvConfigGeneral 2}
      semIsaSdvStatus                                     OBJECT IDENTIFIER ::= {semIsaSdv 2}
         semIsaSdvStatusGeneral                           OBJECT IDENTIFIER ::= {semIsaSdvStatus 1}
--       semIsaSdvSessionStatTable                                              {semIsaSdvStatus 2}
--          semIsaSdvSessionStatEntry                                           {semIsaSdvSessionStatTable 1}
--             semIsaSdvSessionStatIndex                                        {semIsaSdvSessionStatEntry 1}
--             semIsaSdvSessionStatInputGbePort                                 {semIsaSdvSessionStatEntry 2}
--             semIsaSdvSessionStatInputUdpPort                                 {semIsaSdvSessionStatEntry 3}
--             semIsaSdvSessionStatInputProgramNum                              {semIsaSdvSessionStatEntry 4}
--             semIsaSdvSessionStatMulticastIpAddr                              {semIsaSdvSessionStatEntry 5}
--             semIsaSdvSessionStatSourceIpAddr1                                {semIsaSdvSessionStatEntry 6}
--             semIsaSdvSessionStatSourceIpAddr2                                {semIsaSdvSessionStatEntry 7}
--             semIsaSdvSessionStatSourceIpAddr3                                {semIsaSdvSessionStatEntry 8}
--             semIsaSdvSessionStatOutputQamPort                                {semIsaSdvSessionStatEntry 9}
--             semIsaSdvSessionStatOutputProgramNum                             {semIsaSdvSessionStatEntry 10}
--             semIsaSdvSessionStatProgramBandwidth                             {semIsaSdvSessionStatEntry 11}
--             semIsaSdvSessionStatSessionType                                  {semIsaSdvSessionStatEntry 12}
--             semIsaSdvSessionStatSessionIdWord1                               {semIsaSdvSessionStatEntry 13}
--             semIsaSdvSessionStatSessionIdWord2                               {semIsaSdvSessionStatEntry 14}
--             semIsaSdvSessionStatSessionIdWord3                               {semIsaSdvSessionStatEntry 15}
--             semIsaSdvSessionStatManagerIpAddr                                {semIsaSdvSessionStatEntry 16}
--       semIsaSdvQamStatTable                                                  {semIsaSdvStatus 3}
--          semIsaSdvQamStatEntry                                               {semIsaSdvQamStatTable 1}
--             semIsaSdvQamStatQamPortNum                                       {semIsaSdvQamStatEntry 1}
--             semIsaSdvQamStatQamEnabled                                       {semIsaSdvQamStatEntry 2}
--             semIsaSdvQamStatOutTransStreamNum                                {semIsaSdvQamStatEntry 3}
--             semIsaSdvQamStatNumSdvSessions                                   {semIsaSdvQamStatEntry 4}
--             semIsaSdvQamStatNumVodBcSessions                                 {semIsaSdvQamStatEntry 5}
--             semIsaSdvQamStatSdvGroupBandwidth                                {semIsaSdvQamStatEntry 6}
   semAlarms                                              OBJECT IDENTIFIER ::= {sem 20}
--    semAlarmHardwareFault                                                     {semAlarms 8000}
--    semAlarmInvalidInitData                                                   {semAlarms 8001}
--    semAlarmZeroSystemTime                                                    {semAlarms 8002}
--    semAlarmMissingTimeUpdate                                                 {semAlarms 8003}
--    semAlarmCommandTableEmpty                                                 {semAlarms 8004}
--    semAlarmCommandTableNearFull                                              {semAlarms 8005}
--    semAlarmServiceInError                                                    {semAlarms 8006}
--    semAlarmWaitingForExtractedMessage                                        {semAlarms 8007}
--    semAlarmLossOfPhysicalInput                                               {semAlarms 8008}
--    semAlarmServiceNotAuthorized                                              {semAlarms 8009}
--    semAlarmTemperatureFault                                                  {semAlarms 8010}
--    semAlarmFanFault                                                          {semAlarms 8011}
--    semAlarmGigeFailOver                                                      {semAlarms 8012}
--    semAlarmOtsUtilizationFault                                               {semAlarms 8013}
--    semAlarmGigeRedundantModeThreshold                                        {semAlarms 8014}
--    semAlarmSimulcryptCommunicationFault                                      {semAlarms 8015}
--    semAlarmQamFault                                                          {semAlarms 8016}
--    semAlarmUpconverterFault                                                  {semAlarms 8017}
--    semAlarmOtsHostIpOverflow                                                 {semAlarms 8018}
--    semAlarmOtsOverflow                                                       {semAlarms 8019}
--    semAlarmIceEmmServerCommFailure                                           {semAlarms 8020}
--    semAlarmIceEmmServerInvalidResponse                                       {semAlarms 8021}
--    semAlarmIceFullEncryptFailure                                             {semAlarms 8022}
--    semAlarmQamPortFault                                                      {semAlarms 8023}
--    semAlarmGbeBufferFullness                                                 {semAlarms 8024}
--    semAlarmGbeInputStreamLowBitRate                                          {semAlarms 8025}
--    semAlarmGbeMptsRedundPrimaryThreshold                                     {semAlarms 8026}
--    semAlarmGbeMptsRedundFailOver                                             {semAlarms 8027}
--    semAlarmGbeInputStreamHighBitRate                                         {semAlarms 8028}
   semEvents                                              OBJECT IDENTIFIER ::= {sem 21}
--    semEventHardwareError                                                     {semEvents 8100}
--    semEventInvalidInitDataError                                              {semEvents 8101}
--    semEventInvalidConfigDataError                                            {semEvents 8102}
--    semEventLoadDeviceError                                                   {semEvents 8103}
--    semEventPhysicalInputError                                                {semEvents 8104}
--    semEventOtsUtilizationError                                               {semEvents 8105}
--    semEventGbeBufferReset                                                    {semEvents 8106}
--    semEventEmUserLoginFailed                                                 {semEvents 8107}
--    semEventNewControllerObserved                                             {semEvents 8108}
   semErrorStatus                                         OBJECT IDENTIFIER ::= {sem 22}
--    semHwErrorTable                                                           {semErrorStatus 1}
--       semHwErrorEntry                                                        {semHwErrorTable 1}
--          semHwErrorIndex                                                     {semHwErrorEntry 1}
--          semHwErrorCode                                                      {semHwErrorEntry 2}
--          semHwErrorData                                                      {semHwErrorEntry 3}
--          semHwErrorDescription                                               {semHwErrorEntry 4}
--          semHwErrorTimeLogged                                                {semHwErrorEntry 5}
--    semInvalidInitDataTable                                                   {semErrorStatus 2}
--       semInvalidInitDataEntry                                                {semInvalidInitDataTable 1}
--          semInvalidInitDataIndex                                             {semInvalidInitDataEntry 1}
--          semInvalidInitDataMibName                                           {semInvalidInitDataEntry 2}
--          semInvalidInitDataItemNum                                           {semInvalidInitDataEntry 3}
--          semInvalidInitDataIndex1                                            {semInvalidInitDataEntry 4}
--          semInvalidInitDataIndex2                                            {semInvalidInitDataEntry 5}
--    semCommandErrorTable                                                      {semErrorStatus 3}
--       semCommandErrorEntry                                                   {semCommandErrorTable 1}
--          semCommandErrorIndex                                                {semCommandErrorEntry 1}
--          semCommandErrorTimeLogged                                           {semCommandErrorEntry 2}
--          semCommandErrorCommandSeqNum                                        {semCommandErrorEntry 3}
--          semCommandErrorCode                                                 {semCommandErrorEntry 4}
--          semCommandErrorCommandId                                            {semCommandErrorEntry 5}
--    semOutputStreamErrorTable                                                 {semErrorStatus 4}
--       semOutputStreamErrorEntry                                              {semOutputStreamErrorTable 1}
--          semOutputStreamErrorIndex                                           {semOutputStreamErrorEntry 1}
--          semOutputStreamErrorTimeLogged                                      {semOutputStreamErrorEntry 2}
--          semOutputStreamErrorAlarmCode                                       {semOutputStreamErrorEntry 3}
--          semOutputStreamErrorAlarmSeverity                                   {semOutputStreamErrorEntry 4}
--          semOutputStreamErrorOtsNum                                          {semOutputStreamErrorEntry 5}
--          semOutputStreamErrorPhysOutType                                     {semOutputStreamErrorEntry 6}
--          semOutputStreamErrorPhysOutPort                                     {semOutputStreamErrorEntry 7}
--          semOutputStreamErrorCurRate                                         {semOutputStreamErrorEntry 8}
--          semOutputStreamErrorAvgRate                                         {semOutputStreamErrorEntry 9}
--          semOutputStreamErrorMinRate                                         {semOutputStreamErrorEntry 10}
--          semOutputStreamErrorPeakRate                                        {semOutputStreamErrorEntry 11}
--          semOutputStreamErrorDescription                                     {semOutputStreamErrorEntry 12}
--    semGbeInputUdpErrorTable                                                  {semErrorStatus 5}
--       semGbeInputUdpErrorEntry                                               {semGbeInputUdpErrorTable 1}
--          semGbeInputUdpErrorIndex                                            {semGbeInputUdpErrorEntry 1}
--          semGbeInputUdpErrorTimeLogged                                       {semGbeInputUdpErrorEntry 2}
--          semGbeInputUdpErrorAlarmCode                                        {semGbeInputUdpErrorEntry 3}
--          semGbeInputUdpErrorAlarmSeverity                                    {semGbeInputUdpErrorEntry 4}
--          semGbeInputUdpErrorUdpIndex                                         {semGbeInputUdpErrorEntry 5}
--          semGbeInputUdpErrorGbePort                                          {semGbeInputUdpErrorEntry 6}
--          semGbeInputUdpErrorUdpPort                                          {semGbeInputUdpErrorEntry 7}
--          semGbeInputUdpErrorUdpPortState                                     {semGbeInputUdpErrorEntry 8}
--          semGbeInputUdpErrorRateCompareType                                  {semGbeInputUdpErrorEntry 9}
--          semGbeInputUdpErrorSamplingPeriod                                   {semGbeInputUdpErrorEntry 10}
--          semGbeInputUdpErrorCurCount                                         {semGbeInputUdpErrorEntry 11}
--          semGbeInputUdpErrorAvgCount                                         {semGbeInputUdpErrorEntry 12}
--          semGbeInputUdpErrorMinCount                                         {semGbeInputUdpErrorEntry 13}
--          semGbeInputUdpErrorPeakCount                                        {semGbeInputUdpErrorEntry 14}
--          semGbeInputUdpErrorDescription                                      {semGbeInputUdpErrorEntry 15}
   semConfigAlarms                                        OBJECT IDENTIFIER ::= {sem 23}
      semConfAlarmEnable                                  OBJECT IDENTIFIER ::= {semConfigAlarms 1}
--       semConfAlarmEnableLossOfPhysIn                                         {semConfAlarmEnable 1}
--       semConfAlarmEnableGbeInHighBitRate                                     {semConfAlarmEnable 2}
      semConfAlarmClear                                   OBJECT IDENTIFIER ::= {semConfigAlarms 2}
--       semConfAlarmClearInvalInitData                                         {semConfAlarmClear 1}
--       semConfAlarmClearGbeInStreamLowBitRate                                 {semConfAlarmClear 1}
--       semConfAlarmClearGbeMptsRedundThreshold                                {semConfAlarmClear 1}
--       semConfAlarmClearGbeMptsRedundFailOver                                 {semConfAlarmClear 1}
   semTraps                                               OBJECT IDENTIFIER ::= {sem 0}
--    not used for SEM                                                          {semTraps    1}
--    not used for SEM                                                          {semTraps    2}
--    trapConfigurationChangeInteger                                            {semTraps    3}
--    trapConfigurationChangeDisplayString                                      {semTraps    4}
--    trapConfigurationChangeOID                                                {semTraps    5}
--    trapConfigurationChangeIpAddress                                          {semTraps    6}
--    trapToBeSendQueueOverflow                                                 {semTraps    7}
--    trapConditionNotInList                                                    {semTraps   20}
--    trapConditionAlreadyInList                                                {semTraps   21}
--    trapConditionListFull                                                     {semTraps   22}
--    trapInvalidCaseInSwitch                                                   {semTraps   23}
--    trapCannotCreateSemaphore                                                 {semTraps   24}
--    trapCannotOpenSocket                                                      {semTraps   25}
--    trapUnknownMessageReceived                                                {semTraps   26}
--    trapInvalidMessageReceived                                                {semTraps   27}
--    trapHardwareFault                                                         {semTraps 8000}
--    trapInvalidInitData                                                       {semTraps 8001}
--    trapZeroSystemTime                                                        {semTraps 8002}
--    trapMissingTimeUpdate                                                     {semTraps 8003}
--    trapCommandTableEmpty                                                     {semTraps 8004}
--    trapCommandTableNearFull                                                  {semTraps 8005}
--    trapServiceInError                                                        {semTraps 8006}
--    trapWaitingForExtractedMessage                                            {semTraps 8007}
--    trapLossOfPhysicalInput                                                   {semTraps 8008}
--    trapServiceNotAuthorized                                                  {semTraps 8009}
--    trapTemperatureFault                                                      {semTraps 8010}
--    trapFanFault                                                              {semTraps 8011}
--    trapGigeFailOver                                                          {semTraps 8012}
--    trapOtsUtilizationFault                                                   {semTraps 8013}
--    trapGigeRedundantModeThreshold                                            {semTraps 8014}
--    trapSimulcryptCommunicationFault                                          {semTraps 8015}
--    trapQamFault                                                              {semTraps 8016}
--    trapUpconverterFault                                                      {semTraps 8017}
--    trapOtsHostIpOverflow                                                     {semTraps 8018}
--    trapOtsOverflow                                                           {semTraps 8019}
--    trapIceEmmServerCommFailure                                               {semTraps 8020}
--    trapIceEmmServerInvalidResponse                                           {semTraps 8021}
--    trapIceFullEncryptFailure                                                 {semTraps 8022}
--    trapQamPortFault                                                          {semTraps 8023}
--    trapGbeBufferFullness                                                     {semTraps 8024}
--    trapGbeInputStreamLowBitRate                                              {semTraps 8025}
--    trapGbeMptsRedundPrimaryThreshold                                         {semTraps 8026}
--    trapGbeMptsRedundFailOver                                                 {semTraps 8027}
--    trapGbeInputStreamHighBitRate                                             {semTraps 8028}
--    trapHardwareError                                                         {semTraps 8100}
--    trapInvalidInitDataError                                                  {semTraps 8101}
--    trapInvalidConfigDataError                                                {semTraps 8102}
--    trapLoadDeviceError                                                       {semTraps 8103}
--    trapPhysicalInputError                                                    {semTraps 8104}
--    trapOtsUtilizationError                                                   {semTraps 8105}
--    trapGbeBufferReset                                                        {semTraps 8106}
--    trapEmUserLoginFailed                                                     {semTraps 8107}
--    trapEmNewControllerObserved                                               {semTraps 8108}
   semDebug                                               OBJECT IDENTIFIER ::= {sem 5000}
-- Reserved Object Identifier.                                                  {sem 6000}


-- ------------------------------------------------------------------------------
--
-- SEM MIB
--
-- ------------------------------------------------------------------------------


-- ------------------------------------------------------------------------------
--
-- semSys
--
-- semSysConfig
--
-- semSysConfigGeneral
--

semSaveConfig OBJECT-TYPE
    SYNTAX INTEGER
        {
          saveNotInProgress     (1),
          startSaveToFlash      (2),
          savingConfigToFlash   (3)
        }
    MAX-ACCESS read-write
    STATUS current
    DESCRIPTION
        "Writing this object will commit the current
         configuration to Flash.  While a read returns the
         value savingConfigToFlash, the flash is being saved;
         the save may not have been initiated by an SNMP set.

         Once written, the change to this parameter will take immediate effect.

         @Config(config=no, reboot=no)
        "
::= { semSysConfigGeneral 1 }

semProductName OBJECT-TYPE
    SYNTAX DisplayString
    MAX-ACCESS read-write
    STATUS current
    DESCRIPTION
        "This is the Product Name of the SEM loaded at initialization from
         the config.ini file.  Specific configurations of the SEM have
         specific purposes and are identified by their product name.

         If written, a save must be performed via the semSaveConfig
         parameter and the SEM must be rebooted for the change to take effect.

         @Config(config=yes, reboot=yes)
         @Save(semSaveConfig, value=2, default=yes)
         @File(config.ini, type='ini')
        "
::= { semSysConfigGeneral 2 }

semDeviceOperatingMode OBJECT-TYPE
    SYNTAX INTEGER
        {
         cableEncryptor          (1),
         satelliteEncryptor      (2),
         manualRouting           (3),
         udpMapping              (4),
         asiDemultiplexing       (5),
         eightChannelUdpMapping  (6),
         simulcrypt1             (7),
         standardizedUdpMapping  (8),
         isaSdv                  (9)
        }
    MAX-ACCESS read-write
    STATUS current
    DESCRIPTION
        "This parameter is used to set the operating mode of the SEM.

         There are two types of operating modes based upon the source
         of Load SEM commands.  The operating mode is considered external
         if the Load SEM commands come from an external controller and
         internal if the SEM is generating the Load SEM commands.

         External modes are 'cableEncryptor', 'satelliteEncryptor', and
         'simulcrypt1'.

         Internal modes are 'manualRouting', 'udpMapping', 'asiDemultiplexing',
         'eightChannelUdpMapping', 'standardizedUdpMapping', and 'isaSdv'.

         SEM v0/v4: Cannot be 'udpMapping', 'eightChannelUdpMapping', or
         'standardizedUdpMapping'.  The SEM will default to 'manualRouting'
         if any of these modes is selected.

         SEM v12: Cannot be 'asiDemultiplexing'.  The SEM will default to
         'standardizedUdpMapping' if this mode is selected.

         NOTE:
         satelliteEncryptor mode is currently not supported.

         Once written, a save must be performed via the semSaveConfig
         parameter and the SEM must be rebooted for the change to take effect.

         @Config(config=yes, reboot=yes)
         @Save(semSaveConfig, value=2)
         @File(config.ini, type='ini')
        "
::= { semSysConfigGeneral 3 }

semCommandRetryPeriod OBJECT-TYPE
    SYNTAX Integer32
    MAX-ACCESS read-write
    STATUS current
    DESCRIPTION
        "Number of seconds SEM will retry Load SEM commands before invalidating
         them and sending a reportback.  Note that not all errors will result
         in a retry.  Some errors will result in immediate reportback and
         deletion.

         Once written, a save must be performed via the semSaveConfig
         parameter and the SEM must be rebooted for the change to take effect.

         @Range(min=0)
         @Config(config=yes, reboot=yes)
         @Save(semSaveConfig, value=2)
         @File(config.ini, type='ini')
        "
::= { semSysConfigGeneral 4 }

semInsertModeEntry OBJECT-TYPE
    SYNTAX INTEGER
        {
         efficient     (1),
         singleSection (2),
         twentyByte    (3)
        }
    MAX-ACCESS read-write
    STATUS current
    DESCRIPTION
        "This parameter is used to set the insertion mode for the SEM.
         The SEM may be configured to insert messages as efficiently as
         possible (efficient), restrict insertion to a single section starting per
         packet (singleSection), or restrict insertion to prevent any section from
         starting in the last 20 bytes of a packet (twentyByte).

         Once written, the change to this parameter will take immediate
         effect.  However, in order for the change to persist through
         subsequent reboots or power cycles, the change must be saved via
         the semSaveConfig parameter.

         @Config(config=yes, reboot=no)
         @Save(semSaveConfig, value=2)
         @File(config.ini, type='ini')
        "
::= { semSysConfigGeneral 5 }

semBootMethod OBJECT-TYPE
    SYNTAX INTEGER
        {
         noDhcpOrBootp (1),
         dhcpOnly      (2),
         bootpOnly     (3),
         dhcpAndBootp  (4)
        }
    MAX-ACCESS read-write
    STATUS current
    DESCRIPTION
        "This parameter is used to set the boot method for the SEM.
         Selection of dhcpAndBootp means that the SEM will attempt DHCP
         first, if no DHCP response, the SEM will then attempt to BOOTP.
         Selection of noDhcpOrBootp means the SEM will not use DHCP or BOOTP
         - this will result in about a 10 second savings in boot time.

         Once written, a save must be performed via the semSaveConfig
         parameter and the SEM must be rebooted for the change to take effect.

         @Config(config=yes, reboot=no)
         @Save(semSaveConfig, value=2)
         @File(config.ini, type='ini')
        "
::= { semSysConfigGeneral 6 }

semPsiDetectionEnabled OBJECT-TYPE
    SYNTAX EnableDisableTYPE
    MAX-ACCESS read-write
    STATUS current
    DESCRIPTION
        "The loss of input PSI detection enabled or disabled setting. When enabled,
         the SEM will check for missing input PSI (PATs and PMTs) based on the PSI
         detection timeout value. When an input PSI message is determined to be
         missing, the SEM will assume the input service or services are no longer
         being streamed and unmap the service(s). This checking only occurs after
         an initial PSI message has been extracted.

         Once written, the change to this parameter will take immediate effect.
         However, in order for the change to persist through subsequent reboots
         or power cycles, the change must be saved via the semSaveConfig parameter.

         @Config(config=yes, reboot=no)
         @Save(semSaveConfig, value=2)
         @File(config.ini, type='ini')
        "
::= { semSysConfigGeneral 7 }

semPsiDetectionTimeout OBJECT-TYPE
    SYNTAX Integer32
    MAX-ACCESS read-write
    STATUS current
    DESCRIPTION
        "The loss of input PSI detection timeout value. When PSI detection is enabled,
         this is the number of seconds the SEM will use to determine if an input PSI
         message is missing. Each PSI message previously extracted will be checked to
         determine that it is still being received based on this setting.

         Once written, the change to this parameter will take immediate effect.
         However, in order for the change to persist through subsequent reboots
         or power cycles, the change must be saved via the semSaveConfig parameter.

         @Range(min=0)
         @Config(config=yes, reboot=no)
         @Save(semSaveConfig, value=2)
         @File(config.ini, type='ini')
        "
::= { semSysConfigGeneral 8 }

semAutoRebootEnable OBJECT-TYPE
    SYNTAX EnableDisableTYPE
    MAX-ACCESS read-write
    STATUS current
    DESCRIPTION
        "Setting to 'enabled' allows the SEM to automatically reboot when
         specific SEM hardware errors occur.  Refer to manual for more details.

         Once written, the change to this parameter will take immediate effect.
         However, in order for the change to persist through subsequent reboots
         or power cycles, the change must be saved via the semSaveConfig parameter.

         @Config(config=yes, reboot=no)
         @Save(semSaveConfig, value=2)
         @File(config.ini, type='ini')
        "
::= { semSysConfigGeneral 9 }

-- ------------------------------------------------------------------------------
--
-- semSysConfigTime
--

semTimeSource OBJECT-TYPE
    SYNTAX INTEGER
        {
         loadSEM     (1),
         inputStream (2),
         sntp        (3),
         internal    (4)
        }
    MAX-ACCESS read-write
    STATUS current
    DESCRIPTION
        "The source for system time.  The SEM requires a
         time source in order to execute Load SEM commands.
         The time source can be configured to come from
         Load SEM Commands, be extracted from an ASI input stream,
         come from an SNTP time source, or be generated internally.

         For an Internal Operating Mode (as described in
         semDeviceOperatingMode) the Time Source can be inputStream
         (ASI), sntp, or internal.

         For an External Operating Mode (as described in
         semDeviceOperatingMode) the Time Source can be loadSEM,
         inputStream (ASI), or sntp.

         When configured to receive time from an input stream, the
         input Port must be a valid ASI input port.

         When configured as internal:
            - The SEM will internally keep time for processing
              Load SEM commands.
            - The SEM must be operating in an Internal Operating
              Mode (as described in semDeviceOperatingMode).
            - The system time and UTC offset in internal mode are
              not updated and therefore are not valid.

         When configured to receive time via SNTP the
         SntpServerSpecified object and SntpServiceIP objects
         can be used to optionally define the SNTP server.

         Once written, a save must be performed via the semSaveConfig
         parameter and the SEM must be rebooted for the change to take effect.

         @Config(config=yes, reboot=yes)
         @Save(semSaveConfig, value=2)
         @File(config.ini, type='ini')
        "
::= { semSysConfigTime 1 }

semUtcOffset OBJECT-TYPE
    SYNTAX Integer32
    MAX-ACCESS read-write
    STATUS current
    DESCRIPTION
        "The value of this object is the Universal Time
         Coordinated (UTC) offset from GPS time.  Subtract
         this from GPS time to convert from GPS to UTC.
         Units are seconds.

         When time source is SNTP, this object can be set
         to specify the UTC offset that the SEM will use
         in calculating GPS time.

         When time source is from an inputStream, the UTC
         offset is provided in the time message and cannot
         be set here.  It may be read.

         When time source is Load SEM, the UTC offset is
         provided in the Load SEM Set GPS command and cannot
         be set here.  It may be read.

         Once written, a save must be performed via the semSaveConfig
         parameter and the SEM must be rebooted for the change to take effect.

         @Config(config=yes, reboot=yes)
         @Save(semSaveConfig, value=2)
         @File(config.ini, type='ini')
        "
::= { semSysConfigTime 2 }

semTimeSourceInputPort OBJECT-TYPE
    SYNTAX Integer32
    MAX-ACCESS read-write
    STATUS current
    DESCRIPTION
        "Contains the ASI Port from which the SEM will extract a DCII System
         time message when configured for receiving time from an input stream.

         Once written, a save must be performed via the semSaveConfig
         parameter and the SEM must be rebooted for the change to take effect.

         @Range(min=1, max=8)
         @Config(config=yes, reboot=yes)
         @Save(semSaveConfig, value=2)
         @File(config.ini, type='ini')
        "
::= { semSysConfigTime  3 }

semTimeSourceSntpServerSpecified OBJECT-TYPE
    SYNTAX INTEGER
        {
         notSpecified (1),
         specified    (2)
        }
    MAX-ACCESS read-write
    STATUS current
    DESCRIPTION
        "When the TimeSource is SNTP, this object specifies whether
         the SEM will only accept time for a single SNTP server or
         from any server that broadcasts time.
         When notSpecified, the SEM will accept time from any SNTP
         server.

         When specified, the SEM will only accept time from the address
         of an SNTP server specified by the SntpServerIP address object.

         Once written, a save must be performed via the semSaveConfig
         parameter and the SEM must be rebooted for the change to take effect.

         @Config(config=yes, reboot=yes)
         @Save(semSaveConfig, value=2)
         @File(config.ini, type='ini')
        "
::= { semSysConfigTime 4 }

semTimeSourceSntpServerIP OBJECT-TYPE
    SYNTAX IpAddress
    MAX-ACCESS read-write
    STATUS current
    DESCRIPTION
        "This contains the IP address of the specified SNTP server.
         If semTimeSource is SNTP and semTimeSourceSntpServerSpecified
         is set to specified, then the sem will only accept time from
         this ip address.

         Once written, a save must be performed via the semSaveConfig
         parameter and the SEM must be rebooted for the change to take effect.

         @Config(config=yes, reboot=yes)
         @Save(semSaveConfig, value=2)
         @File(config.ini, type='ini')
        "
::= { semSysConfigTime 5 }

semUserSuppliedTime OBJECT-TYPE
    SYNTAX Integer32
    MAX-ACCESS read-write
    STATUS current
    DESCRIPTION
        "The value of this object is the GPS Time the SEM is given
         via user entry.  The time is reported in GPS seconds.  To
         determine the SEM system time in UTC the semUTCoffset object
         must also be read and used in the calculation.
         This time is ONLY used when the SEM is set to Internal time mode.

         Once written, the change to this parameter will take immediate effect.

         @Config(config=no, reboot=no)
        "
::= { semSysConfigTime 6 }


-- ------------------------------------------------------------------------------
--
-- semSysConfigController
--

semControllerIP OBJECT-TYPE
    SYNTAX IpAddress
    MAX-ACCESS read-write
    STATUS current
    DESCRIPTION
        "This contains the IP address of the local controller.  This is most often
         a DAC, but may be some other controlling device. This IP address is only
         used when the SEM is being externally controlled (i.e. Cable Encryptor mode).

         When Multi-controller mode is disabled, the SEM needs to have an IP address
         of the local controller to begin operations when externally controlled. When
         the SEM is externally controlled, this field must be set to the IP address of
         the controller or the SEM will not begin normal operation. This parameter is
         only applicable when the semMultiControllerEnable parameter is set to 'disabled'.

         Once written, the change to this parameter will take immediate
         effect.  To force the change to persist through subsequent reboots or power
         cycles, the change must be saved via the semSaveConfig parameter.

         @Config(config=yes, reboot=no)
         @Save(semSaveConfig, value=2)
         @File(config.ini, type='ini')
        "
::= { semSysConfigController 1 }

semControllerPort OBJECT-TYPE
    SYNTAX Integer32
    MAX-ACCESS read-write
    STATUS current
    DESCRIPTION
        "This contains the port of the local controller.  The SEM uses
         this port when establishing UDP communications with the controller
         for the purpose of receiving Load SEM Commands.  This field is only
         used when the SEM is externally controlled (i.e. Cable Encryptor mode).
         This parameter is only applicable when the semMultiControllerEnable
         parameter is set to 'disabled'

         Once written, the change to this parameter will take immediate
         effect.  However, in order for the change to persist through
         subsequent reboots or power cycles, the change must be saved via
         the semSaveConfig parameter.

         @Range(min=0, max=65535)
         @Config(config=yes, reboot=no)
         @Save(semSaveConfig, value=2)
         @File(config.ini, type='ini')
        "
::= { semSysConfigController 2 }

semLoadDeviceReceivePort OBJECT-TYPE
    SYNTAX Integer32
    MAX-ACCESS read-write
    STATUS current
    DESCRIPTION
        "This contains the port of the SEM.  This is the UDP port which the SEM
         uses to receive UDP messages from the local controller.  These
         messages include Load SEM Messages and Acks of reportbacks that
         the SEM has sent. This field is only used when the SEM is externally
         controlled (i.e. Cable Encryptor Mode).

         Once written, a save must be performed via the semSaveConfig
         parameter and the SEM must be rebooted for the change to take effect.

         @Range(min=0, max=65535)
         @Config(config=yes, reboot=yes)
         @Save(semSaveConfig, value=2)
         @File(config.ini, type='ini')
        "
::= { semSysConfigController 3 }

semRetryTimeout OBJECT-TYPE
    SYNTAX Integer32
    MAX-ACCESS read-write
    STATUS current
    DESCRIPTION
        "This contains the Timeout before retransmitting a Reportback.
         If the SEM does not receive an ack of the last reportback sent
         and this time has expired then the SEM attempts to resend the
         reportback. This field is only used when the SEM is externally
         controlled.  Units of seconds.

         Once written, a save must be performed via the semSaveConfig
         parameter and the SEM must be rebooted for the change to take effect.

         @Range(min=1, max=10)
         @Config(config=yes, reboot=yes)
         @Save(semSaveConfig, value=2)
         @File(config.ini, type='ini')
        "
::= { semSysConfigController 4 }

semNumRetries OBJECT-TYPE
    SYNTAX Integer32
    MAX-ACCESS read-write
    STATUS current
    DESCRIPTION
        "This contains the number of Retries before deciding that the
         connection with the external controller needs to be reestablished.
         Each time a reportback message from the SEM times outs on the ack the
         SEM increments a count of retries.  When the count reaches this value
         the SEM assumes a broken connection and attempts to reconnect. This
         field is only used when the SEM is externally controlled.

         Once written, a save must be performed via the semSaveConfig
         parameter and the SEM must be rebooted for the change to take effect.

         @Range(min=0)
         @Config(config=yes, reboot=yes)
         @Save(semSaveConfig, value=2)
         @File(config.ini, type='ini')
        "
::= { semSysConfigController 5 }

semMultiControllerEnable OBJECT-TYPE
    SYNTAX EnableDisableTYPE
    MAX-ACCESS read-write
    STATUS current
    DESCRIPTION
        "The Multi-controller enabled or disabled setting. Multi-controller support
         allows the SEM to respond to any controller that initiates communications
         with it on the appropriate UDP port. The source of a new valid LOAD SEM
         message becomes the local controller. This parameter is only applicable
         when the SEM is in an external control mode (i.e. Cable Encryptor).

         Once written, the change to this parameter will take immediate effect.
         However, in order for the change to persist through subsequent reboots
         or power cycles, the change must be saved via the semSaveConfig parameter.

         @Config(config=yes, reboot=no)
         @Save(semSaveConfig, value=2)
         @File(config.ini, type='ini')
        "
::= { semSysConfigController 6 }


-- ------------------------------------------------------------------------------
--
-- semSysConfigPidRemapping
--

semPidRemappingEnabled OBJECT-TYPE
    SYNTAX EnableDisableTYPE
    MAX-ACCESS read-write
    STATUS obsolete
    DESCRIPTION
        "The PID Remapping enabled or disabled setting. When enabled, the SEM will determine
         the output PIDs from a predetermined range of PIDs for services and ancillary
         PIDs. In addition, when PID remapping is enabled, the SEM is able to perform
         PID mask encryption (allows for encrypting large numbers of PIDs using fewer ACP
         resources).When set to disabled, the output PIDs for all services and ancillary
         PIDs are the same as the input PID values. In addition, PID mask encryption cannot
         be performed when PID Remapping is disabled.
         Once written, a save must be performed via the semSaveConfig
         parameter and the SEM must be rebooted for the change to take effect.

         This object is obsolete.
        "
::= { semSysConfigPidRemapping  1 }

semPidsPerService OBJECT-TYPE
    SYNTAX Integer32
    MAX-ACCESS read-write
    STATUS obsolete
    DESCRIPTION
        "The PID Remapping parameters are used at initialization to
         deterministically partition the range of output elementary PIDs
         that the SEM uses when remapping PIDs.  The available elementary
         PID range is broken up into services with an equal distribution
         of available PIDs as defined by these parameters.
         Specifically, the PIDs per Service parameter specifies how many
         PIDs are to be allocated for each service.  The elementary PID
         range consists of 4096 available PIDs.  Currently, this parameter
         may be set to values of 64, 32, and 16.  For multiplexes with many
         services with fewer PIDs per service the value 16 will allow up to
         252 services to be multiplexed.  For multiplexes with fewer services
         that contain many elementary PIDs per service, the value of 64 will
         allow 64 services to be multiplexed each with up to 64 components.
         The value 32 allows a 128 multiplexed services with
         up to 32 components per service.
         Once written, a save must be performed via the semSaveConfig
         parameter and the SEM must be rebooted for the change to take effect.

         This object is obsolete.
        "
::= { semSysConfigPidRemapping  2 }

semPidMaskingEnabled OBJECT-TYPE
    SYNTAX EnableDisableTYPE
    MAX-ACCESS read-write
    STATUS obsolete
    DESCRIPTION
        "This parameter is used to enable or disable PID Mask Encryption (1 = disabled, 2 = enabled).
         This parameter is only applicable when the SEM is configured with an ACP module and is externally
         controlled (i.e. Cable Encryptor Mode). When PID Mask Encryption is enabled, the SEM is able to
         encrypt large amounts of PIDs by using each MCSODA PID register to encrypt 16 PIDs. When disabled,
         each MCSODA PID register can only encrypt one PID and therefore the number of PIDs that can be
         encrypted is drastically reduced. The total number of PIDs that can be encrypted is based on the
         number of PID registers of the MCSODA. To enable PID Mask encryption, PID Remapping must be enabled
         (the SEM must be able to specify the output PID values for each service).
         Once written, a save must be performed via the semSaveConfig
         parameter and the SEM must be rebooted for the change to take effect.

         This object is obsolete.
        "
::= { semSysConfigPidRemapping  3 }


-- ------------------------------------------------------------------------------
--
-- semSysConfigElementManagerLogin - obsolete
--

semUserName OBJECT-TYPE
    SYNTAX OCTET STRING (SIZE(0..32))
    MAX-ACCESS read-write
    STATUS obsolete
    DESCRIPTION
        "This object is obsolete.
        "
::= { semSysConfigElementManagerLogin 1 }

semUserPassword OBJECT-TYPE
    SYNTAX OCTET STRING (SIZE(0..32))
    MAX-ACCESS read-write
    STATUS obsolete
    DESCRIPTION
        "This object is obsolete.
        "
::= { semSysConfigElementManagerLogin 2 }


-- ------------------------------------------------------------------------------
--
-- semSysStatus
--
-- semSysStatusGeneral
--

semSystemTime OBJECT-TYPE
    SYNTAX Integer32
    MAX-ACCESS read-only
    STATUS current
    DESCRIPTION
        "The value of this object is the System Time the SEM
         is using for commands and encryption purposes.  The time is the SEMs
         internal time.  The SEM maintains GPS system time that it uses
         to start and stop Load SEM Commands.  The system time is initialized
         when the SEM gets its first time update from the designated
         semTimeSource.  The system time is then compared to each time
         update from the time source and corrections are made to keep the
         system time consistent with the Time Source.
         The system time is reported in GPS seconds.  To determine the
         SEMs system time in UTC the semUTCoffset object must also
         be read and used in the calculation.
         The system time is not used when the SEM is set to Internal time mode."
::= { semSysStatusGeneral 1 }

semHostProcessorBootCodeVersion OBJECT-TYPE
    SYNTAX DisplayString
    MAX-ACCESS read-only
    STATUS current
    DESCRIPTION
        "SEM Host Processor Boot Code Version."
::= { semSysStatusGeneral 2 }

semMuxFpgaVersion OBJECT-TYPE
    SYNTAX DisplayString
    MAX-ACCESS read-only
    STATUS current
    DESCRIPTION
        "SEM MUX FPGA Version."
::= { semSysStatusGeneral 3 }

semMainBoardVersion OBJECT-TYPE
    SYNTAX DisplayString
    MAX-ACCESS read-only
    STATUS current
    DESCRIPTION
        "SEM Main Board Version.  This is the revision of the
         semMainBoardType."
::= { semSysStatusGeneral 4 }

semHostApplicationDate OBJECT-TYPE
    SYNTAX DisplayString
    MAX-ACCESS read-only
    STATUS current
    DESCRIPTION
        "SEM Host Processor Application Creation Date."
::= { semSysStatusGeneral 5 }

semProductType OBJECT-TYPE
    SYNTAX INTEGER
        {
         invalid         (1),
         sem1000         (2),
         v8              (3),
         v4              (4),
         v0              (5),
         v12             (6)
        }
    MAX-ACCESS read-only
    STATUS current
    DESCRIPTION
        "SEM Product Type.  The corresponding product name
         text setting can be found in identUnitModel."
::= { semSysStatusGeneral 6 }

semMainBoardType OBJECT-TYPE
    SYNTAX INTEGER
        {
         type1           (1),
         type2           (2)
        }
    MAX-ACCESS read-only
    STATUS current
    DESCRIPTION
        "SEM Main Board Type.  SEM1000, v8, v4, and v0 use
         'type1'.  SEM v12 uses 'type2'.  The revision
         is found in semMainBoardVersion."
::= { semSysStatusGeneral 7 }

semOperationalTime OBJECT-TYPE
    SYNTAX Integer32
    MAX-ACCESS read-only
    STATUS current
    DESCRIPTION
        "The Operational Time is the time in seconds since the SEM completed
         the boot sequence.  It is the time that the SEM has been operational."
::= { semSysStatusGeneral 8 }

semBootReason OBJECT-TYPE
    SYNTAX INTEGER
        {
         powerCycle       (0),
         operatorReboot   (1),
         acpFpgaReprogram (2),
         hwFault          (3)
        }
    MAX-ACCESS read-only
    STATUS current
    DESCRIPTION
        "Indicates reason for SEM boot:
            'powerCycle'       - Power-up or power cycled.
            'operatorReboot'   - Operator commanded reboot (refer to manual).
            'acpFpgaReprogram' - ACP FPGA Reprogramming (refer to manual).
            'hwFault'          - Automatic reboot occurred as per semAutoRebootEnable.
        "
::= { semSysStatusGeneral 9 }

semCurrentDeviceOperatingMode OBJECT-TYPE
    SYNTAX INTEGER
        {
         cableEncryptor          (1),
         satelliteEncryptor      (2),
         manualRouting           (3),
         udpMapping              (4),
         asiDemultiplexing       (5),
         eightChannelUdpMapping  (6),
         simulcrypt1             (7),
         standardizedUdpMapping  (8),
         isaSdv                  (9)
        }
    MAX-ACCESS read-only
    STATUS current
    DESCRIPTION
        "This parameter indicates the current operating mode of the SEM.

         This may be different from semDeviceOperatingMode if the SEM
         was not rebooted after semDeviceOperatingMode was changed.
        "
::= { semSysStatusGeneral 10 }


-- ------------------------------------------------------------------------------
--
-- semSysStatusEnvironment
--

semTemperatureCenter OBJECT-TYPE
    SYNTAX Integer32
    MAX-ACCESS read-only
    STATUS current
    DESCRIPTION
        "Ambient temperature at the center temperature sensor
         in whole number degrees Celsius."
::= { semSysStatusEnvironment 1 }

semTemperatureRight OBJECT-TYPE
    SYNTAX Integer32
    MAX-ACCESS read-only
    STATUS current
    DESCRIPTION
        "Ambient temperature at the right temperature sensor
         in whole number degrees Celsius.
         Right is as viewed from the front of the SEM unit."
::= { semSysStatusEnvironment 2 }

semFanSpeedLeft OBJECT-TYPE
    SYNTAX Integer32
    MAX-ACCESS read-only
    STATUS current
    DESCRIPTION
        "Fan speed in revolutions per minute of the left fan.
         Due to the nature of the fan speed sensor, the fan
         reading is rounded down to nearest 400 rpm.
         Left is as viewed from the front of the SEM unit."
::= { semSysStatusEnvironment 3 }

semFanSpeedCenter OBJECT-TYPE
    SYNTAX Integer32
    MAX-ACCESS read-only
    STATUS current
    DESCRIPTION
        "Fan speed in revolutions per minute of the center fan.
         Due to the nature of the fan speed sensor, the fan
         reading is rounded down to nearest 400 rpm."
::= { semSysStatusEnvironment 4 }

semFanSpeedRight OBJECT-TYPE
    SYNTAX Integer32
    MAX-ACCESS read-only
    STATUS current
    DESCRIPTION
        "Fan speed in revolutions per minute of the right fan.
         Due to the nature of the fan speed sensor, the fan
         reading is rounded down to nearest 400 rpm.
         Right is as viewed from the front of the SEM unit."
::= { semSysStatusEnvironment 5 }

semFanSpeedRightCenter OBJECT-TYPE
    SYNTAX Integer32
    MAX-ACCESS read-only
    STATUS current
    DESCRIPTION
        "Fan speed in revolutions per minute of the right center
         fan.  Due to the nature of the fan speed sensor, the fan
         reading is rounded down to nearest 400 rpm.
         Right is as viewed from the front of the SEM unit.
         Currently only used for SEM v12."
::= { semSysStatusEnvironment 6 }

semFanSpeedLeftCenter OBJECT-TYPE
    SYNTAX Integer32
    MAX-ACCESS read-only
    STATUS current
    DESCRIPTION
        "Fan speed in revolutions per minute of the left center
         fan.  Due to the nature of the fan speed sensor, the fan
         reading is rounded down to nearest 400 rpm.
         Left is as viewed from the front of the SEM unit.
         Currently only used for SEM v12."
::= { semSysStatusEnvironment 7 }


-- ------------------------------------------------------------------------------
--
-- semSysStatusCommands
--
-- semCommandsGeneral
--

semCommandsActive OBJECT-TYPE
    SYNTAX Integer32
    MAX-ACCESS read-only
    STATUS current
    DESCRIPTION
        "The value of this object is number of LOAD SEM
         commands currently active.  A Load SEM command is
         considered to be active if it is past its start time
         but has not yet reached its stop time.
         This field is only applicable when the SEM is externally Controlled"
::= { semCommandsGeneral 1 }

semCommandsWaiting OBJECT-TYPE
    SYNTAX Integer32
    MAX-ACCESS read-only
    STATUS current
    DESCRIPTION
        "The value of this object is number of LOAD SEM
         commands currently waiting to execute.  Commands
         counted here have not yet reached their start time.
         This field is only applicable when the SEM is externally Controlled"
::= { semCommandsGeneral 2 }

semExtractCommandsWaiting OBJECT-TYPE
    SYNTAX Integer32
    MAX-ACCESS read-only
    STATUS current
    DESCRIPTION
        "The value of this object is number of LOAD SEM
         commands that are waiting for extracted messages.
         This field is only applicable when the SEM is externally Controlled"
::= { semCommandsGeneral 3 }

semBlocksAvailable OBJECT-TYPE
    SYNTAX Integer32
    MAX-ACCESS read-only
    STATUS current
    DESCRIPTION
        "The value of this object is amount of free memory
         blocks available for Load SEM commands.  Each block
         contains 64 bytes of storage space.
         This field is only applicable when the SEM is externally Controlled"
::= { semCommandsGeneral 4 }

semBlocksTotal OBJECT-TYPE
    SYNTAX Integer32
    MAX-ACCESS read-only
    STATUS current
    DESCRIPTION
        "The value of this object is the total amount of
         memory blocks available for Load SEM Commands.
         This field is only applicable when the SEM is externally Controlled"
::= { semCommandsGeneral 5 }


-- ------------------------------------------------------------------------------
--
-- semLoadSemTable
--

semLoadSemTable OBJECT-TYPE
    SYNTAX SEQUENCE OF SemLoadSemEntry
    MAX-ACCESS not-accessible
    STATUS current
    DESCRIPTION
        "A table of LOAD SEM Command status information.
         This table contains status information on every command
         currently stored within the SEM.  The table is ordered in
         such a way as the dependencies of Load SEM Commands can be
         extracted and a tree of commands can be created.  Commands
         that are not dependent upon other commands have a level of
         0.  Commands that are at the top of a dependency tree have
         a level of 1.  The structure of the rest of the dependency tree
         can be determined by the order of the entries to the table. The
         entries are ordered as if doing a depth first decent of
         the tree with the depth of each command indicated by its level.
         Therefore, if a command has a level other than 0 or 1 then
         the first previous command that has a level 1 less than it
         is the command to which it is dependent.
         Example:
         This partial table

           Index  Level ... sequenceNumber ...
            1        0             1
            2        1             2
            3        2             3
            4        3             4
            5        2             5
            6        1             6
            7        2             7

         translates to these trees of sequence numbers
                2           6
               / \          |
              3   5         7
            /
           4

         with sequence number 1 existing on its own not part of a tree.
        "
::= { semSysStatusCommands 2 }

semLoadSemEntry OBJECT-TYPE
    SYNTAX SemLoadSemEntry
    MAX-ACCESS not-accessible
    STATUS current
    DESCRIPTION
        "Load SEM Table Entry."
    INDEX { semLoadSemIndex }
::= { semLoadSemTable 1 }

SemLoadSemEntry ::= SEQUENCE
    {
     semLoadSemIndex                Integer32,
     semLoadSemLevel                Integer32,
     semLoadSemState                INTEGER,
     semLoadSemSubState             INTEGER,
     semLoadSemSequenceNumber       Integer32,
     semLoadSemSubcommandId         Integer32,
     semLoadSemSubcommandErrorCode  Integer32,
     semLoadSemSubcommandRetryCount Integer32,
     semLoadSemCommandBlock1        OCTET STRING
    }

semLoadSemIndex OBJECT-TYPE
    SYNTAX Integer32
    MAX-ACCESS not-accessible
    STATUS current
    DESCRIPTION
        "The index of the Load SEM"
::= { semLoadSemEntry 1 }

semLoadSemLevel OBJECT-TYPE
    SYNTAX Integer32
    MAX-ACCESS read-only
    STATUS current
    DESCRIPTION
        "The level of the command in the tree of load SEM
         commands."
::= { semLoadSemEntry 2 }

semLoadSemState OBJECT-TYPE
    SYNTAX INTEGER
        {
         waitingForStart (1),
         executing       (2),
         waitingForStop  (3),
         deleting        (4),
         error           (5)
        }
    MAX-ACCESS read-only
    STATUS current
    DESCRIPTION
        "The current state of the Command.  "
::= { semLoadSemEntry 3 }

semLoadSemSubState OBJECT-TYPE
    SYNTAX INTEGER
        {
         none                      (1),
         deletingDependants        (2),
         waitingForDependantDelete (3),
         waitingForAck             (4),
         waitingForResponse        (5),
         suspended                 (6),
         waitingForExtractAck      (7),
         waitingForExtractData     (8),
         waitingForValidInputPsi   (9),
         reserved10                (10),
         rebooting                 (11),
         deletingInactive          (12),
         deletingActive            (13),
         deletingSuspended         (14),
         deletedAll                (15),
         deletingOne               (16)
        }
    MAX-ACCESS read-only
    STATUS current
    DESCRIPTION
        "The current substate of the command.
         Command specific"
::= { semLoadSemEntry 4 }

semLoadSemSequenceNumber OBJECT-TYPE
    SYNTAX Integer32
    MAX-ACCESS read-only
    STATUS current
    DESCRIPTION
        "The sequence number from the LOAD SEM Message"
::= { semLoadSemEntry 5 }

semLoadSemSubcommandId OBJECT-TYPE
    SYNTAX Integer32 (1..4)
    MAX-ACCESS read-only
    STATUS current
    DESCRIPTION
        "The subcommand id from the load SEM Message"
::= { semLoadSemEntry 6 }

semLoadSemSubcommandErrorCode OBJECT-TYPE
    SYNTAX Integer32
    MAX-ACCESS read-only
    STATUS current
    DESCRIPTION
        "The error code for the error causing retry of the load SEM Message"
::= { semLoadSemEntry 7 }

semLoadSemSubcommandRetryCount OBJECT-TYPE
    SYNTAX Integer32
    MAX-ACCESS read-only
    STATUS current
    DESCRIPTION
        "The number of retries of the load SEM Message"
::= { semLoadSemEntry 8 }

semLoadSemCommandBlock1 OBJECT-TYPE
    SYNTAX OCTET STRING
    MAX-ACCESS read-only
    STATUS current
    DESCRIPTION
        "This object contains the text of block 1 (up to 255 bytes)
         of a LOAD SEM command.  Additional blocks are not currently
         accessible. "
::= { semLoadSemEntry 9 }


-- ------------------------------------------------------------------------------
--
-- semInsertQueTable
--

semInsertQueTable OBJECT-TYPE
    SYNTAX SEQUENCE OF SemInsertQueEntry
    MAX-ACCESS not-accessible
    STATUS current
    DESCRIPTION
        "A table of Insertion Queue subqueue information. This table
         shows what messages the SEM is currently inserting for each
         output.  The message type, sequence number, pid,
         program number, start time, and stop time are shown. This table
         is indexed by output id, and subqueue id. For each
         index the message type and sequence number are provided."
::= { semSysStatusCommands 3 }

semInsertQueEntry OBJECT-TYPE
    SYNTAX SemInsertQueEntry
    MAX-ACCESS not-accessible
    STATUS current
    DESCRIPTION
        "Insertion Queue Table Entry."
    INDEX { semInsertQueSubqueueOutputId,semInsertQueSubqueueIndex,semInsertQueSubqueueSlotNumber }
::= { semInsertQueTable 1 }

SemInsertQueEntry ::= SEQUENCE
    {
     semInsertQueSubqueueOutputId         Integer32,
     semInsertQueSubqueueIndex            Integer32,
     semInsertQueMessageType              Integer32,
     semInsertQueInsLoadSemSeqNum         Integer32,
     semInsertQuePid                      Integer32,
     semInsertQueProgramNumber            Integer32,
     semInsertQueStartTime                Integer32,
     semInsertQueStopTime                 Integer32,
     semInsertQueFirstTimeInserted        Integer32,
     semInsertQueSubqueueSlotNumber       Integer32
    }

semInsertQueSubqueueOutputId OBJECT-TYPE
    SYNTAX Integer32
    MAX-ACCESS not-accessible
    STATUS current
    DESCRIPTION
        "The output id index.  "
::= { semInsertQueEntry 1 }

semInsertQueSubqueueIndex OBJECT-TYPE
    SYNTAX Integer32
    MAX-ACCESS not-accessible
    STATUS current
    DESCRIPTION
        "The Index of the Subqueue"
::= { semInsertQueEntry 2 }

semInsertQueMessageType OBJECT-TYPE
    SYNTAX Integer32 (0..255)
    MAX-ACCESS read-only
    STATUS current
    DESCRIPTION
        "The message type of the message being inserted"
::= { semInsertQueEntry 3 }

semInsertQueInsLoadSemSeqNum OBJECT-TYPE
    SYNTAX Integer32
    MAX-ACCESS read-only
    STATUS current
    DESCRIPTION
        "The LOAD SEM sequence number of the command
         responsible for the insert"
::= { semInsertQueEntry 4 }

semInsertQuePid OBJECT-TYPE
    SYNTAX Integer32 (0..8191)
    MAX-ACCESS read-only
    STATUS current
    DESCRIPTION
        "The PID of the message being inserted"
::= { semInsertQueEntry 5 }

semInsertQueProgramNumber OBJECT-TYPE
    SYNTAX Integer32 (0..65535)
    MAX-ACCESS read-only
    STATUS current
    DESCRIPTION
        "The Program Number of the message being inserted. Program
         number is 0 for all non-Program related messages (messages
         that are inserted on Ancillary Subqueues)."
::= { semInsertQueEntry 6 }

semInsertQueStartTime OBJECT-TYPE
    SYNTAX Integer32
    MAX-ACCESS read-only
    STATUS current
    DESCRIPTION
        "The Start Time of the message. This is the time that the
         message is inserted into the Output transport stream."
::= { semInsertQueEntry 7 }

semInsertQueStopTime OBJECT-TYPE
    SYNTAX Integer32
    MAX-ACCESS read-only
    STATUS current
    DESCRIPTION
        "The Stop Time of the message. This is the time that the
         message is removed from the Output transport stream."
::= { semInsertQueEntry 8 }

semInsertQueFirstTimeInserted OBJECT-TYPE
    SYNTAX Integer32
    MAX-ACCESS read-only
    STATUS current
    DESCRIPTION
        "The time the message is first inserted."
::= { semInsertQueEntry 9 }

semInsertQueSubqueueSlotNumber OBJECT-TYPE
    SYNTAX Integer32
    MAX-ACCESS not-accessible
    STATUS current
    DESCRIPTION
        "The slot number of the Subqueue.  This index is one
         greater than the actual slot number.  Subtract one when
         displaying."
::= { semInsertQueEntry 10 }


-- ------------------------------------------------------------------------------
--
-- semOutputProgramTables
--

semOutputProgramTable OBJECT-TYPE
    SYNTAX SEQUENCE OF SemOutputProgramEntry
    MAX-ACCESS not-accessible
    STATUS current
    DESCRIPTION
        "This table shows what programs on what inputs are being
         remapped to what programs on what outputs."
::= { semSysStatusCommands 5 }

semOutputProgramEntry OBJECT-TYPE
    SYNTAX SemOutputProgramEntry
    MAX-ACCESS not-accessible
    STATUS current
    DESCRIPTION
        "Output Program Table Entry."
    INDEX { semOutputProgramOutputId, semOutputProgramOutputProgNum }
::= { semOutputProgramTable 1 }

SemOutputProgramEntry ::= SEQUENCE
    {
     semOutputProgramOutputId            Integer32,
     semOutputProgramOutputProgNum       Integer32,
     semOutputProgramInputId             Integer32,
     semOutputProgramInputProgNum        Integer32,
     semOutputProgramState               INTEGER,
     semOutputProgramDsSeqNum            Integer32,
     semOutputProgramRcvUdpPort          Integer32,
     semOutputProgramAcpIndex            Integer32,
     semOutputProgramServiceIndex        Integer32,
     semOutputProgramPsipState           INTEGER,
     semOutputProgramSimScsProgramIndex  Integer32,
     semOutputProgramInputPreEncrypted   INTEGER,
     semOutputProgramInputPort           Integer32
    }

semOutputProgramOutputId OBJECT-TYPE
    SYNTAX Integer32
    MAX-ACCESS not-accessible
    STATUS current
    DESCRIPTION
        "Logical Output ID of output program "
::= { semOutputProgramEntry 1 }

semOutputProgramOutputProgNum OBJECT-TYPE
    SYNTAX Integer32
    MAX-ACCESS not-accessible
    STATUS current
    DESCRIPTION
        "Output MPEG Program Number "
::= { semOutputProgramEntry 2 }

semOutputProgramInputId OBJECT-TYPE
    SYNTAX Integer32
    MAX-ACCESS read-only
    STATUS current
    DESCRIPTION
        "Logical Input ID of input program assigned  "
::= { semOutputProgramEntry 3 }

semOutputProgramInputProgNum OBJECT-TYPE
    SYNTAX Integer32
    MAX-ACCESS read-only
    STATUS current
    DESCRIPTION
        "Input MPEG Program Number "
::= { semOutputProgramEntry 4 }

semOutputProgramState OBJECT-TYPE
    SYNTAX INTEGER
        {
         outputProgramUndefined      (1),
         outputProgramDefined        (2),
         programMappingDefined       (3),
         waitingForInitialInputPAT   (4),
         waitingForPATnoPMTfound     (5),
         waitingForInputPMT          (6),
         errorInputPIDsAlreadyMapped (7),
         errorMaxComponentsExceeded  (8),
         errorInvalidPCRPIDinPMT     (9),
         startingProgramPassThrough  (10),
         startingProgramRemapping    (11),
         startingProgramRemuxing     (12),
         passingthrroughInputProgram (13),
         remappingProgram            (14),
         remultiplexingProgram       (15),
         stoppingProgramPassThrough  (16),
         stoppingProgramRemapping    (17),
         stoppingProgramRemuxing     (18)
        }
    MAX-ACCESS read-only
    STATUS current
    DESCRIPTION
        "Current Program State "
::= { semOutputProgramEntry 5 }

semOutputProgramDsSeqNum OBJECT-TYPE
    SYNTAX Integer32
    MAX-ACCESS read-only
    STATUS current
    DESCRIPTION
        "Load SEM Define Program command sequence number "
::= { semOutputProgramEntry 6 }

semOutputProgramRcvUdpPort OBJECT-TYPE
    SYNTAX Integer32
    MAX-ACCESS read-only
    STATUS current
    DESCRIPTION
        "Input receive UDP Port (0 for non-GbE Inputs) "
::= { semOutputProgramEntry 7 }

semOutputProgramAcpIndex OBJECT-TYPE
    SYNTAX Integer32
    MAX-ACCESS read-only
    STATUS current
    DESCRIPTION
        "This column serves as a foreign key into the acpStatusTable
         defined in the acp.mib. The acpStatusLog table is a triple
         indexed table containing encryption status info. See acp.mib
         for details. The value is 1 based and corresponds to the
         absolute acp index used to encrypt this output program number.
         If the service is in the clear a zero is returned."
::= { semOutputProgramEntry 8 }

semOutputProgramServiceIndex OBJECT-TYPE
    SYNTAX Integer32
    MAX-ACCESS read-only
    STATUS current
    DESCRIPTION
        "This column serves as a foreign key into the acpStatusTable
         defined in the acp.mib. The acpStatusLog table is a triple
         indexed table containing encryption status info. See acp.mib
         for details. The value is 1 based and corresponds to the service
         index on the encrypting acp. For a MC1.7 it would be 1 or 2.
         If the service is in the clear a zero is returned."
::= { semOutputProgramEntry 9 }

semOutputProgramPsipState OBJECT-TYPE
    SYNTAX INTEGER
        {
         notApplicable               (1),
         incompleteWaitingForMGT     (2),
         incompleteWaitingForVCT     (3),
         incompleteWaitingForEIT     (4),
         psipFixingComplete          (5),
         errorEITPIDsAlreadyMapped   (6)
        }
    MAX-ACCESS read-only
    STATUS current
    DESCRIPTION
        "Current PSIP State "
::= { semOutputProgramEntry 10 }

semOutputProgramSimScsProgramIndex OBJECT-TYPE
    SYNTAX Integer32
    MAX-ACCESS read-only
    STATUS current
    DESCRIPTION
        "This column serves as a foreign key into the bcsSimScsProgramTable
         defined in the bcs_simscs.mib. The bcsSimScsProgramTable table is
         a double indexed table containing Simulcrypt encryption status
         information relating to this program. See bcs_simscs.mib for
         details."
::= { semOutputProgramEntry 11 }

semOutputProgramInputPreEncrypted OBJECT-TYPE
    SYNTAX INTEGER
        {
         clear         (1),
         preEncrypted  (2)
        }
    MAX-ACCESS read-only
    STATUS current
    DESCRIPTION
        "Indicates whether the program was pre-encrypted.
         Pre-encryption status is determined by the presence or
         absence of a GI CA ECM descriptor within the input PMT."
::= { semOutputProgramEntry 12 }

semOutputProgramInputPort OBJECT-TYPE
    SYNTAX Integer32
    MAX-ACCESS read-only
    STATUS current
    DESCRIPTION
        "Physical Input port number of the input program being mapped."
::= { semOutputProgramEntry 13 }

-- ------------------------------------------------------------------------------
--
-- semSysStatusMultiController
--
-- semMultiControllerHistoryTable
--

semMultiControllerHistoryTable OBJECT-TYPE
    SYNTAX SEQUENCE OF SemMultiControllerHistoryEntry
    MAX-ACCESS not-accessible
    STATUS current
    DESCRIPTION
        "A table containing the GPS time, IP address, and UDP port of the last
         48 multi-controller-mode local controllers.  This table is sorted in
         reverse chronological order.  Thus, the most recent local
         controller is located at the top (first entry) of the table."
::= { semSysStatusMultiController 1 }

semMultiControllerHistoryEntry OBJECT-TYPE
    SYNTAX SemMultiControllerHistoryEntry
    MAX-ACCESS not-accessible
    STATUS current
    DESCRIPTION
        "Multi-Controller Table Entry."
    INDEX { semMultiControllerHistoryIndex }
::= { semMultiControllerHistoryTable 1 }

SemMultiControllerHistoryEntry ::= SEQUENCE
    {
     semMultiControllerHistoryIndex   Integer32,
     semMultiControllerHistoryTime    Integer32,
     semMultiControllerHistoryIPaddr  IpAddress,
     semMultiControllerHistoryIPport  Integer32
    }

semMultiControllerHistoryIndex OBJECT-TYPE
    SYNTAX Integer32
    MAX-ACCESS not-accessible
    STATUS current
    DESCRIPTION
        "The index of the entry."
::= { semMultiControllerHistoryEntry 1 }

semMultiControllerHistoryTime OBJECT-TYPE
    SYNTAX Integer32
    MAX-ACCESS read-only
    STATUS current
    DESCRIPTION
        "The GPS time during which this entry
         became the local controller."
::= { semMultiControllerHistoryEntry 2 }

semMultiControllerHistoryIPaddr OBJECT-TYPE
    SYNTAX IpAddress
    MAX-ACCESS read-only
    STATUS current
    DESCRIPTION
        "The IP address of the local controller."
::= { semMultiControllerHistoryEntry 3 }

semMultiControllerHistoryIPport OBJECT-TYPE
    SYNTAX Integer32
    MAX-ACCESS read-only
    STATUS current
    DESCRIPTION
        "The UDP port of the local controller."
::= { semMultiControllerHistoryEntry 4 }


-- ------------------------------------------------------------------------------
--
-- semAsi
--
-- semAsiConfig
--
-- semAsiConfigTable
--

semAsiConfigTable OBJECT-TYPE
    SYNTAX SEQUENCE OF SemAsiConfigEntry
    MAX-ACCESS not-accessible
    STATUS current
    DESCRIPTION
        "This is a table of configuration parameters for the eight ASI ports.
         Ports one through four (1-4) can be configured for input only.
         Ports five through eight (5-8) can be configured for input or output.

         @Config(config=yes, reboot=yes)
         @Save(semSaveConfig, value=2)
         @File(config.ini, type='ini')
        "
::= { semAsiConfig 1 }

semAsiConfigEntry OBJECT-TYPE
    SYNTAX SemAsiConfigEntry
    MAX-ACCESS not-accessible
    STATUS current
    DESCRIPTION
        "ASI Interface Configuration Table Entry."
    INDEX { semAsiConfigPortNum }
::= { semAsiConfigTable 1 }

SemAsiConfigEntry ::= SEQUENCE
    {
     semAsiConfigPortNum           Integer32,
     semAsiConfigEnable            INTEGER,
     semAsiConfigOutPacketSize     INTEGER
    }

semAsiConfigPortNum OBJECT-TYPE
    SYNTAX Integer32(1..8)
    MAX-ACCESS not-accessible
    STATUS current
    DESCRIPTION
        "ASI Port Number."
::= { semAsiConfigEntry 1 }

semAsiConfigEnable OBJECT-TYPE
    SYNTAX INTEGER
        {
         disabled      (1),
         enabledInput  (2),
         enabledOutput (3)
        }
    MAX-ACCESS read-write
    STATUS current
    DESCRIPTION
        "This parameter enables the ASI port.
         Ports one through four (1-4) can be configured for input only.
         Ports five through eight (5-8) can be configured for input or output.

         Once written, a save must be performed via the semSaveConfig
         parameter and the SEM must be rebooted for the change to take effect.
        "
::= { semAsiConfigEntry 2 }

semAsiConfigOutPacketSize OBJECT-TYPE
    SYNTAX INTEGER
        {
          byte188 (1),
          byte204 (2)
        }
    MAX-ACCESS read-write
    STATUS current
    DESCRIPTION
        "Not currently supported.

         @Config(config=no, reboot=no)
        "
--        "This parameter configures ASI Output Packet size.  In 204 byte mode
--         the SEM will output the 188 byte MPEG packet followed by 16 null bytes.
--         Ports five through eight (5-8) can be configured for packet size.
--         This parameter is ignored for ports configured as input or disabled.
--
--         Once written, a save must be performed via the semSaveConfig
--         parameter and the SEM must be rebooted for the change to take effect.
--        "
::= { semAsiConfigEntry 3 }


-- ------------------------------------------------------------------------------
--
-- semAsiMonitorPortConfig
--

semAsiMonitorPortOutTransStreamNum OBJECT-TYPE
    SYNTAX Integer32 (0..16)
    MAX-ACCESS read-write
    STATUS current
    DESCRIPTION
        "The number of the output transport stream to route to the
         ASI Monitor Port.  Zero indicates that no stream is to be
         routed to the ASI Monitor port.

         Once written, the change to this parameter will take immediate
         effect.  However, in order for the change to persist through
         subsequent reboots or power cycles, the change must be saved via
         the semSaveConfig parameter.

         @Config(config=yes, reboot=no)
         @Save(semSaveConfig, value=2)
         @File(config.ini, type='ini')
        "
::= { semAsiMonitorPortConfig 1 }

semAsiMonitorPortOutPacketSize OBJECT-TYPE
    SYNTAX INTEGER
        {
          byte188 (1),
          byte204 (2)
        }
    MAX-ACCESS read-write
    STATUS current
    DESCRIPTION
        "Not currently supported.

         @Config(config=no, reboot=no)
        "
--        "This parameter configures ASI Monitor Port Output Packet size.
--         In 204 byte mode the SEM will output the 188 byte MPEG packet
--         followed by 16 null bytes.
--
--         Once written, the change to this parameter will take immediate
--         effect.  However, in order for the change to persist through
--         subsequent reboots or power cycles, the change must be saved via
--         the semSaveConfig parameter.
--
--         @Config(config=yes, reboot=no)
--         @Save(semSaveConfig, value=2)
--         @File(config.ini, type='ini')
--        "
::= { semAsiMonitorPortConfig 2 }

semAsiMonitorPortEncryption OBJECT-TYPE
    SYNTAX INTEGER
        {
          preEncryption  (1),
          postEncryption (2)
        }
    MAX-ACCESS read-write
    STATUS current
    DESCRIPTION
        "Selects pre or post encryption for the ASI monitor port.
         This parameter is only applicable to SEMs with semMainBoardType
         of 'type2'.

         Once written, the change to this parameter will take immediate
         effect.  However, in order for the change to persist through
         subsequent reboots or power cycles, the change must be saved via
         the semSaveConfig parameter.

         @Config(config=yes, reboot=no)
         @Save(semSaveConfig, value=2)
         @File(config.ini, type='ini')
        "
::= { semAsiMonitorPortConfig 3 }


-- ------------------------------------------------------------------------------
--
-- semAsiStatus
--

semAsiStatusTable OBJECT-TYPE
    SYNTAX SEQUENCE OF SemAsiStatusEntry
    MAX-ACCESS not-accessible
    STATUS current
    DESCRIPTION
        "This is a table of status parameters for the eight ASI ports."
::= { semAsiStatus 1 }

semAsiStatusEntry OBJECT-TYPE
    SYNTAX SemAsiStatusEntry
    MAX-ACCESS not-accessible
    STATUS current
    DESCRIPTION
        "Asi Interface Status Table Entry."
    INDEX { semAsiStatusPortNum }
::= { semAsiStatusTable 1 }

SemAsiStatusEntry ::= SEQUENCE
    {
     semAsiStatusPortNum             Integer32,
     semAsiStatusInputActive         ActiveTYPE,
     semAsiStatusOutTransStreamNum   Integer32
    }

semAsiStatusPortNum OBJECT-TYPE
    SYNTAX Integer32(1..8)
    MAX-ACCESS not-accessible
    STATUS current
    DESCRIPTION
        "ASI Port Number."
::= { semAsiStatusEntry 1 }

semAsiStatusInputActive OBJECT-TYPE
    SYNTAX ActiveTYPE
    MAX-ACCESS read-only
    STATUS current
    DESCRIPTION
        "This parameter indicates if input is detected on the ASI port."
::= { semAsiStatusEntry 2 }

semAsiStatusOutTransStreamNum OBJECT-TYPE
    SYNTAX Integer32 (0..16)
    MAX-ACCESS read-only
    STATUS current
    DESCRIPTION
        "The number of the output transport stream routed to this output.
         Zero indicates that no stream is routed to this port.
         It serves as the index into the Transport Stream Configuration Table.
         This parameter is only applicable to ASI ports configured as output."
::= { semAsiStatusEntry 3 }


-- ------------------------------------------------------------------------------
--
-- semAsiStatusGeneral
--

semAsiPortsCount OBJECT-TYPE
    SYNTAX Integer32
    MAX-ACCESS read-only
    STATUS current
    DESCRIPTION
        "The number of ASI ports installed on this SEM."
::= { semAsiStatusGeneral 1 }

semAsiStatusNumOutputStreams OBJECT-TYPE
    SYNTAX Integer32
    MAX-ACCESS read-only
    STATUS current
    DESCRIPTION
        "The number of ASI output streams configured."
::= { semAsiStatusGeneral 2 }


-- ------------------------------------------------------------------------------
--
-- semGbe
--
-- semGbeConfig
--
-- semGbeConfigGeneral
--

semGbeDefaultGateway OBJECT-TYPE
    SYNTAX IpAddress
    MAX-ACCESS read-write
    STATUS current
    DESCRIPTION
        "This is the IP address of the default gateway for this Gigabit Ethernet interface.

         Once written, a save must be performed via the semSaveConfig
         parameter and the SEM must be rebooted for the change to take effect.

         @Config(config=yes, reboot=yes)
         @Save(semSaveConfig, value=2)
         @File(config.ini, type='ini')
        "
::= { semGbeConfigGeneral 1 }

semGbeRoutingApplyChange OBJECT-TYPE
    SYNTAX ApplyDataToDeviceTYPE
    MAX-ACCESS read-write
    STATUS current
    DESCRIPTION
        "The Apply for the Gigabit Ethernet Routing Table.

         This parameter MUST be set to 'apply' in order for any of the data
         in the semGbeRoutingTable to take effect in the SEM.  This parameter
         MUST be set LAST after all other data in the semGbeRoutingTable has
         been configured.

         Once written, the change to this parameter will take immediate effect.

         @Config(config=no, reboot=no)
        "
::= { semGbeConfigGeneral 2 }

semGbeLoadBinaryType OBJECT-TYPE
    SYNTAX INTEGER
        {
         gbeBinLoadNormal         (1),
         gbeBinLoadVBR            (2)
        }
    MAX-ACCESS read-write
    STATUS obsolete
    DESCRIPTION
        "This object is obsolete.
        "
::= { semGbeConfigGeneral 3 }

semGbeJitterAbsorption OBJECT-TYPE
    SYNTAX Integer32
    MAX-ACCESS read-write
    STATUS current
    DESCRIPTION
        "Jitter Absorption setting in range of 0 to 200 milliseconds
         in increments of 5 ms.

         Once written, the change to this parameter will take immediate
         effect.  However, in order for the change to persist through
         subsequent reboots or power cycles, the change must be saved via
         the semSaveConfig parameter.

         @Range(min=0, max=200, step=5)
         @Config(config=yes, reboot=no)
         @Save(semSaveConfig, value=2)
         @File(config.ini, type='ini')
        "
::= { semGbeConfigGeneral 4 }

semGbeMulticastRcvApplyChange OBJECT-TYPE
    SYNTAX ApplyDataToDeviceTYPE
    MAX-ACCESS read-write
    STATUS obsolete
    DESCRIPTION
        "The Apply for the Gigabit Ethernet Multicast Receive. This parameter
         MUST be set to 'apply' in order for any of the data in the
         semGbeMulticastRcvTable to take effect in the SEM.  This parameter
         MUST be set LAST after all other data in the semGbeMulticastRcvTable
         has been configured.

         This object is obsolete.
        "
::= { semGbeConfigGeneral 5 }


-- ------------------------------------------------------------------------------
--
-- semGbeConfigTable
--

semGbeConfigTable OBJECT-TYPE
    SYNTAX SEQUENCE OF SemGbeConfigEntry
    MAX-ACCESS not-accessible
    STATUS current
    DESCRIPTION
        "This is a table of configuration parameters for the
         Gigabit Ethernet Interface."
::= { semGbeConfig 2 }

semGbeConfigEntry OBJECT-TYPE
    SYNTAX SemGbeConfigEntry
    MAX-ACCESS not-accessible
    STATUS current
    DESCRIPTION
        "Gigabit Ethernet Interface Configuration Table Entry."
    INDEX { semGbeConfigPortNum }
::= { semGbeConfigTable 1 }

SemGbeConfigEntry ::= SEQUENCE
    {
     semGbeConfigPortNum             Integer32,
     semGbeConfigEnable              INTEGER,
     semGbeConfigNumInStreams        Integer32,
     semGbeConfigAutoNegotiateEnable EnableDisableTYPE,
     semGbeConfigIgmpVersion         INTEGER
    }

semGbeConfigPortNum OBJECT-TYPE
    SYNTAX Integer32(1..3)
    MAX-ACCESS not-accessible
    STATUS current
    DESCRIPTION
        "Gigabit Ethernet Port Number."
::= { semGbeConfigEntry 1 }

semGbeConfigEnable OBJECT-TYPE
    SYNTAX INTEGER
        {
         disabled                     (1),
         enabledInputOutput           (2),
         enabledLoopThrough           (3),
         enabledLoopThroughTerminator (4)
        }
    MAX-ACCESS read-write
    STATUS current
    DESCRIPTION
        "This parameter enables the Gigabit Ethernet Device.
         Only the first and second GigE Ports can be configured for loop through.

         Once written, a save must be performed via the semSaveConfig
         parameter and the SEM must be rebooted for the change to take effect.

         @Config(config=yes, reboot=yes)
         @Save(semSaveConfig, value=2)
         @File(config.ini, type='ini')
        "
::= { semGbeConfigEntry 2 }

semGbeConfigNumInStreams OBJECT-TYPE
    SYNTAX Integer32
    MAX-ACCESS read-write
    STATUS current
    DESCRIPTION
        "The number of input streams on this Gigabit Ethernet Interface.
         There are maximum of 384 input streams that can be allocated
         across all input enabled Gigabit Ethernet Interface Ports.

         Once written, a save must be performed via the semSaveConfig
         parameter and the SEM must be rebooted for the change to take effect.

         @Config(config=yes, reboot=yes)
         @Save(semSaveConfig, value=2)
         @File(config.ini, type='ini')
        "
::= { semGbeConfigEntry 3 }

semGbeConfigAutoNegotiateEnable OBJECT-TYPE
    SYNTAX EnableDisableTYPE
    MAX-ACCESS read-write
    STATUS current
    DESCRIPTION
        "Auto negotiation enabled or disabled.

         Once written, a save must be performed via the semSaveConfig
         parameter and the SEM must be rebooted for the change to take effect.

         @Config(config=yes, reboot=yes)
         @Save(semSaveConfig, value=2)
         @File(config.ini, type='ini')
        "
::= { semGbeConfigEntry 4 }

semGbeConfigIgmpVersion OBJECT-TYPE
    SYNTAX INTEGER
        {
         igmpV1 (1),
         igmpV2 (2),
         igmpV3 (3),
         staticIgmpV1 (4),
         staticIgmpV2 (5),
         staticIgmpV3 (6)
        }
    MAX-ACCESS read-write
    STATUS current
    DESCRIPTION
        "This parameter sets the IGMP Version (autonomous default or static)
         that the SEM will use on this Gigabit Ethernet interface.
         The Gigabit Ethernet interface uses the IGMP version as follows:
             - Autonomous v1, v2, v3:
                   In this case, the version is the initial default version used
                   by the Gigabit interface until the network informs the SEM to
                   use a different one.
             - Static v1, v2, v3:
                   In this case, the version is static and will not be changed.  This
                   is the version the Gigabit interface will use regardless of the
                   network.  The network is expected to be set up to the same version
                   as the Gigabit Ethernet interface.

         Once written, the change to this parameter will take immediate
         effect.  However, in order for the change to persist through
         subsequent reboots or power cycles, the change must be saved via
         the semSaveConfig parameter.

         @Config(config=yes, reboot=no)
         @Save(semSaveConfig, value=2)
         @File(config.ini, type='ini')
        "
::= { semGbeConfigEntry 5 }


-- ------------------------------------------------------------------------------
--
-- semGbeConfigIpTable
--

semGbeConfigIpTable OBJECT-TYPE
    SYNTAX SEQUENCE OF SemGbeConfigIpEntry
    MAX-ACCESS not-accessible
    STATUS current
    DESCRIPTION
        "This is a table of IP Address configuration parameters for the
         Gigabit Ethernet Interface.

         @Config(config=yes, reboot=yes)
         @Save(semSaveConfig, value=2)
         @File(config.ini, type='ini')
        "
::= { semGbeConfig 3 }

semGbeConfigIpEntry OBJECT-TYPE
    SYNTAX SemGbeConfigIpEntry
    MAX-ACCESS not-accessible
    STATUS current
    DESCRIPTION
        "Gigabit Ethernet Interface IP Configuration Table Entry."
    INDEX { semGbeConfigIpPortNum }
::= { semGbeConfigIpTable 1 }

SemGbeConfigIpEntry ::= SEQUENCE
    {
     semGbeConfigIpPortNum         Integer32,
     semGbeConfigIpAddr            IpAddress,
     semGbeConfigIpSubnetMask      IpAddress
    }

semGbeConfigIpPortNum OBJECT-TYPE
    SYNTAX Integer32(1..3)
    MAX-ACCESS not-accessible
    STATUS current
    DESCRIPTION
        "Gigabit Ethernet Port Number."
::= { semGbeConfigIpEntry 1 }

semGbeConfigIpAddr OBJECT-TYPE
    SYNTAX IpAddress
    MAX-ACCESS read-write
    STATUS current
    DESCRIPTION
        "This is the IP address of this Gigabit Ethernet interface.

         Once written, a save must be performed via the semSaveConfig
         parameter and the SEM must be rebooted for the change to take effect.
        "
::= { semGbeConfigIpEntry 2 }

semGbeConfigIpSubnetMask OBJECT-TYPE
    SYNTAX IpAddress
    MAX-ACCESS read-write
    STATUS current
    DESCRIPTION
        "This is subnet mask of this Gigabit Ethernet interface.

         Once written, a save must be performed via the semSaveConfig
         parameter and the SEM must be rebooted for the change to take effect.
        "
::= { semGbeConfigIpEntry 3 }


-- ------------------------------------------------------------------------------
--
-- semGbeRoutingTable
--

semGbeRoutingTable OBJECT-TYPE
    SYNTAX SEQUENCE OF SemGbeRoutingEntry
    MAX-ACCESS not-accessible
    STATUS current
    DESCRIPTION
        "This table is the configuration Static Routing table for the
         Gigabit Ethernet Interface.

         @Commit(param=semGbeConfigRoutingApplyChange, value=2)
         @Config(config=yes, reboot=no)
         @Save(semSaveConfig, value=2)
         @File(config.ini, type='ini')
        "
::= { semGbeConfig 4 }

semGbeRoutingEntry OBJECT-TYPE
    SYNTAX SemGbeRoutingEntry
    MAX-ACCESS not-accessible
    STATUS current
    DESCRIPTION
        "Gigabit Ethernet Interface Configuration Static Routing Table Entry."
    INDEX { semGbeRoutingIndex }
::= { semGbeRoutingTable 1 }

SemGbeRoutingEntry ::= SEQUENCE
    {
     semGbeRoutingIndex           Integer32,
     semGbeRoutingDestIpAddr      IpAddress,
     semGbeRoutingGateIpAddr      IpAddress,
     semGbeRoutingSubnetMask      IpAddress
    }

semGbeRoutingIndex OBJECT-TYPE
    SYNTAX Integer32
    MAX-ACCESS not-accessible
    STATUS current
    DESCRIPTION
        "The index of the Routing table entry.
         Currently limited to 16."
::= { semGbeRoutingEntry 1 }

semGbeRoutingDestIpAddr OBJECT-TYPE
    SYNTAX IpAddress
    MAX-ACCESS read-write
    STATUS current
    DESCRIPTION
        "The Gigabit Ethernet Routing Destination IP address.

         Once written, the change to this parameter will only take immediate
         effect after semGbeConfigRoutingApplyChange is set to 'apply'.  In order for the
         change to persist through subsequent reboots or power cycles, the
         change must be saved via the semSaveConfig parameter.
        "
::= { semGbeRoutingEntry 2 }

semGbeRoutingGateIpAddr OBJECT-TYPE
    SYNTAX IpAddress
    MAX-ACCESS read-write
    STATUS current
    DESCRIPTION
        "The Gigabit Ethernet Routing Gateway IP address.

         Once written, the change to this parameter will only take immediate
         effect after semGbeConfigRoutingApplyChange is set to 'apply'.  In order for the
         change to persist through subsequent reboots or power cycles, the
         change must be saved via the semSaveConfig parameter.
        "
::= { semGbeRoutingEntry 3 }

semGbeRoutingSubnetMask OBJECT-TYPE
    SYNTAX IpAddress
    MAX-ACCESS read-write
    STATUS current
    DESCRIPTION
        "The Gigabit Ethernet Routing Subnet Mask.

         Once written, the change to this parameter will only take immediate
         effect after semGbeConfigRoutingApplyChange is set to 'apply'.  In order for the
         change to persist through subsequent reboots or power cycles, the
         change must be saved via the semSaveConfig parameter.
        "
::= { semGbeRoutingEntry 4 }


-- ------------------------------------------------------------------------------
--
-- semGbeConfigArp
--

semGbeStaticArpApplyChange OBJECT-TYPE
    SYNTAX ApplyDataToDeviceTYPE
    MAX-ACCESS read-write
    STATUS current
    DESCRIPTION
        "The Apply for the Gigabit Ethernet Static ARP Table.

         This parameter MUST be set to 'apply' in order for any of the data
         in the semGbeStaticArpTable to take effect in the SEM.  This parameter
         MUST be set LAST after all other data in the semGbeStaticArpTable has
         been configured.

         Once written, the change to this parameter will take immediate effect.

         @Config(config=no, reboot=no)
        "
::= { semGbeConfigArp 1 }

semGbeDeleteArpApplyChange OBJECT-TYPE
    SYNTAX ApplyDataToDeviceTYPE
    MAX-ACCESS read-write
    STATUS current
    DESCRIPTION
        "The Apply for the Gigabit Ethernet Delete ARP Table.

         This parameter MUST be set to 'apply' in order for any of the data
         in the semGbeDeleteArpTable to take effect in the SEM.  This parameter
         MUST be set LAST after all other data in the semGbeDeleteArpTable has
         been configured.

         Once written, the change to this parameter will take immediate effect.

         @Config(config=no, reboot=no)
        "
::= { semGbeConfigArp 2 }

semGbeUpdateStatusArpTable OBJECT-TYPE
    SYNTAX UpdateStatusTYPE
    MAX-ACCESS read-write
    STATUS current
    DESCRIPTION
        "Update for the Gigabit Ethernet Status ARP Table.
         The Status ARP Table is updated approximately every 60 seconds.
         When this parameter is set to 'update' the SEM will immediately
         update the Status ARP Table and reset the timer.  The update is
         complete when the SEM changes this parameter to 'updateNotInProgress'.
         Depending on the processor load of the SEM it could take many
         seconds for this update to finish.

         @Config(config=no, reboot=no)
        "
::= { semGbeConfigArp 3 }

semGbeDynamicArpTimeout OBJECT-TYPE
    SYNTAX Unsigned32(1..'ffffffff'h)
    MAX-ACCESS read-write
    STATUS current
    DESCRIPTION
        "Dynamic ARP Entry Timeout in seconds.  Minimum value is one second.
         If within this specified period, no ARP reply is received, the ARP
         table entry will expire and be removed from the table.  This does
         not apply to static ARP entries configured in semGbeStaticArpTable.

         Dynamic ARP entries associated with Output Transport Streams will
         not expire unless explicitly allowed by setting
         semGbeDynamicOutputTsArpTimeoutEnable appropriately.

         This value must be greater than semGbeDynamicArpRetryInterval.
         If semGbeDynamicArpRetryInterval and semGbeDynamicArpTimeout are
         being changed at the same time, semGbeDynamicArpRetryInterval should
         be written first.

         Once written, the change to this parameter will take immediate
         effect.  However, in order for the change to persist through
         subsequent reboots or power cycles, the change must be saved via
         the semSaveConfig parameter.

         @Config(config=yes, reboot=no)
         @Save(semSaveConfig, value=2)
         @File(config.ini, type='ini')
        "
::= { semGbeConfigArp 4 }

semGbeDynamicArpRetryInterval OBJECT-TYPE
    SYNTAX Unsigned32(1..'ffffffff'h)
    MAX-ACCESS read-write
    STATUS current
    DESCRIPTION
        "Dynamic ARP Entry Retry Interval in seconds.  Minimum value is one second.
         The SEM will send an ARP request and will retry twice at 500 millisecond
         interval if no response is received.  After these two retries the SEM will
         retry at the user configured interval.

         If semGbeDynamicArpRetryInterval and semGbeDynamicArpTimeout are
         being changed at the same time, semGbeDynamicArpRetryInterval should
         be written first.

         Once written, the change to this parameter will take immediate
         effect.  However, in order for the change to persist through
         subsequent reboots or power cycles, the change must be saved via
         the semSaveConfig parameter.

         @Config(config=yes, reboot=no)
         @Save(semSaveConfig, value=2)
         @File(config.ini, type='ini')
        "
::= { semGbeConfigArp 5 }

semGbeDynamicOutputTsArpTimeoutEnable OBJECT-TYPE
    SYNTAX EnableDisableTYPE
    MAX-ACCESS read-write
    STATUS current
    DESCRIPTION
        "Setting to 'enable' allows Dynamic ARP entries associated with Output
         Transport Streams to be treated like other dynamic ARPs and expire based
         on ARP timeout configuration settings.

         Once written, the change to this parameter will take immediate
         effect.  However, in order for the change to persist through
         subsequent reboots or power cycles, the change must be saved via
         the semSaveConfig parameter.

         @Config(config=yes, reboot=no)
         @Save(semSaveConfig, value=2)
         @File(config.ini, type='ini')
        "
::= { semGbeConfigArp 6 }

semGbeDynamicArpFlush OBJECT-TYPE
    SYNTAX FlushTYPE
    MAX-ACCESS read-write
    STATUS current
    DESCRIPTION
        "Setting to 'flush' removes all Dynamic ARP entries from the Gigabit
         Ethernet ARP Table.  Static entries are not removed.  Static ARP
         Entries configured in semGbeStaticArpTable must be explicitly
         removed by zeroing all fields in the semGbeStaticArpTable and
         setting semGbeStaticArpApplyChange or using semGbeDeleteArpTable
         and semGbeDeleteArpApplyChange.  An update of the ARP Status Table
         is also automatically performed when 'flush' is set.  The flush
         and update are complete when the SEM changes this parameter to
         'flushNotInProgress'.  Depending on the processor load of the SEM
         it could take many seconds for this operation to finish.

         Once written, the change to this parameter will take immediate effect.

         @Config(config=no, reboot=no)
        "
::= { semGbeConfigArp 7 }


-- ------------------------------------------------------------------------------
--
-- semGbeStaticArpTable
--

semGbeStaticArpTable OBJECT-TYPE
    SYNTAX SEQUENCE OF SemGbeStaticArpEntry
    MAX-ACCESS not-accessible
    STATUS current
    DESCRIPTION
        "This table is the configuration Static ARP table for the
         Gigabit Ethernet Interface.  Entries may be deleted by
         zeroing out the fields then setting semGbeStaticArpApplyChange
         or by utilizing the semGbeDeleteArpTable."
::= { semGbeConfig 6 }

semGbeStaticArpEntry OBJECT-TYPE
    SYNTAX SemGbeStaticArpEntry
    MAX-ACCESS not-accessible
    STATUS current
    DESCRIPTION
        "Gigabit Ethernet Interface Configuration Static ARP Table Entry."
    INDEX { semGbeStaticArpIndex }
::= { semGbeStaticArpTable 1 }

SemGbeStaticArpEntry ::= SEQUENCE
    {
     semGbeStaticArpIndex       Integer32,
     semGbeStaticArpIpAddr      IpAddress,
     semGbeStaticArpMacAddr     DisplayString
    }

semGbeStaticArpIndex OBJECT-TYPE
    SYNTAX Integer32
    MAX-ACCESS not-accessible
    STATUS current
    DESCRIPTION
        "The index of the Static ARP table entry.
         Currently limited to 16."
::= { semGbeStaticArpEntry 1 }

semGbeStaticArpIpAddr OBJECT-TYPE
    SYNTAX IpAddress
    MAX-ACCESS read-write
    STATUS current
    DESCRIPTION
        "The Gigabit Ethernet Static ARP entry IP address.

         Once written, the change to this parameter will only take immediate
         effect after semGbeStaticArpApplyChange is set to 'apply'.  In order for the
         change to persist through subsequent reboots or power cycles, the
         change must be saved via the semSaveConfig parameter.

         @Commit(param=semGbeStaticArpApplyChange, value=2)
         @Config(config=yes, reboot=no)
         @Save(semSaveConfig, value=2)
         @File(config.ini, type='ini')
        "
::= { semGbeStaticArpEntry 2 }

semGbeStaticArpMacAddr OBJECT-TYPE
    SYNTAX DisplayString (SIZE (0..17))
    MAX-ACCESS read-write
    STATUS current
    DESCRIPTION
        "The Gigabit Ethernet Static ARP entry MAC address.
         The string length is 17 characters in the format
         'hh:hh:hh:hh:hh:hh' where 'hh' is a hexadecimal number.

         Once written, the change to this parameter will only take immediate
         effect after semGbeStaticArpApplyChange is set to 'apply'.  In order for the
         change to persist through subsequent reboots or power cycles, the
         change must be saved via the semSaveConfig parameter.

         @Commit(param=semGbeStaticArpApplyChange, value=2)
         @Config(config=yes, reboot=no)
         @Save(semSaveConfig, value=2)
         @File(config.ini, type='ini')
        "
::= { semGbeStaticArpEntry 3 }


-- ------------------------------------------------------------------------------
--
-- semGbeDeleteArpTable
--

semGbeDeleteArpTable OBJECT-TYPE
    SYNTAX SEQUENCE OF SemGbeDeleteArpEntry
    MAX-ACCESS not-accessible
    STATUS current
    DESCRIPTION
        "This table is the configuration Delete ARP table for the
         Gigabit Ethernet Interface.  Entries in the semGbeStaticArpTable
         or the semGbeStatusArpTable may be deleted via this table.
         It is generally expected that semGbeStatusArpTable entries will
         be deleted using this table.
         Entries in this table are not required to be packed at the top
         of the table."
::= { semGbeConfig 7 }

semGbeDeleteArpEntry OBJECT-TYPE
    SYNTAX SemGbeDeleteArpEntry
    MAX-ACCESS not-accessible
    STATUS current
    DESCRIPTION
        "Gigabit Ethernet Interface Configuration Delete ARP Table Entry."
    INDEX { semGbeDeleteArpIndex }
::= { semGbeDeleteArpTable 1 }

SemGbeDeleteArpEntry ::= SEQUENCE
    {
     semGbeDeleteArpIndex       Integer32,
     semGbeDeleteArpIpAddr      IpAddress
    }

semGbeDeleteArpIndex OBJECT-TYPE
    SYNTAX Integer32
    MAX-ACCESS not-accessible
    STATUS current
    DESCRIPTION
        "The index of the Delete ARP table entry.
         Currently limited to 128."
::= { semGbeDeleteArpEntry 1 }

semGbeDeleteArpIpAddr OBJECT-TYPE
    SYNTAX IpAddress
    MAX-ACCESS read-write
    STATUS current
    DESCRIPTION
        "The Gigabit Ethernet Delete ARP IP address.

         Once written, the change to this parameter will only take immediate
         effect after semGbeDeleteArpApplyChange is set to 'apply'.

         @Commit(param=semGbeDeleteArpApplyChange, value=2)
         @Config(config=no, reboot=no)
        "
::= { semGbeDeleteArpEntry 2 }


-- ------------------------------------------------------------------------------
--
-- semGbeRedundantModeConfig
--

semGbeRedunModeEnabled OBJECT-TYPE
    SYNTAX EnableDisableTYPE
    MAX-ACCESS read-write
    STATUS current
    DESCRIPTION
        "The Gigabit Ethernet Redundant Mode Enable/Disable.

         This entry applies to Gigabit Ethernet Interface Redundancy.  When
         Gigabit Ethernet Interface Redundancy is 'enabled' MPTS Redundancy
         cannot be used.  MPTS Redundancy is configured in entries in the
         semGbeInputUdpConfig group.

         Once written, a save must be performed via the semSaveConfig
         parameter and the SEM must be rebooted for the change to take effect.

         @Config(config=yes, reboot=yes)
         @Save(semSaveConfig, value=2)
         @File(config.ini, type='ini')
        "
::= { semGbeRedundantModeConfig 1 }

semGbeRedunModeApplyChange OBJECT-TYPE
    SYNTAX ApplyDataToDeviceTYPE
    MAX-ACCESS read-write
    STATUS current
    DESCRIPTION
        "The Apply for Gigabit Ethernet Redundant Mode.
         This parameter MUST be set to 'apply' in order for any of the
         following to take effect in the SEM:
            semGbeRedunModeThreshold
            semGbeRedunModeMonPeriod
            semGbeRedunModeSuspend

         This parameter MUST be set LAST after all other data has been configured.

         Once written, the change to this parameter will take immediate effect.

         @Config(config=no, reboot=no)
        "
::= { semGbeRedundantModeConfig 2 }

semGbeRedunModeThreshold OBJECT-TYPE
    SYNTAX Integer32 (0..100)
    MAX-ACCESS read-write
    STATUS current
    DESCRIPTION
        "The Gigabit Ethernet Redundant Mode failover threshold.

         FailOver = (PrimaryRate) < (Threshold * SecondaryRate)
         The Primary must remain below the threshold for
         semGbeRedunModeMonPeriod.  Fail Over will not occur when
         semGbeRedunModeSuspend is set to 'suspended'.

         This entry applies to Gigabit Ethernet Interface Redundancy.  MPTS
         Redundancy is configured in entries in the semGbeInputUdpConfig group.

         Once written, the change to this parameter will only take immediate
         effect after semGbeRedunModeApplyChange is set to 'apply'.  In order
         for the change to persist through subsequent reboots or power cycles,
         the change must be saved via the semSaveConfig parameter.

         @Commit(param=semGbeRedunModeApplyChange, value=2)
         @Config(config=yes, reboot=no)
         @Save(semSaveConfig, value=2)
         @File(config.ini, type='ini')
        "
::= { semGbeRedundantModeConfig 3 }

semGbeRedunModeMonPeriod OBJECT-TYPE
    SYNTAX Integer32 (1..30)
    MAX-ACCESS read-write
    STATUS current
    DESCRIPTION
        "The Gigabit Ethernet Redundant Mode monitoring period in seconds.

         This entry applies to Gigabit Ethernet Interface Redundancy.  MPTS
         Redundancy is configured in entries in the semGbeInputUdpConfig group.

         Once written, the change to this parameter will only take immediate
         effect after semGbeRedunModeApplyChange is set to 'apply'.  In order
         for the change to persist through subsequent reboots or power cycles,
         the change must be saved via the semSaveConfig parameter.

         @Commit(param=semGbeRedunModeApplyChange, value=2)
         @Config(config=yes, reboot=no)
         @Save(semSaveConfig, value=2)
         @File(config.ini, type='ini')
        "
::= { semGbeRedundantModeConfig 4 }

semGbeRedunModePrimaryPort OBJECT-TYPE
    SYNTAX Integer32 (1..2)
    MAX-ACCESS read-write
    STATUS current
    DESCRIPTION
        "The Gigabit Ethernet Redundant Mode Primary physical port.

         This entry applies to Gigabit Ethernet Interface Redundancy.  MPTS
         Redundancy is configured in entries in the semGbeInputUdpConfig group.

         Once written, a save must be performed via the semSaveConfig
         parameter and the SEM must be rebooted for the change to take effect.

         @Config(config=yes, reboot=yes)
         @Save(semSaveConfig, value=2)
         @File(config.ini, type='ini')
        "
::= { semGbeRedundantModeConfig 5 }

semGbeRedunModeSuspend OBJECT-TYPE
    SYNTAX EnableDisableTYPE
    MAX-ACCESS read-write
    STATUS current
    DESCRIPTION
        "The Gigabit Ethernet Redundant Mode Suspend.  Setting to 'enable'
         keeps failover from occurring (keeps Gbe on current physical port).

         This entry applies to Gigabit Ethernet Interface Redundancy.  MPTS
         Redundancy is configured in entries in the semGbeInputUdpConfig group.

         Once written, the change to this parameter will only take immediate
         effect after semGbeRedunModeApplyChange is set to 'apply'.  In order
         for the change to persist through subsequent reboots or power cycles,
         the change must be saved via the semSaveConfig parameter.

         @Commit(param=semGbeRedunModeApplyChange, value=2)
         @Config(config=yes, reboot=no)
         @Save(semSaveConfig, value=2)
         @File(config.ini, type='ini')
        "
::= { semGbeRedundantModeConfig 6 }

semGbeRedunModeForceFailOver OBJECT-TYPE
    SYNTAX EnableDisableTYPE
    MAX-ACCESS read-write
    STATUS current
    DESCRIPTION
        "The Gigabit Ethernet Redundant Mode Force Failover.  Setting to 'enable'
         forces GBE switch to physical port not currently in use.

         This entry applies to Gigabit Ethernet Interface Redundancy.  MPTS
         Redundancy is configured in entries in the semGbeInputUdpConfig group.

         The SEM will set this back to 'disable' after forcing the fail over.

         Once written, the change to this parameter will take immediate effect.

         @Config(config=no, reboot=no)
        "
::= { semGbeRedundantModeConfig 7 }

semGbeRedunModeClearFailOverAlarm OBJECT-TYPE
    SYNTAX ClearAlarmTYPE
    MAX-ACCESS read-write
    STATUS current
    DESCRIPTION
        "Setting to 'clearAlarm' clears the semAlarmGigeFailOver.
         The SEM will set this back to 'clearAlarmNotInProgress'
         after clearing the alarm.

         This entry applies to Gigabit Ethernet Interface Redundancy.  MPTS
         Redundancy is configured in entries in the semGbeInputUdpConfig group.

         Once written, the change to this parameter will take immediate effect.

         @Config(config=no, reboot=no)
        "
::= { semGbeRedundantModeConfig 8 }

semGbeRedunSelectCounting OBJECT-TYPE
    SYNTAX INTEGER
        {
         ethernetFrameCounting  (1),
         mpegNullPacketCounting (2)
        }
    MAX-ACCESS read-write
    STATUS current
    DESCRIPTION
        "Selects whether Ethernet Frames Counts or MPEG Null Packet Counts
         will be monitored and used to determine failover while in Gigabit
         Ethernet Redundant Mode.  This entry is only used when
         semGbeRedunModeEnabled is set to 'enabled'.

         This entry applies to Gigabit Ethernet Interface Redundancy.  MPTS
         Redundancy is configured in entries in the semGbeInputUdpConfig group.

         Once written, a save must be performed via the semSaveConfig
         parameter and the SEM must be rebooted for the change to take effect.

         @Config(config=yes, reboot=yes)
         @Save(semSaveConfig, value=2)
         @File(config.ini, type='ini')
        "
::= { semGbeRedundantModeConfig 9 }


-- ------------------------------------------------------------------------------
--
-- semGbeMulticastRcvTable  - obsolete
--

semGbeMulticastRcvTable OBJECT-TYPE
    SYNTAX SEQUENCE OF SemGbeMulticastRcvEntry
    MAX-ACCESS not-accessible
    STATUS obsolete
    DESCRIPTION
        "This table is the Multicast Receive configuration table for the
         Gigabit Ethernet Interface.  It is indexed by multicast receive
         index.
         Once written, the change to this table will only take immediate
         effect after semGbeMulticastRcvApplyChange is set to 'apply'.
         However, in order for the change to persist through subsequent
         reboots or power cycles, the change must be saved via semSaveConfig.

         This table is obsolete.
        "
::= { semGbeConfig 9 }

semGbeMulticastRcvEntry OBJECT-TYPE
    SYNTAX SemGbeMulticastRcvEntry
    MAX-ACCESS not-accessible
    STATUS obsolete
    DESCRIPTION
        "Gigabit Ethernet Interface Multicast Receive Configuration Table Entry.

         This table is obsolete."
    INDEX { semGbeMulticastRcvIndex }
::= { semGbeMulticastRcvTable 1 }

SemGbeMulticastRcvEntry ::= SEQUENCE
    {
     semGbeMulticastRcvIndex          Integer32,
     semGbeMulticastRcvPortNum        Integer32,
     semGbeMulticastRcvIpAddr         IpAddress,
     semGbeMulticastRcvUdpPort        Integer32,
     semGbeMulticastRcvIncludeIpAddr  IpAddress
    }

semGbeMulticastRcvIndex OBJECT-TYPE
    SYNTAX Integer32 (1..64)
    MAX-ACCESS not-accessible
    STATUS obsolete
    DESCRIPTION
        "The Multicast Receive table index.

         This object is obsolete."
::= { semGbeMulticastRcvEntry 1 }

semGbeMulticastRcvPortNum OBJECT-TYPE
    SYNTAX Integer32
    MAX-ACCESS read-write
    STATUS obsolete
    DESCRIPTION
        "The Gigabit Ethernet physical port on which to receive multicast packets.
         Zero indicates this port is not in use for multicast.

         Once written, the change to this table will only take immediate
         effect after semGbeMulticastRcvApplyChange is set to 'apply'.

         This object is obsolete."
::= { semGbeMulticastRcvEntry 2 }

semGbeMulticastRcvIpAddr OBJECT-TYPE
    SYNTAX IpAddress
    MAX-ACCESS read-write
    STATUS obsolete
    DESCRIPTION
        "The Multicast receive IP address (224.0.0.0 to 224.0.0.255 is reserved).
         An IP address of 0.0.0.0 indicates table entry not in use.

         Once written, the change to this table will only take immediate
         effect after semGbeMulticastRcvApplyChange is set to 'apply'.

         This object is obsolete."
::= { semGbeMulticastRcvEntry 3 }

semGbeMulticastRcvUdpPort OBJECT-TYPE
    SYNTAX Integer32
    MAX-ACCESS read-write
    STATUS obsolete
    DESCRIPTION
        "The Multicast receive UDP Port (0 to 65535). The SEM will only
         use the new or changed UDP port for multicast data reception when
         the UDP port is first opened. If the UDP Port is currently in use
         for singlecast or broadcast reception, this change will not take
         affect until after the UDP port is closed and then reopened (all
         service and stream routes must be removed to close a UDP port).

         Once written, the change to this table will only take immediate
         effect after semGbeMulticastRcvApplyChange is set to 'apply'.

         This object is obsolete."
::= { semGbeMulticastRcvEntry 4 }

semGbeMulticastRcvIncludeIpAddr OBJECT-TYPE
    SYNTAX IpAddress
    MAX-ACCESS read-write
    STATUS obsolete
    DESCRIPTION
        "This is the Include IP address of the source device.  If the router
         supports IGMP v3 the GBE will only receive data for this multicast
         group from this source IP.  If Include Source IP is not specified or
         the router does not support IGMP v3 the GBE will receive data for
         this multicast group from any source device.  Include IP address
         must be a valid singlecast address.

         Once written, the change to this table will only take immediate
         effect after semGbeMulticastRcvApplyChange is set to 'apply'.

         This object is obsolete."
::= { semGbeMulticastRcvEntry 5 }


-- ------------------------------------------------------------------------------
--
-- semGbeMulticastTransmit
--
-- semGbeMulticastTxGeneral
--

semGbeMulticastTxTimeToLive OBJECT-TYPE
    SYNTAX Integer32 (0..255)
    MAX-ACCESS read-write
    STATUS current
    DESCRIPTION
        "The Time to Live for Gigabit Ethernet transmit multicast packets.

         Once written, the change to this parameter will take immediate
         effect.  However, in order for the change to persist through
         subsequent reboots or power cycles, the change must be saved via
         the semSaveConfig parameter.

         @Config(config=yes, reboot=no)
         @Save(semSaveConfig, value=2)
         @File(config.ini, type='ini')
        "
::= { semGbeMulticastTxGeneral 1 }


-- ------------------------------------------------------------------------------
--
-- semGbeMulticastTxTable
--

semGbeMulticastTxTable OBJECT-TYPE
    SYNTAX SEQUENCE OF SemGbeMulticastTxEntry
    MAX-ACCESS not-accessible
    STATUS current
    DESCRIPTION
        "This table is the Multicast Transmit configuration table for the
         Gigabit Ethernet Interface.  It is indexed by Output Transport
         Stream Number."
::= { semGbeMulticastTransmit 2 }

semGbeMulticastTxEntry OBJECT-TYPE
    SYNTAX SemGbeMulticastTxEntry
    MAX-ACCESS not-accessible
    STATUS current
    DESCRIPTION
        "Gigabit Ethernet Interface Multicast Transmit Configuration Table Entry."
    INDEX { semGbeMulticastTxOutTransStreamNum }
::= { semGbeMulticastTxTable 1 }

SemGbeMulticastTxEntry ::= SEQUENCE
    {
     semGbeMulticastTxOutTransStreamNum  Integer32,
     semGbeMulticastTxPhysPort           Integer32
    }

semGbeMulticastTxOutTransStreamNum OBJECT-TYPE
    SYNTAX Integer32
    MAX-ACCESS not-accessible
    STATUS current
    DESCRIPTION
        "The SEM output transport stream number."
::= { semGbeMulticastTxEntry 1 }

semGbeMulticastTxPhysPort OBJECT-TYPE
    SYNTAX Integer32
    MAX-ACCESS read-write
    STATUS current
    DESCRIPTION
        "The Gigabit Ethernet physical port on which to transmit multicast packets.
         Zero indicates this port is not in use for multicast.

         Once written, a save must be performed via the semSaveConfig
         parameter and the SEM must be rebooted for the change to take effect.

         @Range(min=1, max=3)
         @Config(config=yes, reboot=yes)
         @Save(semSaveConfig, value=2)
         @File(config.ini, type='ini')
        "
::= { semGbeMulticastTxEntry 2 }

-- ------------------------------------------------------------------------------
--
-- semGbeFrameBufferConfig
--

semGbeMaxInputDataRate OBJECT-TYPE
    SYNTAX Integer32
    MAX-ACCESS read-write
    STATUS current
    DESCRIPTION
        "Maximum Gigabit Ethernet MPEG input data rate in bps.  This is the total amount
         of MPEG data expected to be received by all Gigabit Ethernet frame interfaces.
         This data rate is used to determine the frame buffer reset limit.  The expected
         data rate should always be set equal to or greater than the actual input data rate.
         The value of semGbeJitterAbsorption can limit the valid range of this data rate.
         It is highly recommended that the user consult with Motorola prior to changing
         the expected data rate.

         Once written, the change to this parameter will take immediate
         effect.  However, in order for the change to persist through
         subsequent reboots or power cycles, the change must be saved via
         the semSaveConfig parameter.

         @Range(min=0)
         @Config(config=yes, reboot=no)
         @Save(semSaveConfig, value=2)
         @File(config.ini, type='ini')
        "
::= { semGbeFrameBufferConfig 1 }

semGbeBufferAlarmThreshold OBJECT-TYPE
    SYNTAX Integer32
    MAX-ACCESS read-write
    STATUS current
    DESCRIPTION
        "User defined threshold representing a percentage of frame buffer depth.
         The frame buffer level is monitored by the SEM and the maximum level is
         based on the actual input data rate.  The threshold percentage is used
         to determine when to issue a Gigabit Ethernet Frame Buffer Fullness
         alarm (semAlarmGbeBufferFullness).

         Once written, the change to this parameter will take immediate
         effect.  However, in order for the change to persist through
         subsequent reboots or power cycles, the change must be saved via
         the semSaveConfig parameter.

         @Range(min=0, max=100)
         @Config(config=yes, reboot=no)
         @Save(semSaveConfig, value=2)
         @File(config.ini, type='ini')
        "
::= { semGbeFrameBufferConfig 2 }


-- ------------------------------------------------------------------------------
--
-- semGbeVlanCfmConfig
--

semGbeVlanCfmApplyChange OBJECT-TYPE
    SYNTAX ApplyDataToDeviceTYPE
    MAX-ACCESS read-write
    STATUS current
    DESCRIPTION
        "The Apply for Gigabit Ethernet VLAN Tagging and CFM Insertion configuration.
         This parameter MUST be set to 'apply' in order for any of the
         following to take effect in the SEM:
            semGbeVlanTaggingEnabled
            semGbeVlanTaggingPriority
            semGbeVlanTaggingVidType
            semGbeCfmInsertionEnabled
            semGbeCfmInsertionPeriod
            semGbeCfmInsertionMacAddress

         This parameter MUST be set LAST after all other data has been configured.

         Once written, the change to this parameter will take immediate effect.

         @Config(config=no, reboot=no)
        "
::= { semGbeVlanCfmConfig 1 }

semGbeVlanTaggingEnabled OBJECT-TYPE
    SYNTAX EnableDisableTYPE
    MAX-ACCESS read-write
    STATUS current
    DESCRIPTION
        "The Gigabit Ethernet VLAN Tagging Enable/Disable. VLAN Tagging is
         only applicable when there is at least 1 Gigabit Ethernet output stream.
         VLAN Tagging must be enabled if CFM Insertion is to be enabled. Disabling
         VLAN Tagging will automatically disable CFM Insertion.

         Enabling VLAN Tagging will cause the SEM to output IEEE 802.1q VLAN tags on all
         Gigabit Ethernet output streams.

         Once written, the change to this parameter will take immediate effect after
         semGbeVlanCfmApplyChange is set to 'apply'.  However, in order for the change to
         persist through subsequent reboots or power cycles, the change must be saved via
         the semSaveConfig parameter.

         @Commit(param=semGbeVlanCfmApplyChange, value=2)
         @Config(config=yes, reboot=no)
         @Save(semSaveConfig, value=2)
         @File(config.ini, type='ini')
        "
::= { semGbeVlanCfmConfig 2 }

semGbeVlanTaggingPriority OBJECT-TYPE
    SYNTAX INTEGER
        {
         ordinaryLan                (0),
         bulkTransfers              (1),
         spareNotUsed               (2),
         importantUser              (3),
         importantApplication       (4),
         video                      (5),
         voice                      (6),
         importantManagementTraffic (7)
        }
    MAX-ACCESS read-write
    STATUS current
    DESCRIPTION
        "The Gigabit Ethernet VLAN Tagging Priority.

         Once written, the change to this parameter will take immediate effect after
         semGbeVlanCfmApplyChange is set to 'apply'.  However, in order for the change to
         persist through subsequent reboots or power cycles, the change must be saved via
         the semSaveConfig parameter.

         @Commit(param=semGbeVlanCfmApplyChange, value=2)
         @Config(config=yes, reboot=no)
         @Save(semSaveConfig, value=2)
         @File(config.ini, type='ini')
        "
::= { semGbeVlanCfmConfig 3 }

semGbeVlanTaggingVidTable OBJECT-TYPE
    SYNTAX SEQUENCE OF SemGbeVlanTaggingVidEntry
    MAX-ACCESS not-accessible
    STATUS current
    DESCRIPTION
        "This table is the Gigabit Ethernet VLAN Tagging VLAN ID table (VID table).
         It is indexed by Output Transport Stream Number.

         @Commit(param=semGbeVlanCfmApplyChange, value=2)
         @Config(config=yes, reboot=no)
         @Save(semSaveConfig, value=2)
         @File(config.ini, type='ini')
        "
::= { semGbeVlanCfmConfig 4 }

semGbeVlanTaggingVidEntry OBJECT-TYPE
    SYNTAX SemGbeVlanTaggingVidEntry
    MAX-ACCESS not-accessible
    STATUS current
    DESCRIPTION
        "Gigabit Ethernet VLAN Tagging VLAN ID Entry."
    INDEX { semGbeVlanTaggingStreamNum }
::= { semGbeVlanTaggingVidTable 1 }

SemGbeVlanTaggingVidEntry ::= SEQUENCE
    {
     semGbeVlanTaggingStreamNum  Integer32,
     semGbeVlanTaggingVidType    INTEGER,
     semGbeVlanTaggingUserVid    Integer32
    }

semGbeVlanTaggingStreamNum OBJECT-TYPE
    SYNTAX Integer32
    MAX-ACCESS not-accessible
    STATUS current
    DESCRIPTION
        "The SEM output transport stream number."
::= { semGbeVlanTaggingVidEntry 1 }

semGbeVlanTaggingVidType OBJECT-TYPE
    SYNTAX INTEGER
        {
         calculated (1),
         user       (2)
        }
    MAX-ACCESS read-write
    STATUS current
    DESCRIPTION
        "The Gigabit Ethernet VLAN Tagging VLAN Identifier (VID) type. When set to
         calculated, the SEM will automatically calculate the VID for an output stream
         based on the configured output UDP port. When set to user, the SEM will use
         the VID specified in semGbeVlanTaggingUserVid.

         Once written, the change to this parameter will take immediate effect after
         semGbeVlanCfmApplyChange is set to 'apply'.  However, in order for the change to
         persist through subsequent reboots or power cycles, the change must be saved via
         the semSaveConfig parameter.
        "
::= { semGbeVlanTaggingVidEntry 2 }

semGbeVlanTaggingUserVid OBJECT-TYPE
    SYNTAX Integer32
    MAX-ACCESS read-write
    STATUS current
    DESCRIPTION
        "The Gigabit Ethernet VLAN Tagging VLAN user Identifier (VID). This is the VID
         specified by the user. It is only applicable when the semGbeVlanTaggingVidType
         is set to user. VIDs are currently bounded to be from 1024 to 4095. The SEM
         will ensure that the user entered VID is within this range.

         Once written, the change to this parameter will take immediate effect after
         semGbeVlanCfmApplyChange is set to 'apply'.  However, in order for the change to
         persist through subsequent reboots or power cycles, the change must be saved via
         the semSaveConfig parameter.

         @Range(min=1024, max=4095)
        "
::= { semGbeVlanTaggingVidEntry 3 }

semGbeCfmInsertionEnabled OBJECT-TYPE
    SYNTAX EnableDisableTYPE
    MAX-ACCESS read-write
    STATUS current
    DESCRIPTION
        "The Gigabit Ethernet CFM Insertion enable/disable. CFM Insertion is only applicable
         when there is at least 1 Gigabit Ethernet output stream. CFM Insertion
         can only be enabled if VLAN Tagging is also enabled. Disabling
         VLAN Tagging will automatically disable CFM Insertion.

         Enabling CFM Insertion will cause the SEM to output IEEE 802.1ag Connectivity
         Fault Management (CFM) messages on all Gigabit Ethernet interfaces.

         Once written, the change to this parameter will take immediate effect after
         semGbeVlanCfmApplyChange is set to 'apply'.  However, in order for the change to
         persist through subsequent reboots or power cycles, the change must be saved via
         the semSaveConfig parameter.
        "
::= { semGbeVlanCfmConfig 5 }

semGbeCfmInsertionPeriod OBJECT-TYPE
    SYNTAX Integer32
    MAX-ACCESS read-write
    STATUS current
    DESCRIPTION
        "The Gigabit Ethernet CFM Insertion period in milliseconds. This specifies how
         often a CFM message will be inserted.

         Once written, the change to this parameter will take immediate effect after
         semGbeVlanCfmApplyChange is set to 'apply'.  However, in order for the change to
         persist through subsequent reboots or power cycles, the change must be saved via
         the semSaveConfig parameter.

         @Range(min=0)
        "
::= { semGbeVlanCfmConfig 6 }

semGbeCfmInsertionMacAddress OBJECT-TYPE
    SYNTAX DisplayString (SIZE (0..17))
    MAX-ACCESS read-write
    STATUS current
    DESCRIPTION
        "The Gigabit Ethernet CFM Insertion MAC address. This specifies the destination
         Ethernet multicast MAC address for each CFM message. The string length is 17
         characters in the format:
              'hh:hh:hh:hh:hh:hh'
               where 'hh' is a hexadecimal number.

         Once written, the change to this parameter will take immediate effect after
         semGbeVlanCfmApplyChange is set to 'apply'.  However, in order for the change to
         persist through subsequent reboots or power cycles, the change must be saved via
         the semSaveConfig parameter.
        "
::= { semGbeVlanCfmConfig 7 }


-- ------------------------------------------------------------------------------
--
-- semGbeInputUdpConfig
--
-- semGbeInputUdpConfigGeneral
--

semGbeInputUdpConfigApplyChange OBJECT-TYPE
    SYNTAX ApplyDataToDeviceTYPE
    MAX-ACCESS read-write
    STATUS current
    DESCRIPTION
        "The Apply for Gigabit Ethernet UDP Port configuration.
         This parameter MUST be set to 'apply' in order for any of the
         following to take effect in the SEM:
            semGbeInputUdpConfigTable

         This parameter MUST be set LAST after all other data has been configured.

         Once written, the change to this parameter will take immediate effect.

         @Config(config=no, reboot=no)
        "
::= { semGbeInputUdpConfigGeneral 1 }

semGbeInUdpConfMptsRedundMonPeriod OBJECT-TYPE
    SYNTAX Integer32
    MAX-ACCESS read-write
    STATUS current
    DESCRIPTION
        "This is the time in seconds over which Redundant Gigabit Ethernet UDP
         Port Pairs will be monitored.  Range is 1 to 30 seconds.

         Primary to Secondary Fail Over - The monitored data rate of the Primary
         must be below the Secondary by semGbeInUdpConfMptsRedundThreshold
         percent for semGbeInUdpConfMptsRedundMonPeriod before fail over to
         Secondary will occur.  Fail over to Secondary will not occur if
         semGbeInUdpConfMptsRedundSuspend is set to 'suspended' for the Primary.

         Secondary to Primary Switch Back - The monitored data rate of the
         Primary must have returned above semGbeInUdpConfMptsRedundThreshold
         percent below the Secondary for semGbeInUdpConfMptsRedundMonPeriod
         before switch back to Primary will occur.  Switch back to Primary will
         not occur if semGbeInUdpConfMptsRedundSuspend is set to 'suspended' for
         the Secondary.  Once the Primary is restored, switch back to Primary
         will be delayed by semGbeInUdpConfMptsRedundSwitchTime.

         Once written, the change to this parameter will take immediate effect.
         However, in order for the change to persist through subsequent
         reboots or power cycles, the change must be saved via semSaveConfig.

         @Range(min=1, max=30)
         @Config(config=yes, reboot=no)
         @Save(semSaveConfig, value=2)
         @File(config.ini, type='ini')
        "
::= { semGbeInputUdpConfigGeneral 2 }

semGbeInUdpConfMptsRedundSwitchTime OBJECT-TYPE
    SYNTAX Integer32
    MAX-ACCESS read-write
    STATUS current
    DESCRIPTION
        "This is the time in seconds to wait before switching back to the
         Primary of a Redundant Gigabit Ethernet UDP Port pair after the Primary
         is healthy.  Range is 0 to 3600.  This time is in addition to
         semGbeInUdpConfMptsRedundMonPeriod.  Switch back to Primary will
         not occur if semGbeInUdpConfMptsRedundSuspend is set to 'suspended' for
         the Secondary.

         Once written, the change to this parameter will take immediate effect.
         However, in order for the change to persist through subsequent
         reboots or power cycles, the change must be saved via semSaveConfig.

         @Range(min=0, max=3600)
         @Config(config=yes, reboot=no)
         @Save(semSaveConfig, value=2)
         @File(config.ini, type='ini')
        "
::= { semGbeInputUdpConfigGeneral 3 }

semGbeInUdpConfRedundForceToSecondary OBJECT-TYPE
    SYNTAX INTEGER
        {
         switchNotInProgress (1),
         forceSwitch         (2)
        }
    MAX-ACCESS read-write
    STATUS current
    DESCRIPTION
        "The Gigabit Ethernet Redundant Pair force switch any
         pair that is currently on the Primary to the Secondary.

         This will have no effect if the corresponding row setting of
         semGbeInUdpConfMptsRedundSelection is 'notApplicable'.

         This will only have an effect when the Primary is the In-Use
         UDP port of a Redundant Pair (semGbeStatInUdpState is 'openedInUse').

         Once written, the change to this parameter will take immediate effect.

         @Config(config=no, reboot=no)
        "
::= { semGbeInputUdpConfigGeneral 4 }

semGbeInUdpConfRedundForceToPrimary OBJECT-TYPE
    SYNTAX INTEGER
        {
         switchNotInProgress (1),
         forceSwitch         (2)
        }
    MAX-ACCESS read-write
    STATUS current
    DESCRIPTION
        "The Gigabit Ethernet Redundant Pair force switch any
         pair that is currently on the Secondary to the Primary.

         This will have no effect if the corresponding row setting of
         semGbeInUdpConfMptsRedundSelection is 'notApplicable'.

         This will only have an effect when the Secondary is the In-Use
         UDP port of a Redundant Pair (semGbeStatInUdpState is 'openedInUse').

         Once written, the change to this parameter will take immediate effect.

         @Config(config=no, reboot=no)
        "
::= { semGbeInputUdpConfigGeneral 5 }


-- ------------------------------------------------------------------------------
--
-- semGbeInputUdpConfigTable
--

semGbeInputUdpConfigTable OBJECT-TYPE
    SYNTAX SEQUENCE OF SemGbeInputUdpConfigEntry
    MAX-ACCESS not-accessible
    STATUS current
    DESCRIPTION
        "This table is the Input UDP Port configuration table for the Gigabit
         Ethernet Interface.  Alarming on Gigabit Ethernet Input UDP Ports can
         only occur if they are entered in this table.  This table contains 384
         rows.

         For configuring other Redundancy settings for a UDP port configured
         in this table, refer to the same row index in semGbeInputUdpConfigMptsRedundTable.

         For status of a UDP port configured in this table, refer to the same
         row index in semGbeStatusInputUdpTable.

         External SNMP managers should not write this table when semDeviceOperatingMode
         is 'isaSdv'.  The SEM writes to this table in this mode and the external
         SNMP manager should consider this table to be a read-only status table.

         Once written, the change to this table will only take immediate
         effect after semGbeInputUdpConfigApplyChange is set to 'apply'.
         However, in order for the change to persist through subsequent
         reboots or power cycles, the change must be saved via semSaveConfig.

         @Commit(param=semGbeInputUdpConfigApplyChange, value=2)
         @Config(config=yes, reboot=no)
         @Save(semSaveConfig, value=2)
         @File(config.ini, type='ini')
        "
::= { semGbeInputUdpConfig 2 }

semGbeInputUdpConfigEntry OBJECT-TYPE
    SYNTAX SemGbeInputUdpConfigEntry
    MAX-ACCESS not-accessible
    STATUS current
    DESCRIPTION
        "Gigabit Ethernet Interface Multicast Receive Configuration Table Entry."
    INDEX { semGbeInUdpConfIndex }
::= { semGbeInputUdpConfigTable 1 }

SemGbeInputUdpConfigEntry ::= SEQUENCE
    {
     semGbeInUdpConfIndex                   Integer32,
     semGbeInUdpConfGbePort                 Integer32,
     semGbeInUdpConfUdpPort                 Integer32,
     semGbeInUdpConfMulticastIpAddr         IpAddress,
     semGbeInUdpConfSourceIpAddr            IpAddress,
     semGbeInUdpConfLowAlarmBitRate         Integer32,
     semGbeInUdpConfRateCompareType         RateComparisonTYPE,
     semGbeInUdpConfMptsRedundSelection     RedundancySelectionTYPE,
     semGbeInUdpConfMptsRedundMcJoin        MulticastJoinTYPE,
     semGbeInUdpConfMptsRedundThreshold     Integer32,
     semGbeInUdpConfMptsRedundSuspend       SuspendTYPE
    }

semGbeInUdpConfIndex OBJECT-TYPE
    SYNTAX Integer32 (1..384)
    MAX-ACCESS not-accessible
    STATUS current
    DESCRIPTION
        "The Input UDP Port Configuration table index.
        "
::= { semGbeInputUdpConfigEntry 1 }

semGbeInUdpConfGbePort OBJECT-TYPE
    SYNTAX Integer32(0..3)
    MAX-ACCESS read-write
    STATUS current
    DESCRIPTION
        "The Gigabit Ethernet physical port on which to receive packets
         on semGbeInUdpConfUdpPort.
         Zero indicates this row of the table is not in use.

         Once written, the change to this table will only take immediate
         effect after semGbeInputUdpConfigApplyChange is set to 'apply'.
         However, in order for the change to persist through subsequent
         reboots or power cycles, the change must be saved via semSaveConfig.
        "
::= { semGbeInputUdpConfigEntry 2 }

semGbeInUdpConfUdpPort OBJECT-TYPE
    SYNTAX Integer32
    MAX-ACCESS read-write
    STATUS current
    DESCRIPTION
        "The Gigabit Ethernet Input UDP Port (range is 0 to 65535).

         This entry is dynamically configurable except when
         semGbeStatInUdpState is 'openedInUse'.

         Once written, the change to this table will only take immediate
         effect after semGbeInputUdpConfigApplyChange is set to 'apply'.
         However, in order for the change to persist through subsequent
         reboots or power cycles, the change must be saved via semSaveConfig.

         @Range(min=0, max=65535)
        "
::= { semGbeInputUdpConfigEntry 3 }

semGbeInUdpConfMulticastIpAddr OBJECT-TYPE
    SYNTAX IpAddress
    MAX-ACCESS read-write
    STATUS current
    DESCRIPTION
        "The Multicast receive IP address (224.0.0.0 to 224.0.0.255 is reserved).
         An IP address of 0.0.0.0 indicates table entry not in use.

         Once written, the change to this table will only take immediate
         effect after semGbeInputUdpConfigApplyChange is set to 'apply'.
         However, in order for the change to persist through subsequent
         reboots or power cycles, the change must be saved via semSaveConfig.
        "
::= { semGbeInputUdpConfigEntry 4 }

semGbeInUdpConfSourceIpAddr OBJECT-TYPE
    SYNTAX IpAddress
    MAX-ACCESS read-write
    STATUS current
    DESCRIPTION
        "This is the IP address of the source device.  If the router
         supports IGMP v3 the GBE will only receive data for this UDP
         port from this source IP.  If Source IP is not specified or
         the router does not support IGMP v3 the GBE will receive data
         from any source device.  Source IP address must be a valid
         singlecast address.

         Once written, the change to this table will only take immediate
         effect after semGbeInputUdpConfigApplyChange is set to 'apply'.
         However, in order for the change to persist through subsequent
         reboots or power cycles, the change must be saved via semSaveConfig.
        "
::= { semGbeInputUdpConfigEntry 5 }

semGbeInUdpConfLowAlarmBitRate OBJECT-TYPE
    SYNTAX Integer32
    MAX-ACCESS read-write
    STATUS current
    DESCRIPTION
        "This is the bit rate, in bits per second, below which the
         SEM will issue the semAlarmGbeInputStreamLowBitRate alarm.  The
         SEM will compare either the current Information rate or Stream
         rate as configured in semGbeInUdpConfRateCompareType.
         Setting to zero disables the bit rate alarming.

         The SEM updates the bit rate statistics every five seconds.

         Once written, the change to this table will only take immediate
         effect after semGbeInputUdpConfigApplyChange is set to 'apply'.
         However, in order for the change to persist through subsequent
         reboots or power cycles, the change must be saved via semSaveConfig.
        "
::= { semGbeInputUdpConfigEntry 6 }

semGbeInUdpConfRateCompareType OBJECT-TYPE
    SYNTAX RateComparisonTYPE
    MAX-ACCESS read-write
    STATUS current
    DESCRIPTION
        "This is the rate to use for alarming.  It is either Information
         rate or Stream rate.  This applies to monitoring for Bit Rate
         alarming and monitoring of Redundant Pairs.

         Once written, the change to this table will only take immediate
         effect after semGbeInputUdpConfigApplyChange is set to 'apply'.
         However, in order for the change to persist through subsequent
         reboots or power cycles, the change must be saved via semSaveConfig.
        "
::= { semGbeInputUdpConfigEntry 7 }

semGbeInUdpConfMptsRedundSelection OBJECT-TYPE
    SYNTAX RedundancySelectionTYPE
    MAX-ACCESS read-write
    STATUS current
    DESCRIPTION
        "This entry is used to establish Redundant Pairs.  The odd rows of the
         table (1, 3, 5, etc.) must be 'primary' or 'notApplicable'.  The even
         rows of the table (2, 4, 6, etc.) must be 'secondary' or 'notApplicable'.
         For a pair to be in MPTS Redundant mode the odd must be 'primary' and the
         even row must be 'secondary'.  If either row is 'notApplicable' the SEM
         will restore the row to previous valid values.  If this occurs at Bootup,
         there are no previous valid values, therefore the SEM will clear the rows.

         The SEM will ignore Redundancy Selection when the SEM is enabled for
         Interface Redundancy (when semGbeRedunModeEnabled is not set to 'disabled').

         Once written, the change to this table will only take immediate
         effect after semGbeInputUdpConfigApplyChange is set to 'apply'.
         However, in order for the change to persist through subsequent
         reboots or power cycles, the change must be saved via semSaveConfig.
        "
::= { semGbeInputUdpConfigEntry 8 }

semGbeInUdpConfMptsRedundMcJoin OBJECT-TYPE
    SYNTAX MulticastJoinTYPE
    MAX-ACCESS read-write
    STATUS current
    DESCRIPTION
        "This is not currently supported and is reserved for future use.
        "
::= { semGbeInputUdpConfigEntry 9 }

semGbeInUdpConfMptsRedundThreshold OBJECT-TYPE
    SYNTAX Integer32
    MAX-ACCESS read-write
    STATUS current
    DESCRIPTION
        "This applies to the Primary of a Redundant Pair only
         (semGbeInUdpConfMptsRedundSelection is 'primary').  It is the percent
         used to determine Fail Over from Primary to Secondary, and Switch Back
         from Secondary to Primary.  If a value of zero is specified, Fail Over
         or Switch Back will not occur.  Range is 0 to 100%.

         Primary Fail Over to Secondary:
         FailOver = (PrimaryRate) < (Threshold * SecondaryRate)
         The Primary must remain below the threshold for
         semGbeInUdpConfMptsRedundMonPeriod.  Fail Over will not occur when
         semGbeInUdpConfMptsRedundSuspend is set to 'suspended' for the Primary.

         Secondary Switch Back to Primary:
         SwitchBack = (PrimaryRate) >= (Threshold * SecondaryRate)
         The Primary must remain at or above the threshold for
         semGbeInUdpConfMptsRedundMonPeriod seconds.  The SEM will delay
         Switch Back an additional semGbeInUdpConfMptsRedundSwitchTime
         seconds.  Switch Back will not occur when
         semGbeInUdpConfMptsRedundSuspend is set to 'suspended' for the
         Secondary.

         Once written, the change to this table will only take immediate
         effect after semGbeInputUdpConfigApplyChange is set to 'apply'.
         However, in order for the change to persist through subsequent
         reboots or power cycles, the change must be saved via semSaveConfig.

         @Range(min=0, max=100)
        "
::= { semGbeInputUdpConfigEntry 10 }

semGbeInUdpConfMptsRedundSuspend OBJECT-TYPE
    SYNTAX SuspendTYPE
    MAX-ACCESS read-write
    STATUS current
    DESCRIPTION
        "This suspends Redundant Pair switching when set to 'suspended'.

         Fail Over from Primary to Secondary is suspended when
         semGbeInUdpConfMptsRedundSelection for this row is 'primary'.

         Switch Back from Secondary to Primary is suspended when
         semGbeInUdpConfMptsRedundSelection for this row is 'secondary'.

         This has no effect when semGbeInUdpConfMptsRedundSelection is
         'notApplicable'.

         Forced switching of Redundant Pairs via semGbeInUdpConfMptsRedundForceSwitch
         is prevented when this is set to 'suspended'.

         Once written, the change to this table will only take immediate
         effect after semGbeInputUdpConfigApplyChange is set to 'apply'.
         However, in order for the change to persist through subsequent
         reboots or power cycles, the change must be saved via semSaveConfig.
        "
::= { semGbeInputUdpConfigEntry 11 }


-- ------------------------------------------------------------------------------
--
-- semGbeInputUdpConfigMptsRedundTable
--

semGbeInputUdpConfigMptsRedundTable OBJECT-TYPE
    SYNTAX SEQUENCE OF SemGbeInputUdpConfigMptsRedundEntry
    MAX-ACCESS not-accessible
    STATUS current
    DESCRIPTION
        "This is the UDP Port Redundancy configuration table for the
         Gigabit Ethernet Interface.  A row in this table corresponds to
         the same index in the semGbeInputUdpConfigTable.  This table contains 384
         rows.
        "
::= { semGbeInputUdpConfig 3 }

semGbeInputUdpConfigMptsRedundEntry OBJECT-TYPE
    SYNTAX SemGbeInputUdpConfigMptsRedundEntry
    MAX-ACCESS not-accessible
    STATUS current
    DESCRIPTION
        "Gigabit Ethernet UDP Port Redundancy Configuration Table Entry."
    INDEX { semGbeInUdpConfMptsRedundIndex }
::= { semGbeInputUdpConfigMptsRedundTable 1 }

SemGbeInputUdpConfigMptsRedundEntry ::= SEQUENCE
    {
     semGbeInUdpConfMptsRedundIndex       Integer32,
     semGbeInUdpConfMptsRedundForceSwitch INTEGER
    }

semGbeInUdpConfMptsRedundIndex OBJECT-TYPE
    SYNTAX Integer32 (1..384)
    MAX-ACCESS not-accessible
    STATUS current
    DESCRIPTION
        "The Multicast Receive table index."
::= { semGbeInputUdpConfigMptsRedundEntry 1 }

semGbeInUdpConfMptsRedundForceSwitch OBJECT-TYPE
    SYNTAX INTEGER
        {
         switchNotInProgress (1),
         forceSwitch         (2)
        }
    MAX-ACCESS read-write
    STATUS current
    DESCRIPTION
        "The Gigabit Ethernet Redundant Pair force switch.

         This will have no effect if the corresponding row setting of
         semGbeInUdpConfMptsRedundSelection is 'notApplicable'.

         This will only have an effect when set for the In-Use UDP port of a
         Redundant Pair (semGbeStatInUdpState is 'openedInUse').

         The corresponding row setting semGbeInUdpConfMptsRedundSuspend is
         ignored when 'forceSwitch' is set.  The switch will occur even if
         semGbeInUdpConfMptsRedundSuspend is 'suspended'.

         When forced to the Secondary of the pair the SEM will stay on the
         Secondary until the user forces back to the Primary.  The SEM will
         not automatically switch back to the Primary when the Primary is
         restored above the failover threshold.

         The SEM will not allow a force to the Primary unless the Primary
         is above the failover threshold or the Primary failover is suspended
         (semGbeInUdpConfMptsRedundSuspend is 'suspended').

         Once written, the change to this parameter will take immediate effect.

         @Config(config=no, reboot=no)
        "
::= { semGbeInputUdpConfigMptsRedundEntry 2 }


-- ------------------------------------------------------------------------------
--
-- semGbeStatus
--
-- semGbeStatusGeneral
--

semGbeBootCodeVersion OBJECT-TYPE
    SYNTAX DisplayString
    MAX-ACCESS read-only
    STATUS current
    DESCRIPTION
        "SEM Gigabit Ethernet Processor Boot Code Version."
::= { semGbeStatusGeneral 1 }

semGbeApplicationCodeVersion OBJECT-TYPE
    SYNTAX DisplayString
    MAX-ACCESS read-only
    STATUS current
    DESCRIPTION
        "SEM Gigabit Ethernet Processor Application Code Version."
::= { semGbeStatusGeneral 2 }

semGbeRedunModeCurPortInUse OBJECT-TYPE
    SYNTAX Integer32
    MAX-ACCESS read-only
    STATUS current
    DESCRIPTION
        "SEM Gigabit Ethernet Redundant Mode current port in use.

         This entry applies to Gigabit Ethernet Interface Redundancy.
         "
::= { semGbeStatusGeneral 3 }

semGbePortsCount OBJECT-TYPE
    SYNTAX Integer32
    MAX-ACCESS read-only
    STATUS current
    DESCRIPTION
        "Number of Gigabit Ethernet ports installed on this SEM."
::= { semGbeStatusGeneral 4 }

semGbeMaxInputUdpPorts OBJECT-TYPE
    SYNTAX Integer32
    MAX-ACCESS read-only
    STATUS current
    DESCRIPTION
        "Maximum number of Gigabit Ethernet input UDP ports that can be
         opened on this SEM.  This is the maximum across all installed
         GigE ports.  One GigE port can use all UDP ports."
::= { semGbeStatusGeneral 5 }

semGbeCurrNumOpenInputUdpPorts OBJECT-TYPE
    SYNTAX Integer32
    MAX-ACCESS read-only
    STATUS current
    DESCRIPTION
        "Number of input UDP ports currently open."
::= { semGbeStatusGeneral 6 }

semGbeResetBufferLevelLimit OBJECT-TYPE
    SYNTAX Integer32
    MAX-ACCESS read-only
    STATUS current
    DESCRIPTION
        "The point at which the GigE frame buffer will be reset, in milliseconds.
         This value is equal to (maximum buffer depth - 5).  The maximum buffer depth is
         calculated based on the expected input data rate (semGbeMaxInputDataRate)."
::= { semGbeStatusGeneral 7 }

semGbeBufferCurrMsLevel OBJECT-TYPE
    SYNTAX Integer32
    MAX-ACCESS read-only
    STATUS current
    DESCRIPTION
        "Current highest Gigabit Ethernet Frame Buffer level in milliseconds."
::= { semGbeStatusGeneral 8 }

semGbeBufferCurrPercentFull OBJECT-TYPE
    SYNTAX Integer32
    MAX-ACCESS read-only
    STATUS current
    DESCRIPTION
        "Current highest Gigabit Ethernet Frame Buffer fullness as a percentage of
         the buffer depth available for a given aggregate rate.  This percentage is
         calculated using the current buffer level (semGbeBufferCurrMsLevel) and
         the actual input data rate."
::= { semGbeStatusGeneral 9 }

semGbeBufferOverflowLevel OBJECT-TYPE
    SYNTAX Integer32
    MAX-ACCESS read-only
    STATUS current
    DESCRIPTION
        "The point at which the GigE frame buffer will overflow, in milliseconds.
         This value is calculated based on the sum of the number of received frames per second
         for all interfaces."
::= { semGbeStatusGeneral 10 }

semGbeStatusNumOutputStreams OBJECT-TYPE
    SYNTAX Integer32
    MAX-ACCESS read-only
    STATUS current
    DESCRIPTION
        "The number of Gigabit Ethernet output streams configured."
::= { semGbeStatusGeneral 11 }


-- ------------------------------------------------------------------------------
--
-- semGbeStatusTable
--

semGbeStatusTable OBJECT-TYPE
    SYNTAX SEQUENCE OF SemGbeStatusEntry
    MAX-ACCESS not-accessible
    STATUS current
    DESCRIPTION
        "This is a table of status parameters for the
         Gigabit Ethernet Interface."
::= { semGbeStatus 2 }

semGbeStatusEntry OBJECT-TYPE
    SYNTAX SemGbeStatusEntry
    MAX-ACCESS not-accessible
    STATUS current
    DESCRIPTION
        "Gigabit Ethernet Interface Status Table Entry."
    INDEX { semGbeStatusPortNum }
::= { semGbeStatusTable 1 }

SemGbeStatusEntry ::= SEQUENCE
    {
     semGbeStatusPortNum         Integer32,
     semGbeStatusMacAddr         DisplayString,
     semGbeStatusLinkActive      ActiveTYPE,
     semGbeStatusIgmpVersion     INTEGER
    }

semGbeStatusPortNum OBJECT-TYPE
    SYNTAX Integer32(1..3)
    MAX-ACCESS not-accessible
    STATUS current
    DESCRIPTION
        "Gigabit Ethernet Port Number."
::= { semGbeStatusEntry 1 }

semGbeStatusMacAddr OBJECT-TYPE
    SYNTAX DisplayString (SIZE (0..17))
    MAX-ACCESS read-only
    STATUS current
    DESCRIPTION
        "This is the MAC address of the Gigabit Ethernet Interface.
         It is set at the factory and cannot be changed.
         The string length is 17 characters in the format
         'hh:hh:hh:hh:hh:hh' where 'hh' is a hexadecimal number."
::= { semGbeStatusEntry 2 }

semGbeStatusLinkActive OBJECT-TYPE
    SYNTAX ActiveTYPE
    MAX-ACCESS read-only
    STATUS current
    DESCRIPTION
        "This indicates if the Gigabit Ethernet optical link is active."
::= { semGbeStatusEntry 3 }

semGbeStatusIgmpVersion OBJECT-TYPE
    SYNTAX INTEGER
        {
         igmpV1 (1),
         igmpV2 (2),
         igmpV3 (3)
        }
    MAX-ACCESS read-only
    STATUS current
    DESCRIPTION
        "This indicates the IGMP Version being used on this interface."
::= { semGbeStatusEntry 4 }


-- ------------------------------------------------------------------------------
--
-- semGbeStatusOutTransStreamTable - obsolete
--

semGbeStatusOutTransStreamTable OBJECT-TYPE
    SYNTAX SEQUENCE OF SemGbeStatusOutTransStreamEntry
    MAX-ACCESS not-accessible
    STATUS current
    DESCRIPTION
        "This is a table of Output Transport Streams to which each of the
         Gigabit Ethernet Interface ports are assigned.

         This object is obsolete."
::= { semGbeStatus 3 }

semGbeStatusOutTransStreamEntry OBJECT-TYPE
    SYNTAX SemGbeStatusOutTransStreamEntry
    MAX-ACCESS not-accessible
    STATUS current
    DESCRIPTION
        "Gigabit Ethernet Interface Status Table Entry.

         This object is obsolete."
    INDEX { semGbeStatusOutTransStreamPortNum, semGbeStatusOutTransStreamIndex }
::= { semGbeStatusOutTransStreamTable 1 }

SemGbeStatusOutTransStreamEntry ::= SEQUENCE
    {
     semGbeStatusOutTransStreamPortNum         Integer32,
     semGbeStatusOutTransStreamIndex           Integer32,
     semGbeStatusOutTransStreamNum             Integer32
    }

semGbeStatusOutTransStreamPortNum OBJECT-TYPE
    SYNTAX Integer32(1..3)
    MAX-ACCESS not-accessible
    STATUS current
    DESCRIPTION
        "Gigabit Ethernet Port Number.

         This object is obsolete."
::= { semGbeStatusOutTransStreamEntry 1 }

semGbeStatusOutTransStreamIndex OBJECT-TYPE
    SYNTAX Integer32 (1..16)
    MAX-ACCESS not-accessible
    STATUS current
    DESCRIPTION
        "The Output Transport Stream Index.  This does not correspond
         to a number in the Output Transport Stream Table.

         This object is obsolete."
::= { semGbeStatusOutTransStreamEntry 2 }

semGbeStatusOutTransStreamNum OBJECT-TYPE
    SYNTAX Integer32 (0..16)
    MAX-ACCESS read-only
    STATUS current
    DESCRIPTION
        "The number of the output transport stream routed to this output.
         Zero indicates that no stream is routed to this port.
         It serves as the index into the Transport Stream Configuration Table.
         This parameter is only applicable to Gigabit Ethernet Interface ports
         configured as output.

         This object is obsolete."
::= { semGbeStatusOutTransStreamEntry 3 }


-- ------------------------------------------------------------------------------
--
-- semGbeStatusPacketCounterTable - obsolete
--

semGbeStatusPacketCounterTable OBJECT-TYPE
    SYNTAX SEQUENCE OF SemGbeStatusPacketCounterEntry
    MAX-ACCESS not-accessible
    STATUS obsolete
    DESCRIPTION
        "Table of Gigabit Ethernet Packet Counter Statistics.

         This object is obsolete."
::= { semGbeStatus 4 }

semGbeStatusPacketCounterEntry OBJECT-TYPE
    SYNTAX SemGbeStatusPacketCounterEntry
    MAX-ACCESS not-accessible
    STATUS obsolete
    DESCRIPTION
        "Gigabit Ethernet Interface Packet Counter Table Entry.

         This object is obsolete."
    INDEX { semGbePacketCounterIndex }
::= { semGbeStatusPacketCounterTable 1 }

SemGbeStatusPacketCounterEntry ::= SEQUENCE
    {
     semGbePacketCounterIndex            Integer32,
     semGbePacketCounterResetTotals      ResetStatisticsTYPE,
     semGbeTotalRxSinglecastPackets      Counter32,
     semGbeTotalRxBroadcastPackets       Counter32,
     semGbeTotalTxPackets                Counter32,
     semGbeTotalCollisions               Counter32,
     semGbeTotalRuntJumboFrames          Counter32,
     semGbeTotalPacketsInError           Counter32,
     semGbeCurrentNumOpenInputUdpPorts   Counter32,
     semGbeRxSinglecastPackets           Counter32,
     semGbeRxBroadcastPackets            Counter32,
     semGbeTxPackets                     Counter32,
     semGbeCollisions                    Counter32,
     semGbeRuntJumboFrames               Counter32,
     semGbePacketsInError                Counter32
    }

semGbePacketCounterIndex OBJECT-TYPE
    SYNTAX Integer32 (1)
    MAX-ACCESS not-accessible
    STATUS obsolete
    DESCRIPTION
        "The index of the Gigabit Ethernet Packet Counter Table.
         Currently limited to 1.

         This object is obsolete."
::= { semGbeStatusPacketCounterEntry 1 }

semGbePacketCounterResetTotals OBJECT-TYPE
    SYNTAX ResetStatisticsTYPE
    MAX-ACCESS read-write
    STATUS obsolete
    DESCRIPTION
        "Reset Packet Counter Statistics totals:
            - semGbeTotalRxSinglecastPackets
            - semGbeTotalRxBroadcastPackets
            - semGbeTotalTxPackets
            - semGbeTotalCollisions
            - semGbeTotalRuntJumboFrames
            - semGbeTotalPacketsInError

         This object is obsolete."
::= { semGbeStatusPacketCounterEntry 2 }

semGbeTotalRxSinglecastPackets OBJECT-TYPE
    SYNTAX Counter32
    MAX-ACCESS read-only
    STATUS obsolete
    DESCRIPTION
        "Total number of singlecast packets received since last reset.
         Reset using semGbePacketCounterResetTotals.

        This object is obsolete."
::= { semGbeStatusPacketCounterEntry 3 }

semGbeTotalRxBroadcastPackets OBJECT-TYPE
    SYNTAX Counter32
    MAX-ACCESS read-only
    STATUS obsolete
    DESCRIPTION
        "Total number of broadcast packets received since last reset.
         Reset using semGbePacketCounterResetTotals.

        This object is obsolete."
::= { semGbeStatusPacketCounterEntry 4 }

semGbeTotalTxPackets OBJECT-TYPE
    SYNTAX Counter32
    MAX-ACCESS read-only
    STATUS obsolete
    DESCRIPTION
        "Total number of packets transmitted since last reset.
         Reset using semGbePacketCounterResetTotals.

        This object is obsolete."
::= { semGbeStatusPacketCounterEntry 5 }

semGbeTotalCollisions OBJECT-TYPE
    SYNTAX Counter32
    MAX-ACCESS read-only
    STATUS obsolete
    DESCRIPTION
        "Total number of collisions detected since last reset.
         Reset using semGbePacketCounterResetTotals.
         This object is obsolete."
::= { semGbeStatusPacketCounterEntry 6 }

semGbeTotalRuntJumboFrames OBJECT-TYPE
    SYNTAX Counter32
    MAX-ACCESS read-only
    STATUS obsolete
    DESCRIPTION
        "Total number of runt and jumbo frames detected since last reset.
         Reset using semGbePacketCounterResetTotals.

         This object is obsolete."
::= { semGbeStatusPacketCounterEntry 7 }

semGbeTotalPacketsInError OBJECT-TYPE
    SYNTAX Counter32
    MAX-ACCESS read-only
    STATUS obsolete
    DESCRIPTION
        "Total number of packets in error detected since last reset.
         Reset using semGbePacketCounterResetTotals.

         This object is obsolete."
::= { semGbeStatusPacketCounterEntry 8 }

semGbeCurrentNumOpenInputUdpPorts OBJECT-TYPE
    SYNTAX Counter32
    MAX-ACCESS read-only
    STATUS obsolete
    DESCRIPTION
        "Number of input UDP ports currently open.

         This object is obsolete."
::= { semGbeStatusPacketCounterEntry 9 }

semGbeRxSinglecastPackets OBJECT-TYPE
    SYNTAX Counter32
    MAX-ACCESS read-only
    STATUS obsolete
    DESCRIPTION
        "Number of singlecast packets received during
         last status checking interval.
         Status checking interval is five seconds.

         This object is obsolete."
::= { semGbeStatusPacketCounterEntry 10 }

semGbeRxBroadcastPackets OBJECT-TYPE
    SYNTAX Counter32
    MAX-ACCESS read-only
    STATUS obsolete
    DESCRIPTION
        "Number of broadcast packets received during last
         status checking interval.
         Status checking interval is five seconds.

         This object is obsolete."
::= { semGbeStatusPacketCounterEntry 11 }

semGbeTxPackets OBJECT-TYPE
    SYNTAX Counter32
    MAX-ACCESS read-only
    STATUS obsolete
    DESCRIPTION
        "Number of singlecast packets transmitted during
         last status checking interval.
         Status checking interval is five seconds.

         This object is obsolete."
::= { semGbeStatusPacketCounterEntry 12 }

semGbeCollisions OBJECT-TYPE
    SYNTAX Counter32
    MAX-ACCESS read-only
    STATUS obsolete
    DESCRIPTION
        "Number of collisions detected during last status
         checking interval.
         Status checking interval is five seconds.

         This object is obsolete."
::= { semGbeStatusPacketCounterEntry 13 }

semGbeRuntJumboFrames OBJECT-TYPE
    SYNTAX Counter32
    MAX-ACCESS read-only
    STATUS obsolete
    DESCRIPTION
        "Number of runt and jumbo frames detected during
         last status checking interval.
         Status checking interval is five seconds.

         This object is obsolete."
::= { semGbeStatusPacketCounterEntry 14 }

semGbePacketsInError OBJECT-TYPE
    SYNTAX Counter32
    MAX-ACCESS read-only
    STATUS obsolete
    DESCRIPTION
        "Number of packets in error detected during last
         status checking interval.
         Status checking interval is five seconds.

         This object is obsolete."
::= { semGbeStatusPacketCounterEntry 15 }


-- ------------------------------------------------------------------------------
--
-- semGbeStatusRoutingTable
--

semGbeStatusRoutingTable OBJECT-TYPE
    SYNTAX SEQUENCE OF SemGbeStatusRoutingEntry
    MAX-ACCESS not-accessible
    STATUS current
    DESCRIPTION
        "This table is the Routing Table that is currently active for the
         Gigabit Ethernet Interface."
::= { semGbeStatus 5 }

semGbeStatusRoutingEntry OBJECT-TYPE
    SYNTAX SemGbeStatusRoutingEntry
    MAX-ACCESS not-accessible
    STATUS current
    DESCRIPTION
        "Gigabit Ethernet Interface Routing Table Entry."
    INDEX { semGbeStatusRoutingIndex }
::= { semGbeStatusRoutingTable 1 }

SemGbeStatusRoutingEntry ::= SEQUENCE
    {
     semGbeStatusRoutingIndex           Integer32,
     semGbeStatusRoutingDestIpAddr      IpAddress,
     semGbeStatusRoutingGateIpAddr      IpAddress,
     semGbeStatusRoutingSubnetMask      IpAddress,
     semGbeStatusRoutingGbePort         Integer32,
     semGbeStatusRoutingFlags           INTEGER
    }

semGbeStatusRoutingIndex OBJECT-TYPE
    SYNTAX Integer32
    MAX-ACCESS not-accessible
    STATUS current
    DESCRIPTION
        "The index of the Gigabit Ethernet Routing Table.
         Currently limited to 24."
::= { semGbeStatusRoutingEntry 1 }

semGbeStatusRoutingDestIpAddr OBJECT-TYPE
    SYNTAX IpAddress
    MAX-ACCESS read-only
    STATUS current
    DESCRIPTION
        "The Gigabit Ethernet Routing Destination IP address."
::= { semGbeStatusRoutingEntry 2 }

semGbeStatusRoutingGateIpAddr OBJECT-TYPE
    SYNTAX IpAddress
    MAX-ACCESS read-only
    STATUS current
    DESCRIPTION
        "The Gigabit Ethernet Routing Gateway IP address."
::= { semGbeStatusRoutingEntry 3 }

semGbeStatusRoutingSubnetMask OBJECT-TYPE
    SYNTAX IpAddress
    MAX-ACCESS read-only
    STATUS current
    DESCRIPTION
        "The Gigabit Ethernet Routing Subnet Mask."
::= { semGbeStatusRoutingEntry 4 }

semGbeStatusRoutingGbePort OBJECT-TYPE
    SYNTAX Integer32
    MAX-ACCESS read-only
    STATUS current
    DESCRIPTION
        "The Physical Gigabit Ethernet port to which this route applies."
::= { semGbeStatusRoutingEntry 5 }

semGbeStatusRoutingFlags OBJECT-TYPE
    SYNTAX INTEGER
        {
         notApplicable        (1),
         networkRoute         (2),
         hostRoute            (3),
         defaultRoute         (4),
         interfaceRoute       (5)
        }
    MAX-ACCESS read-only
    STATUS current
    DESCRIPTION
        "The Gigabit Ethernet routing flags."
::= { semGbeStatusRoutingEntry 6 }


-- ------------------------------------------------------------------------------
--
-- semGbeStatusArpTable
--

semGbeStatusArpTable OBJECT-TYPE
    SYNTAX SEQUENCE OF SemGbeStatusArpEntry
    MAX-ACCESS not-accessible
    STATUS current
    DESCRIPTION
        "This table is the ARP Table that is currently active for the
         Gigabit Ethernet Interface.  Entries may be deleted by
         utilizing the semGbeDeleteArpTable for any entry and the
         semGbeDynamicArpFlush for removing all dynamic entries at
         one time."
::= { semGbeStatus 6 }

semGbeStatusArpEntry OBJECT-TYPE
    SYNTAX SemGbeStatusArpEntry
    MAX-ACCESS not-accessible
    STATUS current
    DESCRIPTION
        "Gigabit Ethernet Interface Status ARP Table Entry."
    INDEX { semGbeStatusArpIndex }
::= { semGbeStatusArpTable 1 }

SemGbeStatusArpEntry ::= SEQUENCE
    {
     semGbeStatusArpIndex           Integer32,
     semGbeStatusArpIpAddr          IpAddress,
     semGbeStatusArpMacAddr         DisplayString,
     semGbeStatusArpGbePort         Integer32,
     semGbeStatusArpFlags           INTEGER
    }

semGbeStatusArpIndex OBJECT-TYPE
    SYNTAX Integer32
    MAX-ACCESS not-accessible
    STATUS current
    DESCRIPTION
        "The index of the Gigabit Ethernet ARP Table.
         Currently limited to 128."
::= { semGbeStatusArpEntry 1 }

semGbeStatusArpIpAddr OBJECT-TYPE
    SYNTAX IpAddress
    MAX-ACCESS read-only
    STATUS current
    DESCRIPTION
        "The Gigabit Ethernet ARP IP address."
::= { semGbeStatusArpEntry 2 }

semGbeStatusArpMacAddr OBJECT-TYPE
    SYNTAX DisplayString (SIZE (0..17))
    MAX-ACCESS read-only
    STATUS current
    DESCRIPTION
        "This is the MAC address of the Gigabit Ethernet ARP.
         The string length is 17 characters in the format
         'hh:hh:hh:hh:hh:hh' where 'hh' is a hexadecimal number."
::= { semGbeStatusArpEntry 3 }

semGbeStatusArpGbePort OBJECT-TYPE
    SYNTAX Integer32
    MAX-ACCESS read-only
    STATUS current
    DESCRIPTION
        "The Physical Gigabit Ethernet port to which this ARP applies.
         Zero indicates this field is not applicable to the ARP."
::= { semGbeStatusArpEntry 4 }

semGbeStatusArpFlags OBJECT-TYPE
    SYNTAX INTEGER
        {
         notApplicable        (1),
         arping               (2),
         arpDone              (3),
         arpStatic            (4)
        }
    MAX-ACCESS read-only
    STATUS current
    DESCRIPTION
        "The Gigabit Ethernet ARP flags."
::= { semGbeStatusArpEntry 5 }


-- ------------------------------------------------------------------------------
--
-- semGbeStatusLoopTerminatorTable
--

semGbeStatusLoopTerminatorTable OBJECT-TYPE
    SYNTAX SEQUENCE OF SemGbeStatusLoopTerminatorEntry
    MAX-ACCESS not-accessible
    STATUS current
    DESCRIPTION
        "This table contains the data for devices in Loop
         Through mode that are daisy chained to this SEM.
         This table is only populated for a SEM Gbe interface
         configured in Loop Through Terminator mode via
         semGbeConfigEnable."
::= { semGbeStatus 7 }

semGbeStatusLoopTerminatorEntry OBJECT-TYPE
    SYNTAX SemGbeStatusLoopTerminatorEntry
    MAX-ACCESS not-accessible
    STATUS current
    DESCRIPTION
        "Gigabit Ethernet Interface Status Loop Through Terminator
         Table Entry."
    INDEX { semGbeStatusLoopTerminatorPortNum, semGbeStatusLoopTerminatorIndex }
::= { semGbeStatusLoopTerminatorTable 1 }

SemGbeStatusLoopTerminatorEntry ::= SEQUENCE
    {
     semGbeStatusLoopTerminatorPortNum    Integer32,
     semGbeStatusLoopTerminatorIndex      Integer32,
     semGbeStatusLoopTerminatorMacAddr    DisplayString
    }

semGbeStatusLoopTerminatorPortNum OBJECT-TYPE
    SYNTAX Integer32(1..2)
    MAX-ACCESS not-accessible
    STATUS current
    DESCRIPTION
        "Gigabit Ethernet Port Number.  Can only be 1 or 2."
::= { semGbeStatusLoopTerminatorEntry 1 }

semGbeStatusLoopTerminatorIndex OBJECT-TYPE
    SYNTAX Integer32
    MAX-ACCESS not-accessible
    STATUS current
    DESCRIPTION
        "The index of the Gigabit Ethernet Loop Through Terminator
         Status Table.  Currently limited to 16."
::= { semGbeStatusLoopTerminatorEntry 2 }

semGbeStatusLoopTerminatorMacAddr OBJECT-TYPE
    SYNTAX DisplayString (SIZE (0..17))
    MAX-ACCESS read-only
    STATUS current
    DESCRIPTION
        "This is the MAC address of a device configured in Loop Through
         mode and daisy chained to this SEM.
         The string length is 17 characters in the format
         'hh:hh:hh:hh:hh:hh' where 'hh' is a hexadecimal number."
::= { semGbeStatusLoopTerminatorEntry 3 }


-- ------------------------------------------------------------------------------
--
-- semGbeStatusOutputPacketTable
--

semGbeStatusOutputPacketTable OBJECT-TYPE
    SYNTAX SEQUENCE OF SemGbeStatusOutputPacketEntry
    MAX-ACCESS not-accessible
    STATUS current
    DESCRIPTION
        "This table contains Gigabit Ethernet Output Packet counts for
         each Output Transport Stream of this SEM."
::= { semGbeStatus 8 }

semGbeStatusOutputPacketEntry OBJECT-TYPE
    SYNTAX SemGbeStatusOutputPacketEntry
    MAX-ACCESS not-accessible
    STATUS current
    DESCRIPTION
        "Gigabit Ethernet Interface Status Output Packet
         Table Entry."
    INDEX { semGbeStatusOutputPacketIndex }
::= { semGbeStatusOutputPacketTable 1 }

SemGbeStatusOutputPacketEntry ::= SEQUENCE
    {
     semGbeStatusOutputPacketIndex      Integer32,
     semGbeStatusTotOutputPackets       Counter32,
     semGbeStatusNumOutputPackets       Counter32
    }

semGbeStatusOutputPacketIndex OBJECT-TYPE
    SYNTAX Integer32
    MAX-ACCESS not-accessible
    STATUS current
    DESCRIPTION
        "The index of the Gigabit Ethernet Output Packet
         Status Table.  Represents Output Transport Stream
         number.  Currently limited to 16."
::= { semGbeStatusOutputPacketEntry 1 }

semGbeStatusTotOutputPackets OBJECT-TYPE
    SYNTAX Counter32
    MAX-ACCESS read-only
    STATUS current
    DESCRIPTION
        "Total number of Gigabit Ethernet packets placed on this
         Output Transport Stream."
::= { semGbeStatusOutputPacketEntry 2 }

semGbeStatusNumOutputPackets OBJECT-TYPE
    SYNTAX Counter32
    MAX-ACCESS read-only
    STATUS current
    DESCRIPTION
        "Number of Gigabit Ethernet packets placed on this Output
         Transport Stream during the last monitoring period
         (currently 5 seconds)."
::= { semGbeStatusOutputPacketEntry 3 }


-- ------------------------------------------------------------------------------
--
-- semGbeStatusFrameCounterTableResetAll
--

semGbeStatusFrameCounterTableResetAll OBJECT-TYPE
    SYNTAX ResetStatisticsTYPE
    MAX-ACCESS read-write
    STATUS current
    DESCRIPTION
        "Reset Frame Counter Totals for all GigE ports:
            - semGbeTotalRxSinglecastFrames
            - semGbeTotalRxMulticastFrames
            - semGbeTotalRxBroadcastFrames
            - semGbeTotalRxErrorFrames
            - semGbeTotalRxFrames
            - semGbeTotalTxGoodFrames
            - semGbeTotalTxErrorFrames
            - semGbeTotalTxFrames

         Once written, the change to this parameter will take immediate effect.

         @Config(config=no, reboot=no)
        "
::= { semGbeStatus 9 }


-- ------------------------------------------------------------------------------
--
-- semGbeStatusFrameCounterTable
--

semGbeStatusFrameCounterTable OBJECT-TYPE
    SYNTAX SEQUENCE OF SemGbeStatusFrameCounterEntry
    MAX-ACCESS not-accessible
    STATUS current
    DESCRIPTION
        "Table of Gigabit Ethernet Frame Counter Statistics."
::= { semGbeStatus 10 }

semGbeStatusFrameCounterEntry OBJECT-TYPE
    SYNTAX SemGbeStatusFrameCounterEntry
    MAX-ACCESS not-accessible
    STATUS current
    DESCRIPTION
        "Gigabit Ethernet Interface Frame Counter Table Entry."
    INDEX { semGbeFrameCounterPortNum }
::= { semGbeStatusFrameCounterTable 1 }

SemGbeStatusFrameCounterEntry ::= SEQUENCE
    {
     semGbeFrameCounterPortNum           Integer32,
     semGbeFrameCounterReset             ResetStatisticsTYPE,
     semGbeTotalRxSinglecastFrames       Counter32,
     semGbeTotalRxMulticastFrames        Counter32,
     semGbeTotalRxBroadcastFrames        Counter32,
     semGbeTotalRxErrorFrames            Counter32,
     semGbeTotalRxFrames                 Counter32,
     semGbeTotalTxGoodFrames             Counter32,
     semGbeTotalTxErrorFrames            Counter32,
     semGbeTotalTxFrames                 Counter32,
     semGbeRxSinglecastFrames            Counter32,
     semGbeRxMulticastFrames             Counter32,
     semGbeRxBroadcastFrames             Counter32,
     semGbeRxErrorFrames                 Counter32,
     semGbeRxFrames                      Counter32,
     semGbeTxGoodFrames                  Counter32,
     semGbeTxErrorFrames                 Counter32,
     semGbeTxFrames                      Counter32
    }

semGbeFrameCounterPortNum OBJECT-TYPE
    SYNTAX Integer32
    MAX-ACCESS not-accessible
    STATUS current
    DESCRIPTION
        "The index of the Gigabit Ethernet Frame Counter Table.
         Represents the Gigabit Ethernet port number."
::= { semGbeStatusFrameCounterEntry 1 }

semGbeFrameCounterReset OBJECT-TYPE
    SYNTAX ResetStatisticsTYPE
    MAX-ACCESS read-write
    STATUS current
    DESCRIPTION
        "Reset Frame Counter Statistics totals for a single GigE port:
            - semGbeTotalRxSinglecastFrames
            - semGbeTotalRxMulticastFrames
            - semGbeTotalRxBroadcastFrames
            - semGbeTotalRxErrorFrames
            - semGbeTotalRxFrames
            - semGbeTotalTxGoodFrames
            - semGbeTotalTxErrorFrames
            - semGbeTotalTxFrames

         Once written, the change to this parameter will take immediate effect.

         @Config(config=no, reboot=no)
        "
::= { semGbeStatusFrameCounterEntry 2 }

semGbeTotalRxSinglecastFrames OBJECT-TYPE
    SYNTAX Counter32
    MAX-ACCESS read-only
    STATUS current
    DESCRIPTION
        "Total number of singlecast frames received since last reset.
         Reset using semGbeStatusFrameCounterTableResetAll or semGbeFrameCounterReset."
::= { semGbeStatusFrameCounterEntry 3 }

semGbeTotalRxMulticastFrames OBJECT-TYPE
    SYNTAX Counter32
    MAX-ACCESS read-only
    STATUS current
    DESCRIPTION
        "Total number of multicast frames received since last reset.
         Reset using semGbeStatusFrameCounterTableResetAll or semGbeFrameCounterReset."
::= { semGbeStatusFrameCounterEntry 4 }

semGbeTotalRxBroadcastFrames OBJECT-TYPE
    SYNTAX Counter32
    MAX-ACCESS read-only
    STATUS current
    DESCRIPTION
        "Total number of broadcast frames received since last reset.
         Reset using semGbeStatusFrameCounterTableResetAll or semGbeFrameCounterReset."
::= { semGbeStatusFrameCounterEntry 5 }

semGbeTotalRxErrorFrames OBJECT-TYPE
    SYNTAX Counter32
    MAX-ACCESS read-only
    STATUS current
    DESCRIPTION
        "Total number of bad frames received since last reset.
         Reset using semGbeStatusFrameCounterTableResetAll or semGbeFrameCounterReset."
::= { semGbeStatusFrameCounterEntry 6 }

semGbeTotalRxFrames OBJECT-TYPE
    SYNTAX Counter32
    MAX-ACCESS read-only
    STATUS current
    DESCRIPTION
        "Total number of frames received since last reset.
         This is the sum of semGbeTotalRxSinglecastFrames, semGbeTotalRxMulticastFrames,
         semGbeTotalRxBroadcastFrames, and semGbeTotalRxErrorFrames.
         Reset using semGbeStatusFrameCounterTableResetAll or semGbeFrameCounterReset."
::= { semGbeStatusFrameCounterEntry 7 }

semGbeTotalTxGoodFrames OBJECT-TYPE
    SYNTAX Counter32
    MAX-ACCESS read-only
    STATUS current
    DESCRIPTION
        "Total number of good frames (singlecast, multicast, and broadcast) transmitted since last reset.
         Reset using semGbeStatusFrameCounterTableResetAll or semGbeFrameCounterReset."
::= { semGbeStatusFrameCounterEntry 8 }

semGbeTotalTxErrorFrames OBJECT-TYPE
    SYNTAX Counter32
    MAX-ACCESS read-only
    STATUS current
    DESCRIPTION
        "Total number of bad frames transmitted since last reset.
         Reset using semGbeStatusFrameCounterTableResetAll or semGbeFrameCounterReset."
::= { semGbeStatusFrameCounterEntry 9 }

semGbeTotalTxFrames OBJECT-TYPE
    SYNTAX Counter32
    MAX-ACCESS read-only
    STATUS current
    DESCRIPTION
        "Total number of frames transmitted since last reset.
         This is the sum of semGbeTotalTxGoodFrames and semGbeTotalTxErrorFrames.
         Reset using semGbeStatusFrameCounterTableResetAll or semGbeFrameCounterReset."
::= { semGbeStatusFrameCounterEntry 10 }

semGbeRxSinglecastFrames OBJECT-TYPE
    SYNTAX Counter32
    MAX-ACCESS read-only
    STATUS current
    DESCRIPTION
        "Number of singlecast frames received during last
         status checking interval.
         Status checking interval is five seconds."
::= { semGbeStatusFrameCounterEntry 11 }

semGbeRxMulticastFrames OBJECT-TYPE
    SYNTAX Counter32
    MAX-ACCESS read-only
    STATUS current
    DESCRIPTION
        "Number of multicast frames received during
         last status checking interval.
         Status checking interval is five seconds."
::= { semGbeStatusFrameCounterEntry 12 }

semGbeRxBroadcastFrames OBJECT-TYPE
    SYNTAX Counter32
    MAX-ACCESS read-only
    STATUS current
    DESCRIPTION
        "Number of broadcast frames received during last status
         checking interval.
         Status checking interval is five seconds."
::= { semGbeStatusFrameCounterEntry 13 }

semGbeRxErrorFrames OBJECT-TYPE
    SYNTAX Counter32
    MAX-ACCESS read-only
    STATUS current
    DESCRIPTION
        "Number of bad frames received during
         last status checking interval.
         Status checking interval is five seconds."
::= { semGbeStatusFrameCounterEntry 14 }

semGbeRxFrames OBJECT-TYPE
    SYNTAX Counter32
    MAX-ACCESS read-only
    STATUS current
    DESCRIPTION
        "Number of frames received during last
         status checking interval.
         This is the sum of semGbeRxSinglecastFrames, semGbeRxMulticastFrames,
         semGbeRxBroadcastFrames, and semGbeRxErrorFrames.
         Status checking interval is five seconds."
::= { semGbeStatusFrameCounterEntry 15 }

semGbeTxGoodFrames OBJECT-TYPE
    SYNTAX Counter32
    MAX-ACCESS read-only
    STATUS current
    DESCRIPTION
        "Number of good frames (singlecast, multicast, and broadcast) transmitted during last
         status checking interval.
         Status checking interval is five seconds."
::= { semGbeStatusFrameCounterEntry 16 }

semGbeTxErrorFrames OBJECT-TYPE
    SYNTAX Counter32
    MAX-ACCESS read-only
    STATUS current
    DESCRIPTION
        "Number of bad frames transmitted during last
         status checking interval.
         Status checking interval is five seconds."
::= { semGbeStatusFrameCounterEntry 17 }

semGbeTxFrames OBJECT-TYPE
    SYNTAX Counter32
    MAX-ACCESS read-only
    STATUS current
    DESCRIPTION
        "Number of frames transmitted during last status checking interval.
         This is the sum of semGbeTxErrorFrames and semGbeTxFrames.
         Status checking interval is five seconds."
::= { semGbeStatusFrameCounterEntry 18 }


-- ------------------------------------------------------------------------------
--
-- semGbeStatusFrameBufferTable
--

semGbeStatusFrameBufferTable OBJECT-TYPE
    SYNTAX SEQUENCE OF SemGbeStatusFrameBufferEntry
    MAX-ACCESS not-accessible
    STATUS current
    DESCRIPTION
        "Table of Gigabit Ethernet Frame Buffer Statistics.  There can be up
         to 24 entries in the table.  Each entry represents one hour.  The newest
         entry is placed at the beginning of the table and, if necessary, the oldest
         entry is pushed off the end of the table.  The table will not be full until
         24 hours have passed."
::= { semGbeStatus 11 }

semGbeStatusFrameBufferEntry OBJECT-TYPE
    SYNTAX SemGbeStatusFrameBufferEntry
    MAX-ACCESS not-accessible
    STATUS current
    DESCRIPTION
        "Gigabit Ethernet Interface Frame Buffer Table Entry."
    INDEX { semGbeStatusFrameBufferIndex }
::= { semGbeStatusFrameBufferTable 1 }

SemGbeStatusFrameBufferEntry ::= SEQUENCE
    {
     semGbeStatusFrameBufferIndex           Integer32,
     semGbeStatusFrameBufferInterface       Integer32,
     semGbeStatusFrameBufferUdpPort         Integer32,
     semGbeStatusFrameBufferMaxMsLevel      Integer32,
     semGbeStatusFrameBufferMaxPercentFull  Integer32,
     semGbeStatusFrameBufferGpsTime         Integer32,
     semGbeStatusFrameBufferOverflows       Integer32,
     semGbeStatusFrameBufferResets          Integer32
    }

semGbeStatusFrameBufferIndex OBJECT-TYPE
    SYNTAX Integer32
    MAX-ACCESS not-accessible
    STATUS current
    DESCRIPTION
        "The index of the Gigabit Ethernet Buffer Status Table.  Each index
         represents one hour.  There can be up to 24 entries in the table.
         The most recent entry is always at the beginning of the table."
::= { semGbeStatusFrameBufferEntry 1 }

semGbeStatusFrameBufferInterface OBJECT-TYPE
    SYNTAX Integer32
    MAX-ACCESS read-only
    STATUS current
    DESCRIPTION
        "The Gigabit Ethernet interface that experienced the highest buffer level for the hour."
::= { semGbeStatusFrameBufferEntry 2 }

semGbeStatusFrameBufferUdpPort OBJECT-TYPE
    SYNTAX Integer32
    MAX-ACCESS read-only
    STATUS current
    DESCRIPTION
        "The UDP port on semGbeStatusFrameBufferInterface that experienced the highest gigabit Ethernet frame
         buffer level for the hour."
::= { semGbeStatusFrameBufferEntry 3 }

semGbeStatusFrameBufferMaxMsLevel OBJECT-TYPE
    SYNTAX Integer32
    MAX-ACCESS read-only
    STATUS current
    DESCRIPTION
        "The maximum Gigabit Ethernet frame buffer level (in milliseconds) recorded for the hour."
::= { semGbeStatusFrameBufferEntry 4 }

semGbeStatusFrameBufferMaxPercentFull OBJECT-TYPE
    SYNTAX Integer32
    MAX-ACCESS read-only
    STATUS current
    DESCRIPTION
        "The maximum Gigabit Ethernet frame buffer level percentage recorded for the hour."
::= { semGbeStatusFrameBufferEntry 5 }

semGbeStatusFrameBufferGpsTime OBJECT-TYPE
    SYNTAX Integer32
    MAX-ACCESS read-only
    STATUS current
    DESCRIPTION
        "The GPS time when the maximum Gigabit Ethernet frame buffer level was reached."
::= { semGbeStatusFrameBufferEntry 6 }

semGbeStatusFrameBufferOverflows OBJECT-TYPE
    SYNTAX Integer32
    MAX-ACCESS read-only
    STATUS current
    DESCRIPTION
        "The number of overflows recorded on Gigabit Ethernet interface semGbeStatusFrameBufferInterface and
         UDP port semGbeStatusFrameBufferUdpPort for the hour."
::= { semGbeStatusFrameBufferEntry 7 }

semGbeStatusFrameBufferResets OBJECT-TYPE
    SYNTAX Integer32
    MAX-ACCESS read-only
    STATUS current
    DESCRIPTION
        "The number of resets reported by the GigE processor during the hour."
::= { semGbeStatusFrameBufferEntry 8 }


-- ------------------------------------------------------------------------------
--
-- semGbeStatusVlanCfmTable
--

semGbeStatusVlanCfmTable OBJECT-TYPE
    SYNTAX SEQUENCE OF SemGbeStatusVlanCfmEntry
    MAX-ACCESS not-accessible
    STATUS current
    DESCRIPTION
        "Table of Gigabit Ethernet VLAN and CFM status elements."
::= { semGbeStatus 12 }

semGbeStatusVlanCfmEntry OBJECT-TYPE
    SYNTAX SemGbeStatusVlanCfmEntry
    MAX-ACCESS not-accessible
    STATUS current
    DESCRIPTION
        "Gigabit Ethernet VLAN CFM Table Entry."
    INDEX { semGbeStatusVlanCfmStreamNum }
::= { semGbeStatusVlanCfmTable 1 }

SemGbeStatusVlanCfmEntry ::= SEQUENCE
    {
     semGbeStatusVlanCfmStreamNum     Integer32,
     semGbeVlanTaggingVidInUse        Integer32,
     semGbeCfmInsertionOpcode         Integer32
    }

semGbeStatusVlanCfmStreamNum OBJECT-TYPE
    SYNTAX Integer32 (1..16)
    MAX-ACCESS not-accessible
    STATUS current
    DESCRIPTION
        "The output transport stream number."
::= { semGbeStatusVlanCfmEntry 1 }

semGbeVlanTaggingVidInUse OBJECT-TYPE
    SYNTAX Integer32
    MAX-ACCESS read-only
    STATUS current
    DESCRIPTION
        "The VLAN VID in use for an output transport stream. The VID in use is based on
         the calculated VID or the specified user VID. The VLAN VID configuration
         parameters, semGbeVlanTaggingVidType and semGbeVlanTaggingUserVid, determine
         how the VID in use is determined.

         This table is only applicable when VLAN Tagging is enabled and there is at least
         one Gigabit Ethernet output stream configured."
::= { semGbeStatusVlanCfmEntry 2 }

semGbeCfmInsertionOpcode OBJECT-TYPE
    SYNTAX Integer32
    MAX-ACCESS read-only
    STATUS current
    DESCRIPTION
        "The CFM Insertion opcode for an output transport stream. The CFM opcode reflects
         the health of the Gigabit Ethernet output stream. The following are the only two
         valid values for the CFM opcode:
             00 = Healthy
             06 = Not Healthy

         This table is only applicable when CFM Insertion is enabled and there is at least
         one Gigabit Ethernet output stream configured."
::= { semGbeStatusVlanCfmEntry 3 }


-- ------------------------------------------------------------------------------
--
-- semGbeStatusInputUdp
--
-- semGbeStatusInputUdpGeneral
--

semGbeStatusInputUdpUpdateInterval OBJECT-TYPE
    SYNTAX Integer32
    MAX-ACCESS read-only
    STATUS current
    DESCRIPTION
        "Time in seconds between Gigabit Ethernet UDP Packet Count
         updates.  The count during this time is defined as one sample.

         This time applies to UDP packet counts contained in
         semGbeStatusInputUdpTable, semGbeStatusCommandedInputUdpTable,
         and semGbeInputUdpErrorTable.

         To compute rate from packet count:
         Rate(bps) = (Packet_Count * 188 bytes/packet * 8 bits/byte) / Update_Interval

         This value is set by the SEM at startup and is constant.
        "
::= { semGbeStatusInputUdpGeneral 1 }


-- ------------------------------------------------------------------------------
--
-- semGbeStatusInputUdpTable
--

semGbeStatusInputUdpTable OBJECT-TYPE
    SYNTAX SEQUENCE OF SemGbeStatusInputUdpEntry
    MAX-ACCESS not-accessible
    STATUS current
    DESCRIPTION
        "Table of Gigabit Ethernet UDP Port status.  This table contains 384
         rows.

         This is the status for UDP ports configured in semGbeInputUdpConfigTable.
         For the configuration of a UDP port listed in this table, refer to the
         same row index in semGbeInputUdpConfigTable.

         Packet Counts are updated every semGbeStatusInputUdpUpdateInterval.
         The count during a semGbeStatusInputUdpUpdateInterval is a sample.
         The samples are accumulated into a set of rolling statistics that cover
         a maximum of a 15 minute sampling time period.  The sampling period is
         the amount of time over which the data in the corresponding row has been
         collected.  When the sampling period reaches 15 minutes, old data is
         removed from the accumulated statistics and new data is rolled in.  In
         this way, the average, minimum, and peak rates for the sampling period
         are maintained.

         For the status of other commanded UDP Ports, which include UDP ports
         automatically opened by the SEM in Operating Modes such as UDP Port
         Mapping and UDP ports opened as commanded by a Local Controller,
         refer to semGbeStatusCommandedInputUdpTable.
        "
::= { semGbeStatusInputUdp 2 }

semGbeStatusInputUdpEntry OBJECT-TYPE
    SYNTAX SemGbeStatusInputUdpEntry
    MAX-ACCESS not-accessible
    STATUS current
    DESCRIPTION
        "Gigabit Ethernet UDP Port Status Table Entry."
    INDEX { semGbeStatInUdpIndex }
::= { semGbeStatusInputUdpTable 1 }

SemGbeStatusInputUdpEntry ::= SEQUENCE
    {
     semGbeStatInUdpIndex                Integer32,
     semGbeStatInUdpState                UdpPortStateTYPE,
     semGbeStatInUdpSamplingPeriod       Integer32,
     semGbeStatInUdpCurDataCount         Counter32,
     semGbeStatInUdpAvgDataCount         Counter32,
     semGbeStatInUdpMinDataCount         Counter32,
     semGbeStatInUdpPeakDataCount        Counter32,
     semGbeStatInUdpCurTsCount           Counter32,
     semGbeStatInUdpAvgTsCount           Counter32,
     semGbeStatInUdpMinTsCount           Counter32,
     semGbeStatInUdpPeakTsCount          Counter32,
     semGbeStatInUdpAlarmSummary         INTEGER,
     semGbeStatInUdpLowBitRateAlarm      INTEGER,
     semGbeStatInUdpMptsRedundPriAlarm   INTEGER,
     semGbeStatInUdpMptsRedundFailAlarm  INTEGER,
     semGbeStatInUdpHighBitRateAlarm     INTEGER
    }

semGbeStatInUdpIndex OBJECT-TYPE
    SYNTAX Integer32 (1..384)
    MAX-ACCESS not-accessible
    STATUS current
    DESCRIPTION
        "The Gigabit Ethernet UDP Port Status table index.
        "
::= { semGbeStatusInputUdpEntry 1 }

semGbeStatInUdpState OBJECT-TYPE
    SYNTAX UdpPortStateTYPE
    MAX-ACCESS read-only
    STATUS current
    DESCRIPTION
        "The current state of the Gigabit Ethernet UDP Port configured
         on the same row index in semGbeInputUdpConfigTable.  States are:
            closed              (0) - UDP Port is closed or table row is not in use.
            openedInUse         (1) - UDP Port is opened and in use.
            openedBackup        (2) - UDP Port is opened as backup only.
            openedTransToBackup (3) - UDP Port is opened, transitioning to backup state.
            openedTransToInUse  (4) - UDP Port is opened, transitioning to in use state.

         The states of 'openedBackup', 'openedTransToBackup', and 'openedTransToBackup'
         apply only to Redundant Pairs (semGbeInUdpConfMptsRedundSelection of 'primary'
         or 'secondary').  The state of 'openedBackup' applies to the UDP Port of the pair
         that is not currently in use.  The state of 'openedTransToBackup' applies to the
         UDP Port of the pair that is currently in use but is transitioning to be the
         backup, as when a Fail Over or Switch Back is occurring.  The state of
         'openedTransToInUse' applies to the UDP Port of the pair that is currently the
         backup use but is transitioning to be the in use, as when a Fail Over or Switch
         Back is occurring.
        "
::= { semGbeStatusInputUdpEntry 2 }

semGbeStatInUdpSamplingPeriod OBJECT-TYPE
    SYNTAX Integer32
    MAX-ACCESS read-only
    STATUS current
    DESCRIPTION
        "The total time, in seconds, over which the packet counts statistics
         in this row have been collected.

         Refer to the description of semGbeStatusInputUdpTable for an
         explanation of packet counting.  Refer to the description of
         semGbeStatusInputUdpUpdateInterval for an explanation of update
         interval and computing rates.
        "
::= { semGbeStatusInputUdpEntry 3 }

semGbeStatInUdpCurDataCount OBJECT-TYPE
    SYNTAX Counter32
    MAX-ACCESS read-only
    STATUS current
    DESCRIPTION
        "The Data Packet Count of the most recent sample.

         Refer to the description of semGbeStatusInputUdpTable for an
         explanation of packet counting.  Refer to the description of
         semGbeStatusInputUdpUpdateInterval for an explanation of update
         interval and computing rates.
        "
::= { semGbeStatusInputUdpEntry 4 }

semGbeStatInUdpAvgDataCount OBJECT-TYPE
    SYNTAX Counter32
    MAX-ACCESS read-only
    STATUS current
    DESCRIPTION
        "The Average Data Packet Count per sample during
         semGbeStatInUdpSamplingPeriod.

         Refer to the description of semGbeStatusInputUdpTable for an
         explanation of packet counting.  Refer to the description of
         semGbeStatusInputUdpUpdateInterval for an explanation of update
         interval and computing rates.
        "
::= { semGbeStatusInputUdpEntry 5 }

semGbeStatInUdpMinDataCount OBJECT-TYPE
    SYNTAX Counter32
    MAX-ACCESS read-only
    STATUS current
    DESCRIPTION
        "The Minimum Data Packet Count sample during
         semGbeStatInUdpSamplingPeriod.

         Refer to the description of semGbeStatusInputUdpTable for an
         explanation of packet counting.  Refer to the description of
         semGbeStatusInputUdpUpdateInterval for an explanation of update
         interval and computing rates.
        "
::= { semGbeStatusInputUdpEntry 6 }

semGbeStatInUdpPeakDataCount OBJECT-TYPE
    SYNTAX Counter32
    MAX-ACCESS read-only
    STATUS current
    DESCRIPTION
        "The Peak Data Packet Count sample during
         semGbeStatInUdpSamplingPeriod.

         Refer to the description of semGbeStatusInputUdpTable for an
         explanation of packet counting.  Refer to the description of
         semGbeStatusInputUdpUpdateInterval for an explanation of update
         interval and computing rates.
        "
::= { semGbeStatusInputUdpEntry 7 }

semGbeStatInUdpCurTsCount OBJECT-TYPE
    SYNTAX Counter32
    MAX-ACCESS read-only
    STATUS current
    DESCRIPTION
        "The Transport Stream Packet Count of the most recent sample.

         Refer to the description of semGbeStatusInputUdpTable for an
         explanation of packet counting.  Refer to the description of
         semGbeStatusInputUdpUpdateInterval for an explanation of update
         interval and computing rates.
        "
::= { semGbeStatusInputUdpEntry 8 }

semGbeStatInUdpAvgTsCount OBJECT-TYPE
    SYNTAX Counter32
    MAX-ACCESS read-only
    STATUS current
    DESCRIPTION
        "The Average Transport Stream Packet Count per sample during
         semGbeStatInUdpSamplingPeriod.

         Refer to the description of semGbeStatusInputUdpTable for an
         explanation of packet counting.  Refer to the description of
         semGbeStatusInputUdpUpdateInterval for an explanation of update
         interval and computing rates.
        "
::= { semGbeStatusInputUdpEntry 9 }

semGbeStatInUdpMinTsCount OBJECT-TYPE
    SYNTAX Counter32
    MAX-ACCESS read-only
    STATUS current
    DESCRIPTION
        "The Minimum Transport Stream Packet Count sample during
         semGbeStatInUdpSamplingPeriod.

         Refer to the description of semGbeStatusInputUdpTable for an
         explanation of packet counting.  Refer to the description of
         semGbeStatusInputUdpUpdateInterval for an explanation of update
         interval and computing rates.
        "
::= { semGbeStatusInputUdpEntry 10 }

semGbeStatInUdpPeakTsCount OBJECT-TYPE
    SYNTAX Counter32
    MAX-ACCESS read-only
    STATUS current
    DESCRIPTION
        "The Peak Transport Stream Packet Count sample during
         semGbeStatInUdpSamplingPeriod.

         Refer to the description of semGbeStatusInputUdpTable for an
         explanation of packet counting.  Refer to the description of
         semGbeStatusInputUdpUpdateInterval for an explanation of update
         interval and computing rates.
        "
::= { semGbeStatusInputUdpEntry 11 }

semGbeStatInUdpAlarmSummary OBJECT-TYPE
    SYNTAX INTEGER
        {
         ok(1),
         indeterminate(2),
         warning(3),
         minor(4),
         major(5),
         critical(6)
        }
    MAX-ACCESS read-only
    STATUS current
    DESCRIPTION
        "The current highest severity of the semAlarmGbeInputStreamLowBitRate,
         semAlarmGbeMptsRedundPrimaryThreshold, and semAlarmGbeMptsRedundFailOver
         alarms for this UDP Port.
        "
::= { semGbeStatusInputUdpEntry 12 }

semGbeStatInUdpLowBitRateAlarm OBJECT-TYPE
    SYNTAX INTEGER
        {
         ok(1),
         indeterminate(2),
         warning(3),
         minor(4),
         major(5),
         critical(6)
        }
    MAX-ACCESS read-only
    STATUS current
    DESCRIPTION
        "The current severity of the semAlarmGbeInputStreamLowBitRate
         alarm for this UDP Port.
        "
::= { semGbeStatusInputUdpEntry 13 }

semGbeStatInUdpMptsRedundPriAlarm OBJECT-TYPE
    SYNTAX INTEGER
        {
         ok(1),
         indeterminate(2),
         warning(3),
         minor(4),
         major(5),
         critical(6)
        }
    MAX-ACCESS read-only
    STATUS current
    DESCRIPTION
        "The current severity of the semAlarmGbeMptsRedundPrimaryThreshold
         alarm for this UDP Port.
        "
::= { semGbeStatusInputUdpEntry 14 }

semGbeStatInUdpMptsRedundFailAlarm OBJECT-TYPE
    SYNTAX INTEGER
        {
         ok(1),
         indeterminate(2),
         warning(3),
         minor(4),
         major(5),
         critical(6)
        }
    MAX-ACCESS read-only
    STATUS current
    DESCRIPTION
        "The current severity of the semAlarmGbeMptsRedundFailOver
         alarm for this UDP Port.
        "
::= { semGbeStatusInputUdpEntry 15 }

semGbeStatInUdpHighBitRateAlarm OBJECT-TYPE
    SYNTAX INTEGER
        {
         ok(1),
         indeterminate(2),
         warning(3),
         minor(4),
         major(5),
         critical(6)
        }
    MAX-ACCESS read-only
    STATUS current
    DESCRIPTION
        "The current severity of the semAlarmGbeInputStreamHighBitRate
         alarm for this UDP Port.

         This is only applicable when semDeviceOperatingMode is 'isaSdv'.
        "
::= { semGbeStatusInputUdpEntry 16 }


-- ------------------------------------------------------------------------------
--
-- semGbeStatusCommandedInputUdpTable
--

semGbeStatusCommandedInputUdpTable OBJECT-TYPE
    SYNTAX SEQUENCE OF SemGbeStatusCommandedInputUdpEntry
    MAX-ACCESS not-accessible
    STATUS current
    DESCRIPTION
        "Table of Gigabit Ethernet Commanded UDP Port status.  This table contains 384
         rows.  Commanded UDP Ports include UDP ports automatically opened by the SEM
         in Operating Modes such as UDP Port Mapping and UDP ports opened as commanded
         by a Local Controller.

         Packet Counts are updated every semGbeStatusInputUdpUpdateInterval.
         The count during a semGbeStatusInputUdpUpdateInterval is a sample.
         The samples are accumulated into a set of rolling statistics that cover
         a maximum of a 15 minute sampling time period.  The sampling period is
         the amount of time over which the data in the corresponding row has been
         collected.  When the sampling period reaches 15 minutes, old data is
         removed from the accumulated statistics and new data is rolled in.  In
         this way, the average, minimum, and peak rates for the sampling period
         are maintained.

         The SEM can not alarm on the UDP ports reported in this table.  If alarming
         is required the user must add the UDP Port to semGbeInputUdpConfigTable.
        "
::= { semGbeStatusInputUdp 3 }

semGbeStatusCommandedInputUdpEntry OBJECT-TYPE
    SYNTAX SemGbeStatusCommandedInputUdpEntry
    MAX-ACCESS not-accessible
    STATUS current
    DESCRIPTION
        "Gigabit Ethernet Commanded UDP Port Status Table Entry."
    INDEX { semGbeStatCommUdpIndex }
::= { semGbeStatusCommandedInputUdpTable 1 }

SemGbeStatusCommandedInputUdpEntry ::= SEQUENCE
    {
     semGbeStatCommUdpIndex             Integer32,
     semGbeStatCommUdpGbePort           Integer32,
     semGbeStatCommUdpPort              Integer32,
     semGbeStatCommUdpSamplingPeriod    Integer32,
     semGbeStatCommUdpCurDataCount      Counter32,
     semGbeStatCommUdpAvgDataCount      Counter32,
     semGbeStatCommUdpMinDataCount      Counter32,
     semGbeStatCommUdpPeakDataCount     Counter32,
     semGbeStatCommUdpCurTsCount        Counter32,
     semGbeStatCommUdpAvgTsCount        Counter32,
     semGbeStatCommUdpMinTsCount        Counter32,
     semGbeStatCommUdpPeakTsCount       Counter32
    }

semGbeStatCommUdpIndex OBJECT-TYPE
    SYNTAX Integer32 (1..384)
    MAX-ACCESS not-accessible
    STATUS current
    DESCRIPTION
        "The Gigabit Ethernet Commanded UDP Port Status table index.
        "
::= { semGbeStatusCommandedInputUdpEntry 1 }

semGbeStatCommUdpGbePort OBJECT-TYPE
    SYNTAX Integer32(0..3)
    MAX-ACCESS read-only
    STATUS current
    DESCRIPTION
        "The Gigabit Ethernet physical port on which packets are being received
         on semGbeStatCommUdpPort.
         Zero indicates this row of the table is not in use.
        "
::= { semGbeStatusCommandedInputUdpEntry 2 }

semGbeStatCommUdpPort OBJECT-TYPE
    SYNTAX Integer32
    MAX-ACCESS read-only
    STATUS current
    DESCRIPTION
        "The Gigabit Ethernet Input UDP Port (range is 0 to 65535).
        "
::= { semGbeStatusCommandedInputUdpEntry 3 }

semGbeStatCommUdpSamplingPeriod OBJECT-TYPE
    SYNTAX Integer32
    MAX-ACCESS read-only
    STATUS current
    DESCRIPTION
        "The total time, in seconds, over which the packet counts statistics
         in this row have been collected.

         Refer to the description of semGbeStatusCommandedInputUdpTable for
         an explanation of packet counting.  Refer to the description of
         semGbeStatusInputUdpUpdateInterval for an explanation of update
         interval and computing rates.
        "
::= { semGbeStatusCommandedInputUdpEntry 4 }

semGbeStatCommUdpCurDataCount OBJECT-TYPE
    SYNTAX Counter32
    MAX-ACCESS read-only
    STATUS current
    DESCRIPTION
        "The Data Packet Count of the most recent sample.

         Refer to the description of semGbeStatusCommandedInputUdpTable for
         an explanation of packet counting.  Refer to the description of
         semGbeStatusInputUdpUpdateInterval for an explanation of update
         interval and computing rates.
        "
::= { semGbeStatusCommandedInputUdpEntry 5 }

semGbeStatCommUdpAvgDataCount OBJECT-TYPE
    SYNTAX Counter32
    MAX-ACCESS read-only
    STATUS current
    DESCRIPTION
        "The Average Data Packet Count per sample during
         semGbeStatCommUdpSamplingPeriod.

         Refer to the description of semGbeStatusCommandedInputUdpTable for
         an explanation of packet counting.  Refer to the description of
         semGbeStatusInputUdpUpdateInterval for an explanation of update
         interval and computing rates.
        "
::= { semGbeStatusCommandedInputUdpEntry 6 }

semGbeStatCommUdpMinDataCount OBJECT-TYPE
    SYNTAX Counter32
    MAX-ACCESS read-only
    STATUS current
    DESCRIPTION
        "The Minimum Data Packet Count sample during
         semGbeStatCommUdpSamplingPeriod.

         Refer to the description of semGbeStatusCommandedInputUdpTable for
         an explanation of packet counting.  Refer to the description of
         semGbeStatusInputUdpUpdateInterval for an explanation of update
         interval and computing rates.
        "
::= { semGbeStatusCommandedInputUdpEntry 7 }

semGbeStatCommUdpPeakDataCount OBJECT-TYPE
    SYNTAX Counter32
    MAX-ACCESS read-only
    STATUS current
    DESCRIPTION
        "The Peak Data Packet Count sample during
         semGbeStatCommUdpSamplingPeriod.

         Refer to the description of semGbeStatusCommandedInputUdpTable for
         an explanation of packet counting.  Refer to the description of
         semGbeStatusInputUdpUpdateInterval for an explanation of update
         interval and computing rates.
        "
::= { semGbeStatusCommandedInputUdpEntry 8 }

semGbeStatCommUdpCurTsCount OBJECT-TYPE
    SYNTAX Counter32
    MAX-ACCESS read-only
    STATUS current
    DESCRIPTION
        "The Transport Stream Packet Count of the most recent sample.

         Refer to the description of semGbeStatusCommandedInputUdpTable for
         an explanation of packet counting.  Refer to the description of
         semGbeStatusInputUdpUpdateInterval for an explanation of update
         interval and computing rates.
        "
::= { semGbeStatusCommandedInputUdpEntry 9 }

semGbeStatCommUdpAvgTsCount OBJECT-TYPE
    SYNTAX Counter32
    MAX-ACCESS read-only
    STATUS current
    DESCRIPTION
        "The Average Transport Stream Packet Count per sample during
         semGbeStatCommUdpSamplingPeriod.

         Refer to the description of semGbeStatusCommandedInputUdpTable for
         an explanation of packet counting.  Refer to the description of
         semGbeStatusInputUdpUpdateInterval for an explanation of update
         interval and computing rates.
        "
::= { semGbeStatusCommandedInputUdpEntry 10 }

semGbeStatCommUdpMinTsCount OBJECT-TYPE
    SYNTAX Counter32
    MAX-ACCESS read-only
    STATUS current
    DESCRIPTION
        "The Minimum Transport Stream Packet Count sample during
         semGbeStatCommUdpSamplingPeriod.

         Refer to the description of semGbeStatusCommandedInputUdpTable for
         an explanation of packet counting.  Refer to the description of
         semGbeStatusInputUdpUpdateInterval for an explanation of update
         interval and computing rates.
        "
::= { semGbeStatusCommandedInputUdpEntry 11 }

semGbeStatCommUdpPeakTsCount OBJECT-TYPE
    SYNTAX Counter32
    MAX-ACCESS read-only
    STATUS current
    DESCRIPTION
        "The Peak Transport Stream Packet Count sample during
         semGbeStatCommUdpSamplingPeriod.

         Refer to the description of semGbeStatusCommandedInputUdpTable for
         an explanation of packet counting.  Refer to the description of
         semGbeStatusInputUdpUpdateInterval for an explanation of update
         interval and computing rates.
        "
::= { semGbeStatusCommandedInputUdpEntry 12 }


-- ------------------------------------------------------------------------------
--
-- semQAM
--
-- semQamConfig
--
-- semQamConfigGeneral
--

semQamConfigTransmissionMode OBJECT-TYPE
    SYNTAX INTEGER
        {
         annexB-ATSC-DCII     (1),
         annexA-DVB           (2),
         annexC-Asia-Pacific  (3)
        }
    MAX-ACCESS read-write
    STATUS current
    DESCRIPTION
        "This is the QAM Transmission Mode as defined in:
         Series J: Transmission of Television, Sound Programme
         and other Multimedia Signals, ITU-T J.83.

         Once written, a save must be performed via the semSaveConfig
         parameter and the SEM must be rebooted for the change to take effect.

         @Config(config=yes, reboot=yes)
         @Save(semSaveConfig, value=2)
         @File(config.ini, type='ini')
        "
::= { semQamConfigGeneral 1 }


-- ------------------------------------------------------------------------------
--
-- semQamConfigTable
--

semQamConfigTable OBJECT-TYPE
    SYNTAX SEQUENCE OF SemQamConfigEntry
    MAX-ACCESS not-accessible
    STATUS current
    DESCRIPTION
        "Table of parameters for configuring each of the SEM QAM
         ports.

         For SEMs with Upconverters, two QAM channels feed into one
         upconverter channel.  The first upconverter in the upconverter
         config table is associated with the first and second QAM channels
         of this Table, the second upconverter with the third and fourth
         QAM channels, and so forth.

         For SEMs without Upconverters, only the 'A' side of the QAM is
         used.  The first, third, fifth, etc., QAM configuration is used.
         The second, fourth, sixth, etc., are not used by the SEM.
         The only currently supported non-Upconverter SEM configuration
         is four channels.

         SEM1000/v8 have 8 ports and use table entries 1 through 8.
         SEM v4 has 4 ports and uses table entries 1, 3, 5, and 7.
         SEM v12 has 8 ports and uses table entries 1 through 12.
         It should be noted that the ini file that contains this
         table should contain 12 sets of data regardless of SEM type
         in order to conform to this MIB.  User interfaces need only
         display and configure the appropriate data for each SEM type.

         @Commit(param=semUpConvConfigApplyChange, value=2)
         @Config(config=yes, reboot=no)
         @Save(semSaveConfig, value=2)
         @File(config.ini, type='ini')
        "
::= { semQamConfig 2 }

semQamConfigEntry OBJECT-TYPE
    SYNTAX SemQamConfigEntry
    MAX-ACCESS not-accessible
    STATUS current
    DESCRIPTION
        "A row in the Qam Configuration table."
    INDEX { semQamConfigPortNum }
::= { semQamConfigTable 1 }

SemQamConfigEntry ::= SEQUENCE
    {
     semQamConfigPortNum              Integer32,
     semQamConfigMute                 OutputMuteTYPE,
     semQamConfigMode                 INTEGER,
     semQamConfigInterleaverDepth     INTEGER,
     semQamConfigSymbolRate           Integer32,
     semQamConfigSpectrumInvert       INTEGER,
     semQamConfigTestMode             INTEGER,
     semQamConfigRfGainLevel          INTEGER,
     semQamConfigIfFreq               Integer32,
     semQamConfigIfGainLevel          INTEGER
    }

semQamConfigPortNum OBJECT-TYPE
    SYNTAX Integer32 (1..12)
    MAX-ACCESS not-accessible
    STATUS current
    DESCRIPTION
        "The port number of the Qam Channel."
::= { semQamConfigEntry 1 }

semQamConfigMute OBJECT-TYPE
    SYNTAX OutputMuteTYPE
    MAX-ACCESS read-write
    STATUS current
    DESCRIPTION
        "The Mute control for the Qam channel.

         Once written, the change to this parameter will only take immediate
         effect after the appropriate semUpConvConfigApplyChange is set to
         'apply'.  In order for the change to persist through subsequent
         reboots or power cycles, the change must be saved via the semSaveConfig
         parameter.
        "
::= { semQamConfigEntry 2 }

semQamConfigMode OBJECT-TYPE
    SYNTAX INTEGER
        {
         qam64  (1),
         qam256 (2)
        }
    MAX-ACCESS read-write
    STATUS current
    DESCRIPTION
        "The Qam mode for the Qam channel.  Note that the input data rate and
         clock configured elsewhere in the SEM must match the QAM setting above
         for the QAM module to operate properly.

         Once written, the change to this parameter will only take immediate
         effect after the appropriate semUpConvConfigApplyChange is set to
         'apply'.  In order for the change to persist through subsequent
         reboots or power cycles, the change must be saved via the semSaveConfig
         parameter.
        "
::= { semQamConfigEntry 3 }

semQamConfigInterleaverDepth OBJECT-TYPE
    SYNTAX INTEGER
        {
         i64-j2  (1),
         i32-j4  (2),
         i16-j8  (3),
         i8-j16  (4),
         i128-j1 (5),
         i128-j2 (6),
         i128-j3 (7),
         i128-j4 (8),
         i128-j5 (9),
         i128-j6 (10),
         i128-j7 (11),
         i128-j8 (12)
        }
    MAX-ACCESS read-write
    STATUS current
    DESCRIPTION
        "The Interleaver Setting for the Qam channel.
         Configurable ONLY in AnnexB-ATSC-DCII 256 QAM.
         For AnnexB-ATSC-DCII 64 QAM the SEM defaults to
         I=128 , J= 1.  The value is written to this parameter
         for the user to access.
         This parameter is not configurable for FEC Modes annexA-DVB or
         annexC-Asia-Pacific and is ignored.  In these modes the correct interleaver
         setting is determined by the SEM and is not user accessible.

         Once written, the change to this parameter will only take immediate
         effect after the appropriate semUpConvConfigApplyChange is set to
         'apply'.  In order for the change to persist through subsequent
         reboots or power cycles, the change must be saved via the semSaveConfig
         parameter.
        "
::= { semQamConfigEntry 4 }

semQamConfigSymbolRate OBJECT-TYPE
    SYNTAX Integer32 (800000..7000000)
    MAX-ACCESS read-write
    STATUS current
    DESCRIPTION
        "The Symbol Rate Setting for the Qam channel in symbols per
         second (sps). It's  range is between 800000 sps to 7000000 sps in
         1 Ksps steps.
         This parameter is not configurable in AnnexB-ATSC-DCII transmission
         mode and is initialized by SEM to the standard specified value based
         on QAM Modulation Mode.  The value configured by the SEM is written
         to this parameter for the user to access.

         Once written, the change to this parameter will only take immediate
         effect after the appropriate semUpConvConfigApplyChange is set to
         'apply'.  In order for the change to persist through subsequent
         reboots or power cycles, the change must be saved via the semSaveConfig
         parameter.

         @Range(step=1000)
        "
::= { semQamConfigEntry 5 }

semQamConfigSpectrumInvert OBJECT-TYPE
    SYNTAX INTEGER
        {
         normal  (1),
         invert  (2)
        }
    MAX-ACCESS read-write
    STATUS current
    DESCRIPTION
        "The Spectrum Inversion Setting for the Qam channel.

         Once written, the change to this parameter will only take immediate
         effect after the appropriate semUpConvConfigApplyChange is set to
         'apply'.  In order for the change to persist through subsequent
         reboots or power cycles, the change must be saved via the semSaveConfig
         parameter.
        "
::= { semQamConfigEntry 6 }

semQamConfigTestMode OBJECT-TYPE
    SYNTAX INTEGER
        {
         off     (1),
         cwtest  (2),
         prbs15  (3),
         prbs15m (4),
         prbs23  (5),
         prbs23m (6)
        }
    MAX-ACCESS read-write
    STATUS current
    DESCRIPTION
        "Test mode setting for the QAM Channel.

         Once written, the change to this parameter will only take immediate
         effect after the appropriate semUpConvConfigApplyChange is set to
         'apply'.  In order for the change to persist through subsequent
         reboots or power cycles, the change must be saved via the semSaveConfig
         parameter.
        "
::= { semQamConfigEntry 7 }


semQamConfigRfGainLevel OBJECT-TYPE
    SYNTAX INTEGER
        {
         dBmV45-00  (1),  dBmV45-50  (2),  dBmV46-00  (3),  dBmV46-50  (4),
         dBmV47-00  (5),  dBmV47-50  (6),  dBmV48-00  (7),  dBmV48-50  (8),
         dBmV49-00  (9),  dBmV49-50  (10), dBmV50-00  (11), dBmV50-50  (12),
         dBmV51-00  (13), dBmV51-50  (14), dBmV52-00  (15), dBmV52-50  (16),
         dBmV53-00  (17), dBmV53-50  (18), dBmV54-00  (19), dBmV54-50  (20),
         dBmV55-00  (21), dBmV55-50  (22), dBmV56-00  (23), dBmV56-50  (24),
         dBmV57-00  (25), dBmV57-50  (26), dBmV58-00  (27), dBmV58-50  (28),
         dBmV59-00  (29), dBmV59-50  (30), dBmV60-00  (31), dBmV60-50  (32),
         dBmV61-00  (33)
        }
    MAX-ACCESS read-write
    STATUS current
    DESCRIPTION
        "The RF Gain Control level Setting for the QAM Channel.

         For semUpConvModuleMcn less than 20, the range is 45 dBmV to 56 dBmV.

         For semUpConvModuleMcn of 20 and greater, the range is 45 dBmV to 58 dBmV
         when both outputs are unmuted.  When one output is muted, the range is
         45 dBmV to 61 dBmV for the unmuted output.

         If too high a level is entered the SEM will set the value to the applicable
         maximum value allowed.

         For SEMs without Upconverters, this parameter is not used.


         Once written, the change to this parameter will only take immediate
         effect after the appropriate semUpConvConfigApplyChange is set to
         'apply'.  In order for the change to persist through subsequent
         reboots or power cycles, the change must be saved via the semSaveConfig
         parameter.
        "
::= { semQamConfigEntry 8 }

semQamConfigIfFreq OBJECT-TYPE
    SYNTAX Integer32
    MAX-ACCESS read-write
    STATUS current
    DESCRIPTION
        "This is the IF frequency that the QAM will use.  This value
         must be in Hz in the range 35,000,000 Hz to 44,000,000 Hz.

         The value should be entered in 1 kHz steps.  The SEM will correct
         values not on a 1 kHz boundary so the user or management
         system does not need to enforce the step size.

         This parameter is configurable ONLY when the SEM is configured to
         operate without an Upconverter.

         Once written, the change to this parameter will only take immediate
         effect after the appropriate semUpConvConfigApplyChange is set to
         'apply'.  In order for the change to persist through subsequent
         reboots or power cycles, the change must be saved via the semSaveConfig
         parameter.

         @Range(min=35000000, max=44000000, step=1000)
        "
::= { semQamConfigEntry 9 }

semQamConfigIfGainLevel OBJECT-TYPE
    SYNTAX INTEGER
        {
         dBmV30-00  (1),  dBmV30-50  (2),  dBmV31-00  (3),  dBmV31-50  (4),
         dBmV32-00  (5),  dBmV32-50  (6),  dBmV33-00  (7),  dBmV33-50  (8),
         dBmV34-00  (9),  dBmV34-50  (10), dBmV35-00  (11), dBmV35-50  (12),
         dBmV36-00  (13), dBmV36-50  (14), dBmV37-00  (15), dBmV37-50  (16),
         dBmV38-00  (17), dBmV38-50  (18), dBmV39-00  (19), dBmV39-50  (20),
         dBmV40-00  (21)
        }
    MAX-ACCESS read-write
    STATUS current
    DESCRIPTION
        "The IF Gain Control level Setting for the QAM Channel.

         The range is 30 dBmV to 40 dBmV and in 0.50 dBmV steps.

         This parameter is configurable ONLY when the SEM is configured to
         operate without an Upconverter.

         Once written, the change to this parameter will only take immediate
         effect after the appropriate semUpConvConfigApplyChange is set to
         'apply'.  In order for the change to persist through subsequent
         reboots or power cycles, the change must be saved via the semSaveConfig
         parameter.
        "
::= { semQamConfigEntry 10 }


-- ------------------------------------------------------------------------------
--
-- semQamStatus
--
-- semQamStatusGeneral

semQamModuleInstalled OBJECT-TYPE
    SYNTAX InstalledTYPE
    MAX-ACCESS read-only
    STATUS current
    DESCRIPTION
        "Indicates whether the QAM module is installed in the SEM."
::= { semQamStatusGeneral 1 }

semQamModuleMcn OBJECT-TYPE
    SYNTAX Integer32
    MAX-ACCESS read-only
    STATUS current
    DESCRIPTION
        "QAM Board MCN."
::= { semQamStatusGeneral 2 }

semQamModuleVersion OBJECT-TYPE
    SYNTAX Integer32
    MAX-ACCESS read-only
    STATUS current
    DESCRIPTION
        "QAM Board Version."
::= { semQamStatusGeneral 3 }

semQamModuleFirmwareVersion OBJECT-TYPE
    SYNTAX Integer32
    MAX-ACCESS read-only
    STATUS current
    DESCRIPTION
        "QAM Board Firmware Version."
::= { semQamStatusGeneral 4 }

semQamStatusNumOutputStreams OBJECT-TYPE
    SYNTAX Integer32
    MAX-ACCESS read-only
    STATUS current
    DESCRIPTION
        "The number of QAM output streams configured."
::= { semQamStatusGeneral 5 }


-- ------------------------------------------------------------------------------
--
-- semQamStatusTable
--

semQamStatusTable OBJECT-TYPE
    SYNTAX SEQUENCE OF SemQamStatusEntry
    MAX-ACCESS not-accessible
    STATUS current
    DESCRIPTION
        "Table of status parameters for each of the SEM QAM ports.

         For SEMs with Upconverters, two QAM channels feed into one
         upconverter.  The first upconverter in the upconverter status
         table is associated with the first and second QAM channels of
         this Table, the second upconverter with the third and fourth
         QAM channels, and so forth.

         For SEMs without Upconverters, only the 'A' side of the QAM is
         used.  The first, third, fifth, etc., QAM status is used.
         The second, fourth, sixth, etc., are not set by the SEM.
         The only currently supported non-Upconverter SEM configuration
         is four channels.

         SEM1000/v8 have 8 ports and use table entries 1 through 8.
         SEM v4 has 4 ports and uses table entries 1, 3, 5, and 7.
         SEM v12 has 8 ports and uses table entries 1 through 12.
         It should be noted that user interfaces need only
         display and the appropriate data for each SEM type."
::= { semQamStatus 2 }

semQamStatusEntry OBJECT-TYPE
    SYNTAX SemQamStatusEntry
    MAX-ACCESS not-accessible
    STATUS current
    DESCRIPTION
        "A row in the Qam Status table."
    INDEX { semQamStatusPortNum }
::= { semQamStatusTable 1 }

SemQamStatusEntry ::= SEQUENCE
    {
     semQamStatusPortNum              Integer32,
     semQamStatusInfoRate             Integer32,
     semQamStatusMpegFecSyncLock      INTEGER,
     semQamStatusAlpha                INTEGER,
     semQamStatusInputBufferError     INTEGER,
     semQamStatusOutputBufferError    INTEGER,
     semQamStatusOutTransStreamNum    Integer32,
     semQamStatusModulatorRevision    Integer32,
     semQamStatusPllStatus            PllErrorTYPE,
     semQamStatusError                INTEGER,
     semQamStatusFault                INTEGER,
     semQamStatusPortError            INTEGER,
     semQamStatusPortFault            INTEGER
    }

semQamStatusPortNum OBJECT-TYPE
    SYNTAX Integer32 (1..12)
    MAX-ACCESS not-accessible
    STATUS current
    DESCRIPTION
        "The port number of the Qam Channel."
::= { semQamStatusEntry 1 }

semQamStatusInfoRate OBJECT-TYPE
    SYNTAX Integer32
    MAX-ACCESS read-only
    STATUS current
    DESCRIPTION
        "The information rate of the QAM channel in bits per second."
::= { semQamStatusEntry 2 }

semQamStatusMpegFecSyncLock OBJECT-TYPE
    SYNTAX INTEGER
        {
         notLocked   (1),
         locked      (2)
        }
    MAX-ACCESS read-only
    STATUS current
    DESCRIPTION
        "Indicates MPEG lock status of FEC encoder."
::= { semQamStatusEntry 3 }

semQamStatusAlpha OBJECT-TYPE
    SYNTAX INTEGER
        {
         twelvePercent        (1),
         fifteenPercent       (2),
         eighteenPercent      (3)
        }
    MAX-ACCESS read-only
    STATUS current
    DESCRIPTION
        "Alpha status of the QAM channel."
::= { semQamStatusEntry 4 }

semQamStatusInputBufferError OBJECT-TYPE
    SYNTAX INTEGER
        {
         noError                    (1),
         overFlowOrUnderFlow        (2)
        }
    MAX-ACCESS read-only
    STATUS current
    DESCRIPTION
        "Indicates when symbol FIFO overflows or underflows."
::= { semQamStatusEntry 5 }

semQamStatusOutputBufferError OBJECT-TYPE
    SYNTAX INTEGER
        {
         noError      (1),
         overflow     (2)
        }
    MAX-ACCESS read-only
    STATUS current
    DESCRIPTION
        "Indicates when gain scalar output overflows."
::= { semQamStatusEntry 6 }

semQamStatusOutTransStreamNum OBJECT-TYPE
    SYNTAX Integer32 (0..16)
    MAX-ACCESS read-only
    STATUS current
    DESCRIPTION
        "The number of the output transport stream routed to this output.
         Zero indicates that no stream is routed to this port.
         It serves as the index into the Transport Stream Configuration Table."
::= { semQamStatusEntry 7 }

semQamStatusModulatorRevision OBJECT-TYPE
    SYNTAX Integer32 (0..16)
    MAX-ACCESS read-only
    STATUS current
    DESCRIPTION
        "The revision number of the Modulator (BCM 3034).
         It is read ONLY once from the modulator for each input."
::= { semQamStatusEntry 8 }

semQamStatusPllStatus OBJECT-TYPE
    SYNTAX PllErrorTYPE
    MAX-ACCESS read-only
    STATUS current
    DESCRIPTION
        "Indicates PLL status of the QAM card."
::= { semQamStatusEntry 9 }

semQamStatusError OBJECT-TYPE
    SYNTAX INTEGER
        {
         noError         (1),
         inFifoError     (2),
         outScalarError  (3),
         fecSyncError    (4),
         clockPllError   (5),
         commError       (6)
        }
    MAX-ACCESS read-only
    STATUS current
    DESCRIPTION
        "Current Modulator Error Status summary based on the following from
         lowest to highest priority:
           - No Error        - No Error
           - Scalar Error    - Modulator output buffer error.  Status also reported in
                               semQamStatusOutputBufferError.
           - FIFO Error      - Modulator input buffer error.  Status also reported in
                               semQamStatusInputBufferError.
           - FEC Sync Error  - FEC encoder indicates loss of MPEG lock.  Status also reported in
                               semQamStatusMpegFecSyncLock.
           - Clock PLL Error - Modulator PLL error.  Status also reported in semQamStatusPllStatus.
           - Comm Error      - Failure of host processor to communicate with the QAM modulator.

         If more than one error is present, the most severe will be reported."
::= { semQamStatusEntry 10 }

semQamStatusFault OBJECT-TYPE
    SYNTAX INTEGER
        {
         ok(1),
         indeterminate(2),
         warning(3),
         minor(4),
         major(5),
         critical(6)
        }
    MAX-ACCESS read-only
    STATUS current
    DESCRIPTION
        "Highest current fault condition associated with this QAM Output.
         This is like the semAlarmQamFault but for an individual QAM.
         See semAlarmQamFault description for additional information."
::= { semQamStatusEntry 11 }

semQamStatusPortError OBJECT-TYPE
    SYNTAX INTEGER
        {
         noError            (1),
         modInFifoError     (2),
         modOutScalarError  (3),
         modFecSyncError    (4),
         modClockPllError   (5),
         modCommError       (6),
         ucSynthesizerError (7),
         ucRfLowError       (8),
         ucRfHighError      (9),
         ucCommError        (10)
        }
    MAX-ACCESS read-only
    STATUS current
    DESCRIPTION
        "Current QAM Port Error Status summary, including Upconverter
         errors that effect this QAM Port, based on the following from
         lowest to highest priority:
           - No Error            - No Error
           - Mod Scalar Error    - Modulator output buffer error.  Status also reported in
                                   semQamStatusOutputBufferError.
           - Mod FIFO Error      - Modulator input buffer error.  Status also reported in
                                   semQamStatusInputBufferError.
           - Mod FEC Sync Error  - FEC encoder indicates loss of MPEG lock.  Status also reported in
                                   semQamStatusMpegFecSyncLock.
           - Mod Clock PLL Error - Modulator PLL error.  Status also reported in semQamStatusPllStatus.
           - Mod Comm Error      - Failure of host processor to communicate with the QAM modulator.
                                   Status also reported in semQamStatusError as 'commError'.
           - UC RF Low Error     - RF output level is lower than configured.  Status also
                                   reported in semUpConvStatusRfOutLevelError as 'lowError'.
           - UC RF High Error    - RF level is higher than configured.  Status also reported
                                   in semUpConvStatusRfOutLevelError as 'highError'.
           - UC Synth Error      - UC PLL error.  Status also reported in semUpConvStatusUpConvError
                                   as 'synthesizerError'.
           - UC Comm Error       - Failure of host processor to communicate with the UC.
                                   Status also reported in semUpConvStatusUpConvError as
                                   'commError'.

         If more than one error is present, the most severe will be reported."
::= { semQamStatusEntry 12 }

semQamStatusPortFault OBJECT-TYPE
    SYNTAX INTEGER
        {
         ok(1),
         indeterminate(2),
         warning(3),
         minor(4),
         major(5),
         critical(6)
        }
    MAX-ACCESS read-only
    STATUS current
    DESCRIPTION
        "Highest current fault condition associated with this QAM Output,
         including Upconverter errors that effect this QAM Port.
         This is like the semAlarmQamPortFault but for an individual QAM.
         See semAlarmQamPortFault description for additional information."
::= { semQamStatusEntry 13 }


-- ------------------------------------------------------------------------------
--
-- semUpConvConfig
--
-- semUpConvConfigTable
--

semUpConvConfigTable OBJECT-TYPE
    SYNTAX SEQUENCE OF SemUpConvConfigEntry
    MAX-ACCESS not-accessible
    STATUS current
    DESCRIPTION
        "Table of parameters for configuring each of the SEM
         Upconverter devices.  Two QAM channels feed into each of the
         upconverter devices.  The first upconverter in this table is
         associated with the first and second QAM channels of the
         QAM Config Table, the second upconverter with the third
         and fourth QAM channels, and so forth.

         SEM1000/v8/v4 have 4 UC devices and use table entries 1 through 4.
         SEM v12 has 6 upconverter devices and uses table entries 1 through 6.
         It should be noted that the ini file that contains this
         table should contain 6 sets of data regardless of SEM type
         in order to conform to this MIB.  User interfaces need only
         display and configure the appropriate data for each SEM type.

         @Config(config=yes, reboot=no)
         @Save(semSaveConfig, value=2)
         @File(config.ini, type='ini')
        "
::= { semUpConvConfig 1 }

semUpConvConfigEntry OBJECT-TYPE
    SYNTAX SemUpConvConfigEntry
    MAX-ACCESS not-accessible
    STATUS current
    DESCRIPTION
        "A row in the Upconverter Configuration table."
    INDEX { semUpConvConfigOutputNumber }
::= { semUpConvConfigTable 1 }

SemUpConvConfigEntry ::= SEQUENCE
    {
     semUpConvConfigOutputNumber       Integer32,
     semUpConvConfigApplyChange        ApplyDataToDeviceTYPE,
     semUpConvConfigTuningMode         INTEGER,
     semUpConvConfigEiaChanNumQamA     Integer32,
     semUpConvConfigRfFreqQamA         Integer32,
     semUpConvConfigRfChanSpacing      Integer32
    }

semUpConvConfigOutputNumber OBJECT-TYPE
    SYNTAX Integer32 (1..6)
    MAX-ACCESS not-accessible
    STATUS current
    DESCRIPTION
        "The unpconverter number."
::= { semUpConvConfigEntry 1 }

semUpConvConfigApplyChange OBJECT-TYPE
    SYNTAX ApplyDataToDeviceTYPE
    MAX-ACCESS read-write
    STATUS current
    DESCRIPTION
        "The Apply for the Upconverter data and the two QAM channels in
         semQamConfigTable associated with it.

         For SEMs without Upconverters, this parameter is still used to
         indicate a change in the semQamConfigTable data.

         This parameter MUST be set to 'apply' in order for any of the data
         in this row of semUpConvConfigTable and the associated QAM channel
         rows in semQamConfigTable to take effect in the SEM.  This parameter
         MUST be set LAST after all other data has been configured.
        "
::= { semUpConvConfigEntry 2 }

semUpConvConfigTuningMode OBJECT-TYPE
    SYNTAX INTEGER
        {
         frequency     (1),
         stdChannel    (2),
         hrcChannel    (3),
         hrcFrequency  (4)
        }
    MAX-ACCESS read-write
    STATUS current
    DESCRIPTION
        "The upconverter tuning mode.
           - 'frequency'    - The SEM tunes based on frequency as configured in
                 semUpConvConfigRfFreqQamA.  When semQamConfigTransmissionMode
                 is 'annexB-ATSC-DCII' or 'annexC-Asia-Pacific', the SEM will use
                 standard EIA channel spacing to determine the frequency of the B
                 channel.  When semQamConfigTransmissionMode is 'annexA-DVB',
                 the SEM will use channel spacing as configured in
                 semUpConvConfigRfChanSpacing.
           - 'stdChannel'   - The SEM tunes based on standard EIA channel as
                 configured in semUpConvConfigEiaChanNumQamA.  The SEM will set
                 the B channel to the next standard EIA channel.  Applies only
                 when semQamConfigTransmissionMode is 'annexB-ATSC-DCII'.
           - 'hrcChannel'   - The SEM tunes based on HRC channel as configured
                 in semUpConvConfigEiaChanNumQamA.  The SEM will set the B
                 channel to the next HRC channel.  Applies only when
                 semQamConfigTransmissionMode is 'annexB-ATSC-DCII'.
           - 'hrcFrequency' - The SEM tunes based on frequency as configured in
                 semUpConvConfigRfFreqQamA and uses HRC channel spacing to
                 determine the frequency of the B channel.  Applies only when
                 semQamConfigTransmissionMode is 'annexB-ATSC-DCII'.

         Once written, the change to this parameter will only take immediate
         effect after semUpConvConfigApplyChange is set to 'apply'.  In order
         for the change to persist through subsequent reboots or power cycles,
         the change must be saved via the semSaveConfig parameter.

         @Commit(param=semUpConvConfigApplyChange, value=2)
        "
::= { semUpConvConfigEntry 3 }

semUpConvConfigEiaChanNumQamA OBJECT-TYPE
    SYNTAX Integer32 (7..134)
    MAX-ACCESS read-write
    STATUS current
    DESCRIPTION
        "Channel Number used to determine output frequency based on value of the
         Tuning Mode parameter. When Tuning Mode equals stdChannel (i.e. EIA Channel)
         then this parameter is an index into the EIA Channel / Standard Frequency
         Table for NTSC North American CATV market.  However, when Tuning Mode is
         hrcChannel then this parameter is an index into HRC Centered Frequency Table.
         Indexed value of either table determines output RF Frequency of the
         up-converter. This parameter is configurable ONLY when FEC Mode is
         AnnexB-ATSC-DCII and configurable ONLY when tuning mode is stdChannel
         or hrcChannel. It should be noted that FEC Mode is AnnexB-ATSC-DCII and
         tuning mode is frequency, the value is computed by the SEM and written to
         this parameter for user to access.  When Tuning Mode equals Frequency
         SEM supplies the EIA channel number corresponding to user configured
         frequency. If there is no EIA channel number for the frequency then EM
         displays Not-Applicable as Channel Number. This parameter is not
         configurable for FEC Modes annexA-DVB or annexC-Asia-Pacific and a value is not
         computed by the SEM for these modes.

         Once written, the change to this parameter will only take immediate
         effect after semUpConvConfigApplyChange is set to 'apply'.  In order
         for the change to persist through subsequent reboots or power cycles,
         the change must be saved via the semSaveConfig parameter.

         @Commit(param=semUpConvConfigApplyChange, value=2)
        "
::= { semUpConvConfigEntry 4 }

semUpConvConfigRfFreqQamA OBJECT-TYPE
    SYNTAX Integer32
    MAX-ACCESS read-write
    STATUS current
    DESCRIPTION
        "This is the frequency that the upconverter will use for the
         first QAM channel associated with the upconverter.  This value
         must be in Hz in the range 88,000,000 Hz to 864,000,000 Hz.

         For semQamModuleMcn less than 50, the value should be entered
         in 250 kHz steps.  For semQamModuleMcn of 50 and greater, the
         value should be entered in 100 Hz steps.  The SEM will correct
         values not on a 250 kHz or 100 Hz boundary so the user or management
         system does not need to enforce the step size.

         The upper and lower limit of RF Output Frequency is computed from
         frequency band limits specified in the FRS and channel spacing.
         The lower and upper RF Frequency band limits are 88 and 864 MHz
         respectively.  Channel Spacing is fixed at 6.0 MHz in DCII (Annex B)
         and Annex C, and variable in DVB (Annex A) between 1.0 and 8.0 MHz.
         Note: Frequency limit checks apply to channel A.

         Lower Frequency Band Limit Check
            Configured RF Frequency - (Channel Spacing / 2) >= 88.0 MHz

         Upper Frequency Band Limit Check
            Configured RF Frequency + Channel Spacing  + (Channel Spacing / 2) <= 864.0 MHz

         This parameter is configurable ONLY when tuning mode is frequency.

         When not configurable, the value is computed by the SEM and written
         to this parameter for the user to access.

         Once written, the change to this parameter will only take immediate
         effect after semUpConvConfigApplyChange is set to 'apply'.  In order
         for the change to persist through subsequent reboots or power cycles,
         the change must be saved via the semSaveConfig parameter.

         @Range(min=88000000, max=864000000)
         @Commit(param=semUpConvConfigApplyChange, value=2)
        "
::= { semUpConvConfigEntry 5 }


semUpConvConfigRfChanSpacing OBJECT-TYPE
    SYNTAX Integer32
    MAX-ACCESS read-write
    STATUS current
    DESCRIPTION
        "This is the Channel spacing for the upconverter.  This value must be
         in Hz in the range 1,000,000 Hz to 8,000,000 Hz.

         It must be entered in 500 kHz steps.

         When semQamConfigTransmissionMode is 'annexA-DVB' this value
         is configurable.

         When semQamConfigTransmissionMode is 'annexB-ATSC-DCII' and
         semUpConvConfigTuningMode is 'frequency' or 'stdChannel',
         this value is fixed at 6000 kHz.

         When semQamConfigTransmissionMode is 'annexB-ATSC-DCII' and
         semUpConvConfigTuningMode is 'hrcChannel' or 'hrcFrequency',
         this value is fixed at 6000.300 kHz.

         When semQamConfigTransmissionMode is 'annexC-Asia-Pacific'
         this value is fixed at 6000 kHz.

         Once written, the change to this parameter will only take immediate
         effect after semUpConvConfigApplyChange is set to 'apply'.  In order
         for the change to persist through subsequent reboots or power cycles,
         the change must be saved via the semSaveConfig parameter.

         @Range(min=1000000, max=8000000, step=500000)
         @Commit(param=semUpConvConfigApplyChange, value=2)
        "
::= { semUpConvConfigEntry 6 }


-- ------------------------------------------------------------------------------
--
-- semUpConvStatus
--
-- semUpConvStatusGeneral

semUpconverterModuleInstalled OBJECT-TYPE
    SYNTAX InstalledTYPE
    MAX-ACCESS read-only
    STATUS current
    DESCRIPTION
        "Indicates whether the Upconverter module is installed in the SEM."
::= { semUpConvStatusGeneral 1 }

semUpconverterModulePldVersion OBJECT-TYPE
    SYNTAX Integer32
    MAX-ACCESS read-only
    STATUS current
    DESCRIPTION
        "Upconverter module PLD Version."
::= { semUpConvStatusGeneral 2 }

semUpconverterModuleMCN OBJECT-TYPE
    SYNTAX Integer32
    MAX-ACCESS read-only
    STATUS current
    DESCRIPTION
        "MCN of the Up-converter."
::= { semUpConvStatusGeneral 3 }

semUpconverterModuleVersion OBJECT-TYPE
    SYNTAX Integer32
    MAX-ACCESS read-only
    STATUS current
    DESCRIPTION
        "Up-converter module version."
::= { semUpConvStatusGeneral 4 }


-- ------------------------------------------------------------------------------
--
-- semUpConvStatusTable
--

semUpConvStatusTable OBJECT-TYPE
    SYNTAX SEQUENCE OF SemUpConvStatusEntry
    MAX-ACCESS not-accessible
    STATUS current
    DESCRIPTION
        "Table of status parameters for each of the SEM
         Upconverters.  Two QAM channels feed into each of the
         upconverters.  The first upconverter in this table is
         associated with the first and second QAM channels of the
         QAM Status Table, the second upconverter with the third
         and fourth QAM channels, and so forth.

         SEM1000/v8/v4 have 4 UC devices and use table entries 1 through 4.
         SEM v12 has 6 upconverter devices and uses table entries 1 through 6.
         It should be noted that user interfaces need only
         display the appropriate data for each SEM type."
::= { semUpConvStatus 2 }

semUpConvStatusEntry OBJECT-TYPE
    SYNTAX SemUpConvStatusEntry
    MAX-ACCESS not-accessible
    STATUS current
    DESCRIPTION
        "A row in the Upconverter Status table."
    INDEX { semUpConvStatusOutputNumber }
::= { semUpConvStatusTable 1 }

SemUpConvStatusEntry ::= SEQUENCE
    {
     semUpConvStatusOutputNumber       Integer32,
     semUpConvStatusEiaChanNumQamB     Integer32,
     semUpConvStatusRfFreqQamB         Integer32,
     semUpConvStatusRfOutLevelError    INTEGER,
     semUpConvStatusIfLevelError       INTEGER,
     semUpConvStatusUpConvError        INTEGER,
     semUpConvStatusTemperature        Integer32,
     semUpConvStatusFault              INTEGER,
     semUpConvStatusStartDigAtten      Integer32,
     semUpConvStatusCurrentDigAtten    Integer32,
     semUpConvStatusCurrentAgc         Integer32,
     semUpConvStatusCurrentAgcLimit    Integer32
    }

semUpConvStatusOutputNumber OBJECT-TYPE
    SYNTAX Integer32 (1..6)
    MAX-ACCESS not-accessible
    STATUS current
    DESCRIPTION
        "The unpconverter number."
::= { semUpConvStatusEntry 1 }

semUpConvStatusEiaChanNumQamB OBJECT-TYPE
    SYNTAX Integer32
    MAX-ACCESS read-only
    STATUS current
    DESCRIPTION
        "This is the EIA Channel that the upconverter is using for the
        second QAM channel associated with the upconverter.  It is computed
        by the SEM based on the frequency of the first channel and channel
        spacing."
::= { semUpConvStatusEntry 2 }

semUpConvStatusRfFreqQamB OBJECT-TYPE
    SYNTAX Integer32
    MAX-ACCESS read-only
    STATUS current
    DESCRIPTION
        "This is the frequency that the upconverter is using for the
        first QAM channel associated with the upconverter.  It is computed
        by the SEM based on the frequency of the first channel and channel
        spacing."
::= { semUpConvStatusEntry 3 }

semUpConvStatusRfOutLevelError OBJECT-TYPE
    SYNTAX INTEGER
        {
         noError   (1),
         highError (2),
         lowError  (3)
        }
    MAX-ACCESS read-only
    STATUS current
    DESCRIPTION
        "Status of RF Output level.  Indicates that it is OK or that
         there is a deviation from the configured level."
::= { semUpConvStatusEntry 4 }

semUpConvStatusIfLevelError OBJECT-TYPE
    SYNTAX INTEGER
        {
         noError   (1),
         highError (2),
         lowError  (3)
        }
    MAX-ACCESS read-only
    STATUS obsolete
    DESCRIPTION
        "Not supported.
        "
::= { semUpConvStatusEntry 5 }

semUpConvStatusUpConvError OBJECT-TYPE
    SYNTAX INTEGER
        {
         noError           (1),
         commError         (2),
         rfHighError       (3),
         rfLowError        (4),
         synthesizerError  (5)
        }
    MAX-ACCESS read-only
    STATUS current
    DESCRIPTION
        "Overall prioritized error status of upconverter.  If there are
         multiple errors, the priority of reporting is as follows from
         lowest to highest priority:
           - No Error      - No Error
           - RF Low Error  - RF output level is lower than configured.  Status also
                             reported in semUpConvStatusRfOutLevelError as 'lowError'.
           - RF High Error - RF level is higher than configured.  Status also reported
                             in semUpConvStatusRfOutLevelError as 'highError'.
           - Synth Error   - UC PLL error.
           - Comm Error    - Failure of host processor to communicate with the UC.

         If more than one error is present, the most severe will be reported."
::= { semUpConvStatusEntry 6 }

semUpConvStatusTemperature OBJECT-TYPE
    SYNTAX Integer32
    MAX-ACCESS read-only
    STATUS current
    DESCRIPTION
        "Upconverter temperature in degrees Celsius."
::= { semUpConvStatusEntry 7 }

semUpConvStatusFault OBJECT-TYPE
    SYNTAX INTEGER
        {
         ok(1),
         indeterminate(2),
         warning(3),
         minor(4),
         major(5),
         critical(6)
        }
    MAX-ACCESS read-only
    STATUS current
    DESCRIPTION
        "Highest current fault condition associated with this Upconverter.
         This is like the semAlarmUpconverterFault but for an individual Upconverter.
         See semAlarmUpconverterFault description for additional information."
::= { semUpConvStatusEntry 8 }

semUpConvStatusStartDigAtten OBJECT-TYPE
    SYNTAX Integer32
    MAX-ACCESS read-only
    STATUS current
    DESCRIPTION
        "The starting digital attenuator setting."
::= { semUpConvStatusEntry 9 }

semUpConvStatusCurrentDigAtten OBJECT-TYPE
    SYNTAX Integer32
    MAX-ACCESS read-only
    STATUS current
    DESCRIPTION
        "The current digital attenuator setting."
::= { semUpConvStatusEntry 10 }

semUpConvStatusCurrentAgc OBJECT-TYPE
    SYNTAX Integer32
    MAX-ACCESS read-only
    STATUS current
    DESCRIPTION
        "The current AGC setting."
::= { semUpConvStatusEntry 11 }

semUpConvStatusCurrentAgcLimit OBJECT-TYPE
    SYNTAX Integer32
    MAX-ACCESS read-only
    STATUS current
    DESCRIPTION
        "The current AGC limit."
::= { semUpConvStatusEntry 12 }


-- ------------------------------------------------------------------------------
--
-- semUpConvModuleStatusTable
--

semUpConvModuleStatusTable OBJECT-TYPE
    SYNTAX SEQUENCE OF SemUpConvModuleStatusEntry
    MAX-ACCESS not-accessible
    STATUS current
    DESCRIPTION
        "Table of status parameters for each of the SEM
         Upconverter Modules.  Currently only the SEM v12
         contains multiple Upconverter module boards.

         The data for the first Upconverter module is
         repeated in entries:
         semUpconverterModuleInstalled,
         semUpconverterModulePldVersion,
         semUpconverterModuleMCN, and
         semUpconverterModuleVersion."
::= { semUpConvStatus 3 }

semUpConvModuleStatusEntry OBJECT-TYPE
    SYNTAX SemUpConvModuleStatusEntry
    MAX-ACCESS not-accessible
    STATUS current
    DESCRIPTION
        "A row in the Upconverter Module Status table."
    INDEX { semUpConvModuleNumber }
::= { semUpConvModuleStatusTable 1 }

SemUpConvModuleStatusEntry ::= SEQUENCE
    {
     semUpConvModuleNumber                   Integer32,
     semUpConvModuleInstalled                InstalledTYPE,
     semUpConvModulePldVersion               Integer32,
     semUpConvModuleMcn                      Integer32,
     semUpConvModuleVersion                  Integer32
    }

semUpConvModuleNumber OBJECT-TYPE
    SYNTAX Integer32
    MAX-ACCESS not-accessible
    STATUS current
    DESCRIPTION
        "Upconverter Board number."
::= { semUpConvModuleStatusEntry 1 }

semUpConvModuleInstalled OBJECT-TYPE
    SYNTAX InstalledTYPE
    MAX-ACCESS read-only
    STATUS current
    DESCRIPTION
        "Indicates whether the Upconverter module is installed in the SEM."
::= { semUpConvModuleStatusEntry 2 }

semUpConvModulePldVersion OBJECT-TYPE
    SYNTAX Integer32
    MAX-ACCESS read-only
    STATUS current
    DESCRIPTION
        "Upconverter module PLD Version."
::= { semUpConvModuleStatusEntry 3 }

semUpConvModuleMcn OBJECT-TYPE
    SYNTAX Integer32
    MAX-ACCESS read-only
    STATUS current
    DESCRIPTION
        "MCN of the Up-converter."
::= { semUpConvModuleStatusEntry 4 }

semUpConvModuleVersion OBJECT-TYPE
    SYNTAX Integer32
    MAX-ACCESS read-only
    STATUS current
    DESCRIPTION
        "Up-converter module version."
::= { semUpConvModuleStatusEntry 5 }


-- ------------------------------------------------------------------------------
--
-- semHostIp
--
-- semHostIpConfig
--
-- semHostIpConfigGeneral
--

semHostIpDefaultGateway OBJECT-TYPE
    SYNTAX IpAddress
    MAX-ACCESS read-write
    STATUS current
    DESCRIPTION
        "This is the IP address of the default gateway for the Host IP interfaces
         of this SEM.

         Once written, a save must be performed via the semSaveConfig
         parameter and the SEM must be rebooted for the change to take effect.

         @Config(config=yes, reboot=yes)
         @Save(semSaveConfig, value=2)
         @File(config.ini, type='ini')
        "
::= { semHostIpConfigGeneral 1 }

semHostIpRoutingApplyChange OBJECT-TYPE
    SYNTAX ApplyDataToDeviceTYPE
    MAX-ACCESS read-write
    STATUS current
    DESCRIPTION
        "Not currently supported.

         @Config(config=no, reboot=no)
        "
--        "The Apply for the Host IP Routing Table.
--
--         This parameter MUST be set to 'apply' in order for any of the data
--         in the semHostIpRoutingTable to take effect in the SEM.  This parameter
--         MUST be set LAST after all other data in the semHostIpRoutingTable has
--         been configured.
--
--         Once written, the change to this parameter will take immediate effect.
--
--         @Config(config=no, reboot=no)
--        "
::= { semHostIpConfigGeneral 2 }

semHostIpMulticastApplyChange OBJECT-TYPE
    SYNTAX ApplyDataToDeviceTYPE
    MAX-ACCESS read-write
    STATUS current
    DESCRIPTION
        "The Apply for the Host IP Multicast Tables (OAM&P and Data IP tables).
         This parameter MUST be set to 'apply' in order for any of the data
         in the semOampMulticastRcvTable or the semDataIpMulticastRcvTable
         to take effect in the SEM.  This parameter MUST be set LAST after all
         other data in these tables have been configured.

         Once written, the change to this parameter will take immediate effect.

         @Config(config=no, reboot=no)
        "
::= { semHostIpConfigGeneral 3 }


-- ------------------------------------------------------------------------------
--
-- semHostIpStatus
--
-- semHostIpStatusGeneral
--

semHostIpMaxInputUdpPorts OBJECT-TYPE
    SYNTAX Integer32
    MAX-ACCESS read-only
    STATUS current
    DESCRIPTION
        "Maximum number of Host Ethernet input UDP ports that can be opened on a
         single Host IP port on this SEM.  Multiply this number by the number of
         Host IP ports on the SEM to get the total for the SEM."
::= { semHostIpStatusGeneral 1 }


-- ------------------------------------------------------------------------------
--
-- semHostIpStatistics
--
-- semHostIpPacketStatisticsTable
--

semHostIpPacketStatisticsTable OBJECT-TYPE
    SYNTAX SEQUENCE OF SemHostIpPacketStatisticsEntry
    MAX-ACCESS not-accessible
    STATUS current
    DESCRIPTION
        "Table of Host Ip Packet Statistics.  Indexed by Host Ip
         Port Num where 1=OAMP; 2=DataIp."
::= { semHostIpStatistics 1 }

semHostIpPacketStatisticsEntry OBJECT-TYPE
    SYNTAX SemHostIpPacketStatisticsEntry
    MAX-ACCESS not-accessible
    STATUS current
    DESCRIPTION
        "A row in the Host Ip Packet Statistics table."
    INDEX { semHostIpPacketStatHostIpPortNum }
::= { semHostIpPacketStatisticsTable 1 }

SemHostIpPacketStatisticsEntry ::= SEQUENCE
    {
     semHostIpPacketStatHostIpPortNum     Integer32,
     semHostIpPacketStatNumRcvPkts        Integer32,
     semHostIpPacketStatNumInsPkts        Integer32,
     semHostIpPacketStatTotRcvPkts        Integer32,
     semHostIpPacketStatTotInsPkts        Integer32,
     semHostIpPacketStatNumDiscardPkts    Integer32,
     semHostIpPacketStatTotDiscardPkts    Integer32
    }

semHostIpPacketStatHostIpPortNum OBJECT-TYPE
    SYNTAX Integer32 (1..2)
    MAX-ACCESS not-accessible
    STATUS current
    DESCRIPTION
        "The Host Ip Port Num where 1=OAMP; 2=DataIp."
::= { semHostIpPacketStatisticsEntry 1 }

semHostIpPacketStatNumRcvPkts OBJECT-TYPE
    SYNTAX Integer32
    MAX-ACCESS read-only
    STATUS current
    DESCRIPTION
        "Number of packets received during the last monitoring
         period (currently 5 seconds)."
::= { semHostIpPacketStatisticsEntry 2 }

semHostIpPacketStatNumInsPkts OBJECT-TYPE
    SYNTAX Integer32
    MAX-ACCESS read-only
    STATUS current
    DESCRIPTION
        "Number of packets inserted during the last monitoring
         period (currently 5 seconds)."
::= { semHostIpPacketStatisticsEntry 3 }

semHostIpPacketStatTotRcvPkts OBJECT-TYPE
    SYNTAX Integer32
    MAX-ACCESS read-only
    STATUS current
    DESCRIPTION
        "Total number of packets received that came in on this
         IP interface."
::= { semHostIpPacketStatisticsEntry 4 }

semHostIpPacketStatTotInsPkts OBJECT-TYPE
    SYNTAX Integer32
    MAX-ACCESS read-only
    STATUS current
    DESCRIPTION
        "Total number of packets inserted that came in on this
         IP interface."
::= { semHostIpPacketStatisticsEntry 5 }

semHostIpPacketStatNumDiscardPkts OBJECT-TYPE
    SYNTAX Integer32
    MAX-ACCESS read-only
    STATUS current
    DESCRIPTION
        "Number of packets discarded during the last monitoring
         period (currently 5 seconds) that came in on this IP
         interface.  See semIpInsertPacketStatTotPkts to see which
         Output Transport Stream(s) are at fault.
         Packets will be discarded when there is not enough buffer
         space.  This may be due to buffer overflow or incorrect
         configuration of semIpConfigInsertionRate."
::= { semHostIpPacketStatisticsEntry 6 }

semHostIpPacketStatTotDiscardPkts OBJECT-TYPE
    SYNTAX Integer32
    MAX-ACCESS read-only
    STATUS current
    DESCRIPTION
        "Total number of packets discarded that came in on this
         IP interface."
::= { semHostIpPacketStatisticsEntry 7 }


-- ------------------------------------------------------------------------------
--
-- semOampConfig
--
-- semOampConfigGeneral
--

semOampIpAddr OBJECT-TYPE
    SYNTAX IpAddress
    MAX-ACCESS read-write
    STATUS current
    DESCRIPTION
        "This is the IP address of the OAMP IP interface of this SEM.
         This IP address is set via a BootP when connected
         to a Bootp server.  When not connected to a BootP server, the IP
         address may directly be changed by setting this parameter.

         Once written, a save must be performed via the semSaveConfig
         parameter and the SEM must be rebooted for the change to take effect.

         @Config(config=yes, reboot=yes)
         @Save(semSaveConfig, value=2)
         @File(config.ini, type='ini')
        "
::= { semOampConfigGeneral 1 }

semOampSubnetMask OBJECT-TYPE
    SYNTAX IpAddress
    MAX-ACCESS read-write
    STATUS current
    DESCRIPTION
        "This is subnet mask of the OAMP IP interface of this SEM.
         The subnet mask is normally via a BootP when connected
         to a BootP server.  When not connected to a Bootp Server, the
         Subnet Mask may directly be changed by setting this parameter.

         Once written, a save must be performed via the semSaveConfig
         parameter and the SEM must be rebooted for the change to take effect.

         @Config(config=yes, reboot=yes)
         @Save(semSaveConfig, value=2)
         @File(config.ini, type='ini')
        "
::= { semOampConfigGeneral 2 }


-- ------------------------------------------------------------------------------
--
-- semOampMulticastRcvTable
--

semOampMulticastRcvTable OBJECT-TYPE
    SYNTAX SEQUENCE OF SemOampMulticastRcvEntry
    MAX-ACCESS not-accessible
    STATUS current
    DESCRIPTION
        "This table is the Multicast Receive configuration table for the
         OAMP Interface.  It is indexed by multicast receive index.

         Once written, the change to this table will only take immediate
         effect after semHostIpMulticastApplyChange is set to 'apply'.

         @Commit(param=semHostIpMulticastApplyChange, value=2)
        "
::= { semOampConfig 9 }

semOampMulticastRcvEntry OBJECT-TYPE
    SYNTAX SemOampMulticastRcvEntry
    MAX-ACCESS not-accessible
    STATUS current
    DESCRIPTION
        "OAMP Interface Multicast Receive Configuration Table Entry."
    INDEX { semOampMulticastRcvIndex }
::= { semOampMulticastRcvTable 1 }

SemOampMulticastRcvEntry ::= SEQUENCE
    {
     semOampMulticastRcvIndex    Integer32,
     semOampMulticastRcvIpAddr   IpAddress,
     semOampMulticastRcvUdpPort  Integer32
    }

semOampMulticastRcvIndex OBJECT-TYPE
    SYNTAX Integer32 (1..16)
    MAX-ACCESS not-accessible
    STATUS current
    DESCRIPTION
        "The Multicast Receive table index."
::= { semOampMulticastRcvEntry 1 }

semOampMulticastRcvIpAddr OBJECT-TYPE
    SYNTAX IpAddress
    MAX-ACCESS read-write
    STATUS current
    DESCRIPTION
        "The Multicast receive IP address (224.0.0.0 to 224.0.0.255 is reserved).
         An IP address of 0.0.0.0 indicates table entry not in use.

         Once written, the change to this table will only take immediate
         effect after semHostIpMulticastApplyChange is set to 'apply'.
         However, in order for the change to persist through subsequent
         reboots or power cycles, the change must be saved via the
         semSaveConfig parameter.

         @Config(config=yes, reboot=no)
         @Save(semSaveConfig, value=2)
         @File(config.ini, type='ini')
        "
::= { semOampMulticastRcvEntry 2 }

semOampMulticastRcvUdpPort OBJECT-TYPE
    SYNTAX Integer32
    MAX-ACCESS read-write
    STATUS current
    DESCRIPTION
        "The Multicast receive UDP Port (1024 to 65535). The SEM will only
         use the new or changed UDP port for multicast data reception when
         the UDP port is first opened. If the UDP Port is currently in use
         for singlecast or broadcast reception, this change will not take
         affect until after the UDP port is closed and then reopened (all
         service and stream routes must be removed to close a UDP port).

         Once written, the change to this table will only take immediate
         effect after semHostIpMulticastApplyChange is set to 'apply'.
         However, in order for the change to persist through subsequent
         reboots or power cycles, the change must be saved via the
         semSaveConfig parameter.

         @Range(min=0, max=65535)
         @Config(config=yes, reboot=no)
         @Save(semSaveConfig, value=2)
         @File(config.ini, type='ini')
        "
::= { semOampMulticastRcvEntry 3 }


-- ------------------------------------------------------------------------------
--
-- semOampStatus
--
-- semOampStatusGeneral
--

semOampMacAddr OBJECT-TYPE
    SYNTAX DisplayString (SIZE (0..17))
    MAX-ACCESS read-only
    STATUS current
    DESCRIPTION
        "This is the MAC address of the SEM OAMP IP Interface.
         It is set at the factory and cannot be changed.
         The string length is 17 characters in the format
         'hh:hh:hh:hh:hh:hh' where 'hh' is a hexadecimal number."
::= { semOampStatusGeneral 1 }

semOampNumberInputStreams OBJECT-TYPE
    SYNTAX Integer32
    MAX-ACCESS read-only
    STATUS current
    DESCRIPTION
        "Number of input streams on the SEM OAMP IP Interface. This is the maximum
         number of UDP Ports that can be opened on this interface."
::= { semOampStatusGeneral 2 }

semOampPortSpeed OBJECT-TYPE
    SYNTAX INTEGER
        {
          portSpeed10Mbps  (1),
          portSpeed100Mbps (2)
        }
    MAX-ACCESS read-only
    STATUS current
    DESCRIPTION
        "OAM&P Ethernet speed (10Mbps or 100Mbps). This is determined by the results of the
         auto-negotiation process. If auto-negotiation fails, the default speed is 100Mbps."
::= { semOampStatusGeneral 3 }

semOampPortDuplexMode OBJECT-TYPE
    SYNTAX INTEGER
        {
          halfDuplex (1),
          fullDuplex (2)
        }
    MAX-ACCESS read-only
    STATUS current
    DESCRIPTION
        "OAM&P Ethernet Duplex Mode (full or half) This is determined by the results of the
         auto-negotiation process. If auto-negotiation fails, the default mode is Full."
::= { semOampStatusGeneral 4 }

semOampAutoNegotiate OBJECT-TYPE
    SYNTAX EnableDisableTYPE
    MAX-ACCESS read-only
    STATUS current
    DESCRIPTION
        "OAM&P Ethernet Auto-Negotiation setting. This setting is predefined by the SEM
         during the network stack initialization process. It is not user configurable."
::= { semOampStatusGeneral 5 }


-- ------------------------------------------------------------------------------
--
-- semDataIpConfig
--
-- semDataIpConfigGeneral
--

semDataIpAddr OBJECT-TYPE
    SYNTAX IpAddress
    MAX-ACCESS read-write
    STATUS current
    DESCRIPTION
        "This is the IP address of the Data IP interface of this SEM.
         The data IP address may directly be changed by setting this parameter.
         The Data IP address must be configured such that the Data IP interface
         and the OAM&P interface are on different networks.

         Once written, a save must be performed via the semSaveConfig
         parameter and the SEM must be rebooted for the change to take effect.

         @Config(config=yes, reboot=yes)
         @Save(semSaveConfig, value=2)
         @File(config.ini, type='ini')
        "
::= { semDataIpConfigGeneral 1 }

semDataIpSubnetMask OBJECT-TYPE
    SYNTAX IpAddress
    MAX-ACCESS read-write
    STATUS current
    DESCRIPTION
        "This is subnet mask of the Data IP interface of this SEM.
         The data IP Subnet Mask may directly be changed by setting this parameter.

         Once written, a save must be performed via the semSaveConfig
         parameter and the SEM must be rebooted for the change to take effect.

         @Config(config=yes, reboot=yes)
         @Save(semSaveConfig, value=2)
         @File(config.ini, type='ini')
        "
::= { semDataIpConfigGeneral 2 }


-- ------------------------------------------------------------------------------
--
-- semDataIpMulticastRcvTable
--

semDataIpMulticastRcvTable OBJECT-TYPE
    SYNTAX SEQUENCE OF SemDataIpMulticastRcvEntry
    MAX-ACCESS not-accessible
    STATUS current
    DESCRIPTION
        "This table is the Multicast Receive configuration table for the
         Data Ip Interface.  It is indexed by multicast receive index.

         Once written, the change to this table will only take immediate
         effect after semHostIpMulticastApplyChange is set to 'apply'.
        "
::= { semDataIpConfig 9 }

semDataIpMulticastRcvEntry OBJECT-TYPE
    SYNTAX SemDataIpMulticastRcvEntry
    MAX-ACCESS not-accessible
    STATUS current
    DESCRIPTION
        "Data Ip Interface Multicast Receive Configuration Table Entry."
    INDEX { semDataIpMulticastRcvIndex }
::= { semDataIpMulticastRcvTable 1 }

SemDataIpMulticastRcvEntry ::= SEQUENCE
    {
     semDataIpMulticastRcvIndex    Integer32,
     semDataIpMulticastRcvIpAddr   IpAddress,
     semDataIpMulticastRcvUdpPort  Integer32
    }

semDataIpMulticastRcvIndex OBJECT-TYPE
    SYNTAX Integer32 (1..16)
    MAX-ACCESS not-accessible
    STATUS current
    DESCRIPTION
        "The Multicast Receive table index."
::= { semDataIpMulticastRcvEntry 1 }

semDataIpMulticastRcvIpAddr OBJECT-TYPE
    SYNTAX IpAddress
    MAX-ACCESS read-write
    STATUS current
    DESCRIPTION
        "The Multicast receive IP address (224.0.0.0 to 224.0.0.255 is reserved).
         An IP address of 0.0.0.0 indicates table entry not in use.

         Once written, the change to this table will only take immediate
         effect after semHostIpMulticastApplyChange is set to 'apply'.
         However, in order for the change to persist through subsequent
         reboots or power cycles, the change must be saved via the
         semSaveConfig parameter.

         @Commit(param=semHostIpMulticastApplyChange, value=2)
         @Config(config=yes, reboot=no)
         @Save(semSaveConfig, value=2)
         @File(config.ini, type='ini')
        "
::= { semDataIpMulticastRcvEntry 2 }

semDataIpMulticastRcvUdpPort OBJECT-TYPE
    SYNTAX Integer32
    MAX-ACCESS read-write
    STATUS current
    DESCRIPTION
        "The Multicast receive UDP Port (1024 to 65535). The SEM will only
         use the new or changed UDP port for multicast data reception when
         the UDP port is first opened. If the UDP Port is currently in use
         for singlecast or broadcast reception, this change will not take
         affect until after the UDP port is closed and then reopened (all
         service and stream routes must be removed to close a UDP port).

         Once written, the change to this table will only take immediate
         effect after semHostIpMulticastApplyChange is set to 'apply'.
         However, in order for the change to persist through subsequent
         reboots or power cycles, the change must be saved via the
         semSaveConfig parameter.

         @Range(min=0, max=65535)
         @Commit(param=semHostIpMulticastApplyChange, value=2)
         @Config(config=yes, reboot=no)
         @Save(semSaveConfig, value=2)
         @File(config.ini, type='ini')
        "
::= { semDataIpMulticastRcvEntry 3 }


-- ------------------------------------------------------------------------------
--
-- semDataIpStatus
--
-- semDataIpStatusGeneral
--

semDataIpMacAddr OBJECT-TYPE
    SYNTAX DisplayString (SIZE (0..17))
    MAX-ACCESS read-only
    STATUS current
    DESCRIPTION
        "This is the MAC address of the SEM Data IP Interface.
         It is set at the factory and cannot be changed.
         The string length is 17 characters in the format
         'hh:hh:hh:hh:hh:hh' where 'hh' is a hexadecimal number."
::= { semDataIpStatusGeneral 1 }

semDataIpNumberInputStreams OBJECT-TYPE
    SYNTAX Integer32
    MAX-ACCESS read-only
    STATUS current
    DESCRIPTION
        "Number of input streams on the SEM Data IP Interface. This is the maximum number
         of UDP Ports that can be opened on this interface. If this number is 0, then this
         interface is not enabled and cannot be used."
::= { semDataIpStatusGeneral 2 }

semDataIpPortSpeed OBJECT-TYPE
    SYNTAX INTEGER
        {
          portSpeed10Mbps  (1),
          portSpeed100Mbps (2)
        }
    MAX-ACCESS read-only
    STATUS current
    DESCRIPTION
        "Data IP Ethernet speed (10Mbps or 100Mbps). This is determined by the results of the
         auto-negotiation process. If auto-negotiation fails, the default speed is 100Mbps. This
         status item is only valid when the Data IP port is enabled and properly configured."
::= { semDataIpStatusGeneral 3 }

semDataIpPortDuplexMode OBJECT-TYPE
    SYNTAX INTEGER
        {
          halfDuplex (1),
          fullDuplex (2)
        }
    MAX-ACCESS read-only
    STATUS current
    DESCRIPTION
        "Data IP Ethernet Duplex Mode (full or half) This is determined by the results of the
         auto-negotiation process. If auto-negotiation fails, the default mode is Full. This
         status item is only valid when the Data IP port is enabled and properly configured."
::= { semDataIpStatusGeneral 4 }

semDataIpAutoNegotiate OBJECT-TYPE
    SYNTAX EnableDisableTYPE
    MAX-ACCESS read-only
    STATUS current
    DESCRIPTION
        "Data IP Ethernet Auto-Negotiation setting. This setting is predefined by the SEM
         during the network stack initialization process. It is not user configurable. This
         status item is only valid when the Data IP port is enabled and properly configured."
::= { semDataIpStatusGeneral 5 }


-- ------------------------------------------------------------------------------
--
-- semAcp
--
-- semAcpConfig
--
-- semAcpConfigGeneral
--

semAcpEncryptAlgorithm OBJECT-TYPE
    SYNTAX INTEGER
        {
          des (1),
          csa (2)
        }
    MAX-ACCESS read-write
    STATUS current
    DESCRIPTION
        "Controls the current scrambling mode of the SEM ACPs.
         1 - DES (DCII, North American)
         2 - CSA (DVB Common Scrambling Algorithm)

         This field is only applicable when the SEM is externally controlled
         and has an ACP Module installed.

         Once written, a save must be performed via the semSaveConfig
         parameter and the SEM must be rebooted for the change to take effect.

         @Config(config=yes, reboot=yes)
         @Save(semSaveConfig, value=2)
         @File(config.ini, type='ini')
        "
::= { semAcpConfigGeneral 1 }

semAcpReProgramControlFpga OBJECT-TYPE
    SYNTAX INTEGER
        {
          retainCurrentProgram      (1),
          initiateReProgramSequence (2)
        }
    MAX-ACCESS read-write
    STATUS current
    DESCRIPTION
        "Setting to initiateReProgramSequence initiates an ACP
         Control FPGA reprogramming sequence.

         THIS PROCESS TAKES APPROXIMATELY TWENTY MINUTES, DURING
         WHICH THE SEM WILL BE AUTOMATICALLY REBOOTED!!

         This is intended for use by, or under direction of, a
         Motorola Field Engineer.

         Once written, the change to this parameter will take immediate effect.

         @Config(config=no, reboot=no)
        "
::= { semAcpConfigGeneral 2 }


-- ------------------------------------------------------------------------------
--
-- semAcpStatus
--
-- semAcpStatusGeneral
--

semAcpModuleInstalled OBJECT-TYPE
    SYNTAX InstalledTYPE
    MAX-ACCESS read-only
    STATUS current
    DESCRIPTION
        "Indicates whether the ACP module is installed in the SEM."
::= { semAcpStatusGeneral 1 }

semAcpWkePeriod OBJECT-TYPE
    SYNTAX Integer32
    MAX-ACCESS read-only
    STATUS current
    DESCRIPTION
        "Indicates current Working Key Epoch which on the
         sem1000 is system wide in scope. The number is returned
         in units of 1/30 of a second."
::= { semAcpStatusGeneral 2 }

semAcpUnitCreatedAs OBJECT-TYPE
    SYNTAX Integer32(1 | 2)
    MAX-ACCESS read-only
    STATUS current
    DESCRIPTION
        "Indicates whether the ACP module was unit created as a satellite or cable
         type. This information is obtained from the ACP module during initialization.
         enumerated type {Cable (1), Satellite(2)}"
::= { semAcpStatusGeneral 3 }


-- ------------------------------------------------------------------------------
--
-- semAcpModule
--

semAcpBoardType OBJECT-TYPE
    SYNTAX Integer32
    MAX-ACCESS read-only
    STATUS current
    DESCRIPTION
        "A numeric code identifying the board type of the installed acp module.
         The value is under the control of the acp hardware designers. MIB Manager
         software should avoid directly using this code to implement modal behavior.
         This value is only provided for identification purposes only"
::= { semAcpModule 1 }

semAcpBoardVersion OBJECT-TYPE
    SYNTAX DisplayString
    MAX-ACCESS read-only
    STATUS current
    DESCRIPTION
        "The ACP board version is displayed as a string 'xx.yy' where
         xx indicates the PWB version, and yy indicates the BOM version.
         The value returned is determined by reading a register in the
         ACP modules memory map. MIB Manager software should avoid directly
         using this code to implement modal behavior.
         This value is provided for identification purposes only."
::= { semAcpModule 2 }

semAcpFpgaVersion OBJECT-TYPE
    SYNTAX Integer32
    MAX-ACCESS read-only
    STATUS current
    DESCRIPTION
        "A numeric code identifying the FPGA version of the installed acp module.
         The value is under the control of the acp hardware designers. MIB Manager
         software should avoid directly using this code to implement modal behavior.
         This value is provided for identification purposes only."
::= { semAcpModule 3 }

semAcpCascadeUnitSize OBJECT-TYPE
    SYNTAX Integer32
    MAX-ACCESS read-only
    STATUS current
    DESCRIPTION
        "The ACP module architecture only allows sequential chaining of ACP units
         for a given output transport. The number of ACP unit chains is fixed at 16
         for serial mode and 4 for parallel mode independent of MC versions. The
         cascade unit size is the minimum granularity of acp chaining. As an example
         for the MC 1.7 case there are 48 ACPs distributed on the 16 chains for a
         cascade unit size of 3 ACPs."
::= { semAcpModule 4 }

semAcpServicesPerCU OBJECT-TYPE
    SYNTAX Integer32
    MAX-ACCESS read-only
    STATUS current
    DESCRIPTION
        "Equals the number of services that may be encrypted on a single cascade unit.
         It represents the minimum granularity with which encryption capacity in terms
         of services may be distributed between transports. For the MC 1.7 case there
         can be 2 services encrypted per ACP and there are 3 ACPs in a cascade unit so
         6 services may be encrypted per cascade unit."
::= { semAcpModule 5 }

semAcpCascadeUnitCount OBJECT-TYPE
    SYNTAX Integer32
    MAX-ACCESS read-only
    STATUS current
    DESCRIPTION
        "Equals the total number of cascade units."
::= { semAcpModule 6 }


-- ------------------------------------------------------------------------------
--
-- semAcpStatusTransportTable
--

semAcpStatusTransportTable OBJECT-TYPE
    SYNTAX SEQUENCE OF SemAcpStatusTransportEntry
    MAX-ACCESS not-accessible
    STATUS current
    DESCRIPTION
        "This table contains read-only information about MC routing
         within the ACP module. It is indexed by output transport."
::= { semAcpStatus 3 }

semAcpStatusTransportEntry OBJECT-TYPE
    SYNTAX SemAcpStatusTransportEntry
    MAX-ACCESS not-accessible
    STATUS current
    DESCRIPTION
        "Acp Status Transport Entry."
    INDEX { semAcpTransportIndex }
::= { semAcpStatusTransportTable 1 }

SemAcpStatusTransportEntry ::= SEQUENCE
    {
       semAcpTransportIndex         Integer32,
       semAcpFirstAcpNumber         Integer32,
       semAcpLastAcpNumber          Integer32,
       semAcpServAuthFailedCount    Integer32
    }

semAcpTransportIndex OBJECT-TYPE
    SYNTAX Integer32(1..16)
    MAX-ACCESS not-accessible
    STATUS current
    DESCRIPTION
        "Output Transport Index Number."
::= { semAcpStatusTransportEntry 1 }

semAcpFirstAcpNumber OBJECT-TYPE
    SYNTAX Integer32
    MAX-ACCESS read-only
    STATUS current
    DESCRIPTION
        "The acp number (1 based) of the first acp in the acp chain
         assigned to this output transport. The SEM ACP module design
         only allows sequential acp numbers to be cascaded."
::= { semAcpStatusTransportEntry 2 }

semAcpLastAcpNumber OBJECT-TYPE
    SYNTAX Integer32
    MAX-ACCESS read-only
    STATUS current
    DESCRIPTION
        "The acp number (1 based) of the last acp in the acp chain
         assigned to this output transport. The SEM ACP module design
         only allows sequential acp numbers to be cascaded."
::= { semAcpStatusTransportEntry 3 }

semAcpServAuthFailedCount OBJECT-TYPE
    SYNTAX Integer32
    MAX-ACCESS read-only
    STATUS current
    DESCRIPTION
        "Totals all services with failed authorization status on this transport.
         Zero indicates that all services that should be authorized are authorized.
         If there are no encrypted services then a zero is returned.
         Positive non-zero values represent the number of services that are not
         authorized for encryption.
         If for some reason the information cannot be returned a -1 would be
         returned indicating a problem with the acp module interface."
::= { semAcpStatusTransportEntry 4 }


-- ------------------------------------------------------------------------------
--
-- semAcpStatusTable
--

semAcpStatusTable OBJECT-TYPE
    SYNTAX SEQUENCE OF SemAcpStatusEntry
    MAX-ACCESS not-accessible
    STATUS current
    DESCRIPTION
        "This table contains read-only information about each individual ACP or MC
         within the ACP module. It is indexed by ACP index number."
::= { semAcpStatus 4 }

semAcpStatusEntry OBJECT-TYPE
    SYNTAX SemAcpStatusEntry
    MAX-ACCESS not-accessible
    STATUS current
    DESCRIPTION
        "Acp Status Table Entry."
    INDEX { semAcpIndex }
::= { semAcpStatusTable 1 }

SemAcpStatusEntry ::= SEQUENCE
    {
       semAcpIndex            Integer32,
       semAcpUnitAddress      DisplayString,
       semAcpOutputTransport  Integer32
    }

semAcpIndex OBJECT-TYPE
    SYNTAX Integer32(1..64)
    MAX-ACCESS not-accessible
    STATUS current
    DESCRIPTION
        "The acp index number, the acp module architecture limits
         the number of acps to no more than 64 acps.
         For the actual number of encrypt acps see acpNumberofEncryptTypes"

::= { semAcpStatusEntry 1 }

semAcpUnitAddress OBJECT-TYPE
    SYNTAX DisplayString (SIZE (20))
    MAX-ACCESS read-only
    STATUS current
    DESCRIPTION
        "Unit address of this ACP in human readable form.
         Format is decimal digits grouped in 3-5-5-3 format.
         A typical address would look like: '123-45678-87654-321'."
::= { semAcpStatusEntry 2 }

semAcpOutputTransport OBJECT-TYPE
    SYNTAX Integer32(0..16)
    MAX-ACCESS read-only
    STATUS current
    DESCRIPTION
        "Specifies which output transport if any this acp is assigned to.
         If assigned to a valid transport the number will be in the 1-16 range.
         If this acp is not used on any transport a zero is returned"
::= { semAcpStatusEntry 3 }


-- ------------------------------------------------------------------------------
--
-- semOutputTransport
--
-- semOutTransConfig
--
-- semOutTransConfigGeneral
--

semPcrOffset OBJECT-TYPE
    SYNTAX Integer32
    MAX-ACCESS read-write
    STATUS current
    DESCRIPTION
        "The PCR Offset.  Maximum value is 131071.

         Once written, the change to this parameter will take immediate
         effect.  However, in order for the change to persist through
         subsequent reboots or power cycles, the change must be saved via
         the semSaveConfig parameter.

         @Range(min=0, max=131071)
         @Config(config=yes, reboot=no)
         @Save(semSaveConfig, value=2)
         @File(config.ini, type='ini')
        "
::= { semOutTransConfigGeneral 1 }

semOutTransHighLowSpeedMode OBJECT-TYPE
    SYNTAX INTEGER
        {
         highSpeed (1),
         lowSpeed  (2)
        }
    MAX-ACCESS read-write
    STATUS current
    DESCRIPTION
        "SEM Output Transport Stream High or Low Speed Mode.
         The SEM can support a High Speed mode (limited to a maximum of four
         Output Transport Streams and limited to OTS 1-4) and a Low Speed mode
         (all OTS may be used).  The SEM will configure
         internal routing of resources based on the mode.
            1) High Speed Mode - The user is limited to use of Output Transport
               Streams 1 to 4, and can have data rates up to 206 Mbps for unencrypted
               streams.  Maximum encrypted data rates will vary depending on the
               capabilities of the Access Control Processors installed in the SEM.
               In High Speed Mode the user is not limited to configuring stream
               data rates of greater than 53 Mbps.
            2) Low Speed Mode - The user may use all Output Transport Streams but
               is limited to a maximum of 53 Mbps.  The streams may be encrypted
               or unencrypted.

         Once written, a save must be performed via the semSaveConfig
         parameter and the SEM must be rebooted for the change to take effect.

         @Config(config=yes, reboot=yes)
         @Save(semSaveConfig, value=2)
         @File(config.ini, type='ini')
        "
::= { semOutTransConfigGeneral 2 }


-- ------------------------------------------------------------------------------
--
-- semOutTransStreamTable
--

semOutTransStreamTable OBJECT-TYPE
    SYNTAX SEQUENCE OF SemOutTransStreamEntry
    MAX-ACCESS not-accessible
    STATUS current
    DESCRIPTION
        "This is a table of configuration parameters for the sixteen
         Output Transport Streams.

         @Config(config=yes, reboot=yes)
         @Save(semSaveConfig, value=2)
         @File(config.ini, type='ini')
        "
::= { semOutTransConfig 2 }

semOutTransStreamEntry OBJECT-TYPE
    SYNTAX SemOutTransStreamEntry
    MAX-ACCESS not-accessible
    STATUS current
    DESCRIPTION
        "Output Transport Stream Configuration Table Entry."
    INDEX { semOutTransStreamStreamNum }
::= { semOutTransStreamTable 1 }

SemOutTransStreamEntry ::= SEQUENCE
    {
     semOutTransStreamStreamNum            Integer32,
     semOutTransStreamEnable               EnableDisableTYPE,
     semOutTransStreamPhysOutType          INTEGER,
     semOutTransStreamPhysOutPort          Integer32,
     semOutTransStreamClockAssigned        Integer32,
     semOutTransStreamNumEncryptPrograms   Integer32
    }

semOutTransStreamStreamNum OBJECT-TYPE
    SYNTAX Integer32(1..16)
    MAX-ACCESS not-accessible
    STATUS current
    DESCRIPTION
        "Output Transport Stream Number."
::= { semOutTransStreamEntry 1 }

semOutTransStreamEnable OBJECT-TYPE
    SYNTAX EnableDisableTYPE
    MAX-ACCESS read-write
    STATUS current
    DESCRIPTION
        "This parameter indicates that the Output Transport Stream
         is configured and in use.

         Once written, a save must be performed via the semSaveConfig
         parameter and the SEM must be rebooted for the change to take effect.
        "
::= { semOutTransStreamEntry 2 }

semOutTransStreamPhysOutType OBJECT-TYPE
    SYNTAX INTEGER
        {
         gbe (1),
         asi (2),
         qam (4)
        }
    MAX-ACCESS read-write
    STATUS current
    DESCRIPTION
        "The physical interface type to which this Output Transport Stream
         is to be routed.  The settings are limited to the following:
           - gbe - for any stream 1-16
                   Notes on GbE:
                   SEM1000/SEM v8/SEM v4:
                   1) There are three GbE outputs on the SEM.
                   SEM v12:
                   1) There are two GbE outputs on the SEM.
           - asi - only for streams 1-4, depending on product
                   Notes on ASI:
                   SEM v12:
                   1) There are no ASI outputs on the SEM.
           - qam - for streams 1-16, depending on product
                   Notes on QAM:
                   SEM1000/SEM v8:  streams 9-16
                   1) There are four upconverters on the SEM.
                   2) Each upconverter has two QAM channels associated with it.
                   3) They are grouped such that Output Transport Streams
                      9 & 10 are associated with Upconverter 1,
                      OTS 11 & 12 with UC 2, OTS 13 & 14 with UC 3,
                      and 15 & 16 with UC 4.  These are referred to
                      as QAM1A, QAM1B, QAM2A, QAM2B, etc.
                   4) When only one QAM channel of UC pair is to be enabled, it
                      must be the first QAM of the pair, e.g., 9, 11, 13, and 15,
                      or the SEM will flag the configuration as invalid and disable
                      the Output Transport Stream.
                   5) The first channel of a QAM pair must be enabled when the
                      second channel is enabled or the SEM will flag the configuration
                      as invalid and disable the Output Transport Stream.  This is
                      necessary because the configuration of the first QAM channel
                      of a pair is used as a basis for configuring the second QAM
                      channel of the pair.
                   SEM v4:  streams 9, 11, 13, and 15
                   1) Is IF only and has a QAM module without an upconverter.
                   2) Is four channel.
                   3) Utilizes the 'A' channels of a SEM1000/SEM v8.  Therefore,
                      only Output Transport Streams 9, 11, 13, and 15 may be set
                      to QAM.
                   SEM v12:  streams 1-12
                   1) There are six upconverters on the SEM.
                   2) Each upconverter has two QAM channels associated with it.
                   3) They are grouped such that Output Transport Streams
                      1 & 2 are associated with Upconverter 1,
                      OTS 3 & 4 with UC 2, OTS 5 & 6 with UC 3,
                      OTS 7 & 8 with UC 4, OTS 9 & 10 with UC 5,
                      and OTS 11 & 12 with UC 6.  These are referred
                      to as QAM1A, QAM1B, QAM2A, QAM2B, etc.
                   4) When only one QAM channel of UC pair is to be enabled, it
                      must be the first QAM of the pair, e.g., 1, 3, 5, 7, 9, 11
                      or the SEM will flag the configuration as invalid and disable
                      the Output Transport Stream.
                   5) The first channel of a QAM pair must be enabled when the
                      second channel is enabled or the SEM will flag the configuration
                      as invalid and disable the Output Transport Stream.  This is
                      necessary because the configuration of the first QAM channel
                      of a pair is used as a basis for configuring the second QAM
                      channel of the pair.

         Once written, a save must be performed via the semSaveConfig
         parameter and the SEM must be rebooted for the change to take effect.
        "
::= { semOutTransStreamEntry 3 }

semOutTransStreamPhysOutPort OBJECT-TYPE
    SYNTAX Integer32
    MAX-ACCESS read-write
    STATUS current
    DESCRIPTION
        "Number of the output, of type configured by PhysOutType,
         to which this Output Transport Stream is routed.
         The user configured value is ignored by the SEM.
         For ASI and QAM the value is set by the SEM.
         Not used or set for GBE.

         @Config(config=no, reboot=no)
        "
::= { semOutTransStreamEntry 4 }

semOutTransStreamClockAssigned OBJECT-TYPE
    SYNTAX Integer32(0..8)
    MAX-ACCESS read-write
    STATUS current
    DESCRIPTION
        "Number of the clock to use for this output transport stream.
         The SEM has eight clocks.
         This is used as the index into semOutputClockConfigTable.
         The clock rate must be configured (non-zero) in semOutputClockConfigTable
         to be a valid selection.
         Zero indicates no clock is assigned.  Zero can only be selected for disabled
         Output Transport Streams.  A clock must be assigned for an enabled Output
         Transport Stream.
         For dynamic configuration of the clock selection:
           - If the Output Transport Stream is enabled, the clock rate of the clock
             selected must be within the limits based on the semOutTransHighLowSpeedMode
             the SEM is in.
         Clock Assigned is not applicable or used for QAM output.  QAM rates
         are configured in qamConfig.

         Once written, the change to this parameter will take immediate
         effect.  However, in order for the change to persist through
         subsequent reboots or power cycles, the change must be saved via
         the semSaveConfig parameter.

         @Config(config=yes, reboot=no)
        "
::= { semOutTransStreamEntry 5 }

semOutTransStreamNumEncryptPrograms OBJECT-TYPE
    SYNTAX Integer32
    MAX-ACCESS read-write
    STATUS current
    DESCRIPTION
        "Number of programs that can be encrypted in the output transport stream.
         This parameter is subject to 2 constraints for this number. First only
         integer multiples of semAcpServicesPerCU are valid. Second the combined
         encrypted service count for all transports cannot exceed the acp modules
         capacity. Encrypted services shall be allocated on a first come first serve
         basis.

         This field is only applicable when the SEM is externally controlled
         and has an ACP Module installed.

         Once written, a save must be performed via the semSaveConfig
         parameter and the SEM must be rebooted for the change to take effect.

         @Range(min=0)
        "
::= { semOutTransStreamEntry 6 }


-- ------------------------------------------------------------------------------
--
-- semOutputClockConfigTable
--

semOutputClockConfigTable OBJECT-TYPE
    SYNTAX SEQUENCE OF SemOutputClockConfigEntry
    MAX-ACCESS not-accessible
    STATUS current
    DESCRIPTION
        "This is a table of configuration parameters for the eight
         SEM clocks."
::= { semOutTransConfig 3 }

semOutputClockConfigEntry OBJECT-TYPE
    SYNTAX SemOutputClockConfigEntry
    MAX-ACCESS not-accessible
    STATUS current
    DESCRIPTION
        "Output Clock Configuration Table Entry."
    INDEX { semOutputClockConfigNum }
::= { semOutputClockConfigTable 1 }

SemOutputClockConfigEntry ::= SEQUENCE
    {
     semOutputClockConfigNum            Integer32,
     semOutputClockConfigRate           Integer32
    }

semOutputClockConfigNum OBJECT-TYPE
    SYNTAX Integer32(1..8)
    MAX-ACCESS not-accessible
    STATUS current
    DESCRIPTION
        "Output Clock Number."
::= { semOutputClockConfigEntry 1 }

semOutputClockConfigRate OBJECT-TYPE
    SYNTAX Integer32 (0 | 1000000..206000000)
    MAX-ACCESS read-write
    STATUS current
    DESCRIPTION
        "Rate for this clock in bits per second (bps).
         Zero indicates clock not in use.  Clock cannot be set to zero
         if it is in use by an enabled Output Transport Stream.
         Minimum is 1,000,000 bps.
         Maximum is 206,000,000 bps.
         Because of clock granularity, SEM clocks cannot be set to the
         exact value the user has selected.  The actual clock rate set
         in the SEM can be found in the semOutputClockStatusTable.
         Changing clock rates:
           - If a clock is not in use by an enabled Output Transport Stream
             any rate in the entire range can be selected.
           - If a clock is in use by an enabled Output Transport Stream
             the rate is limited based on the semOutTransHighLowSpeedMode
             the SEM is in.

         Once written, the change to this parameter will take immediate
         effect.  However, in order for the change to persist through
         subsequent reboots or power cycles, the change must be saved via
         the semSaveConfig parameter.

         @Config(config=yes, reboot=no)
         @Save(semSaveConfig, value=2)
         @File(config.ini, type='ini')
        "
::= { semOutputClockConfigEntry 2 }


-- ------------------------------------------------------------------------------
--
-- semOutTransUtilizationMonitoring
--
-- semOutTransUtilizationMonitorGeneral
--

semOutTransUtilMonAlarmThreshold OBJECT-TYPE
    SYNTAX Integer32 (0..100)
    MAX-ACCESS read-write
    STATUS current
    DESCRIPTION
        "The threshold, in percent, used to produce the
         semAlarmOtsUtilizationFault alarm 'minor' while
         monitoring Output Transport Stream Bandwidth Utilization.
         An alarm of 'minor' will occur when this threshold is met
         or exceeded for semOutTransUtilMonSetAlarmDelay.  The alarm
         will clear after remaining below this threshold for
         semOutTransUtilMonClearAlarmDelay.  The SEM will only
         use this parameter when one or more OTS are enabled to
         be monitored via semOutTransUtilMonEnable.

         Once written, the change to this parameter will take immediate
         effect.  However, in order for the change to persist through
         subsequent reboots or power cycles, the change must be saved via
         the semSaveConfig parameter.

         @Config(config=yes, reboot=no)
         @Save(semSaveConfig, value=2)
         @File(config.ini, type='ini')
        "
::= { semOutTransUtilizationMonitorGeneral 1 }

semOutTransUtilMonSetAlarmDelay OBJECT-TYPE
    SYNTAX Integer32
    MAX-ACCESS read-write
    STATUS current
    DESCRIPTION
        "This is the time in seconds that the Output Transport Stream
         must be at or exceeding semOutTransUtilMonAlarmThreshold before
         setting the semAlarmOtsUtilizationFault alarm.  The SEM will
         only use this parameter when one or more OTS are enabled to
         be monitored via semOutTransUtilMonEnable.

         Once written, the change to this parameter will take immediate
         effect.  However, in order for the change to persist through
         subsequent reboots or power cycles, the change must be saved via
         the semSaveConfig parameter.

         @Range(min=0)
         @Config(config=yes, reboot=no)
         @Save(semSaveConfig, value=2)
         @File(config.ini, type='ini')
        "
::= { semOutTransUtilizationMonitorGeneral 2 }

semOutTransUtilMonClearAlarmDelay OBJECT-TYPE
    SYNTAX Integer32
    MAX-ACCESS read-write
    STATUS current
    DESCRIPTION
        "This is the time in seconds that the Output Transport Stream
         must be below semOutTransUtilMonAlarmThreshold before
         setting the semAlarmOtsUtilizationFault alarm.  The SEM will
         only use this parameter when one or more OTS are enabled to
         be monitored via semOutTransUtilMonEnable.

         Once written, the change to this parameter will take immediate
         effect.  However, in order for the change to persist through
         subsequent reboots or power cycles, the change must be saved via
         the semSaveConfig parameter.

         @Range(min=0)
         @Config(config=yes, reboot=no)
         @Save(semSaveConfig, value=2)
         @File(config.ini, type='ini')
        "
::= { semOutTransUtilizationMonitorGeneral 3 }


-- ------------------------------------------------------------------------------
--
-- semOutTransUtilizationMonitorTable
--

semOutTransUtilizationMonitorTable OBJECT-TYPE
    SYNTAX SEQUENCE OF SemOutTransUtilizationMonitorEntry
    MAX-ACCESS not-accessible
    STATUS current
    DESCRIPTION
        "This is a table of configuration parameters for Rate Monitoring
         of the Output Transport Stream Bandwidth Utilization.  Utilization
         information is accessed via semOutTransUtilizationTable."
::= { semOutTransUtilizationMonitoring 2 }

semOutTransUtilizationMonitorEntry OBJECT-TYPE
    SYNTAX SemOutTransUtilizationMonitorEntry
    MAX-ACCESS not-accessible
    STATUS current
    DESCRIPTION
        "Output Transport Rate Monitoring Configuration Table Entry."
    INDEX { semOutTransUtilMonStreamNum }
::= { semOutTransUtilizationMonitorTable 1 }

SemOutTransUtilizationMonitorEntry ::= SEQUENCE
    {
     semOutTransUtilMonStreamNum          Integer32,
     semOutTransUtilMonEnable             EnableDisableTYPE,
     semOutTransUtilMonFlushHistory       FlushTYPE,
     semOutTransUtilMonFlushStart         Integer32,
     semOutTransUtilMonFlushEnd           Integer32
    }

semOutTransUtilMonStreamNum OBJECT-TYPE
    SYNTAX Integer32(1..16)
    MAX-ACCESS not-accessible
    STATUS current
    DESCRIPTION
        "Output Transport Stream Number."
::= { semOutTransUtilizationMonitorEntry 1 }

semOutTransUtilMonEnable OBJECT-TYPE
    SYNTAX EnableDisableTYPE
    MAX-ACCESS read-write
    STATUS current
    DESCRIPTION
        "Setting to 'enable' enables rate monitoring of the Output Transport Stream.
         Only output transport streams that are enabled via semOutTransStreamEnable
         may be monitored.
         Bandwidth utilization statistics are found in semOutTransUtilizationTable.
         Data in semOutTransUtilizationTable will not be cleared when monitoring
         is disabled for the Output Transport Stream.  However, the data will be
         cleared when monitoring is re-enabled.

         Once written, the change to this parameter will take immediate
         effect.  However, in order for the change to persist through
         subsequent reboots or power cycles, the change must be saved via
         the semSaveConfig parameter.

         @Config(config=yes, reboot=no)
         @Save(semSaveConfig, value=2)
         @File(config.ini, type='ini')
        "
::= { semOutTransUtilizationMonitorEntry 2 }

semOutTransUtilMonFlushHistory OBJECT-TYPE
    SYNTAX FlushTYPE
    MAX-ACCESS read-write
    STATUS current
    DESCRIPTION
        "Setting to 'flush' removes semOutTransUtilizationHistoryTable entries
         from semOutTransUtilMonFlushStart to semOutTransUtilMonFlushEnd for the
         Output Transport Stream.  The flush is complete when the SEM changes
         this parameter to 'flushNotInProgress'.

         Once written, the change to this parameter will take immediate effect.

         @Config(config=no, reboot=no)
        "
::= { semOutTransUtilizationMonitorEntry 3 }

semOutTransUtilMonFlushStart OBJECT-TYPE
    SYNTAX Integer32
    MAX-ACCESS read-write
    STATUS current
    DESCRIPTION
        "This is the starting index into semOutTransUtilizationHistoryTable
         to use when semOutTransUtilMonFlushHistory is applied.

         Once written, the change to this parameter will take immediate effect
         when semOutTransUtilMonFlushHistory is applied.

         @Commit(param=semOutTransUtilMonFlushHistory, value=2)
         @Config(config=no, reboot=no)
        "
::= { semOutTransUtilizationMonitorEntry 4 }

semOutTransUtilMonFlushEnd OBJECT-TYPE
    SYNTAX Integer32
    MAX-ACCESS read-write
    STATUS current
    DESCRIPTION
        "This is the ending index into semOutTransUtilizationHistoryTable
         to use when semOutTransUtilMonFlushHistory is applied.

         Once written, the change to this parameter will take immediate effect
         when semOutTransUtilMonFlushHistory is applied.

         @Commit(param=semOutTransUtilMonFlushHistory, value=2)
         @Config(config=no, reboot=no)
        "
::= { semOutTransUtilizationMonitorEntry 5 }


-- ------------------------------------------------------------------------------
--
-- semIpConfigInsertionRateTable
--

semIpConfigInsertionRateTable OBJECT-TYPE
    SYNTAX SEQUENCE OF SemIpConfigInsertionRateEntry
    MAX-ACCESS not-accessible
    STATUS current
    DESCRIPTION
        "This is a table of configuration parameters for Output Transport
         Rate of Host Ip Data Insertion."
::= { semOutTransConfig 5 }

semIpConfigInsertionRateEntry OBJECT-TYPE
    SYNTAX SemIpConfigInsertionRateEntry
    MAX-ACCESS not-accessible
    STATUS current
    DESCRIPTION
        "Output Transport Rate of Host Ip Data Insertion Configuration Table Entry."
    INDEX { semIpConfigInsertionRateStreamNum }
::= { semIpConfigInsertionRateTable 1 }

SemIpConfigInsertionRateEntry ::= SEQUENCE
    {
     semIpConfigInsertionRateStreamNum          Integer32,
     semIpConfigInsertionRate                   Integer32
    }

semIpConfigInsertionRateStreamNum OBJECT-TYPE
    SYNTAX Integer32(1..16)
    MAX-ACCESS not-accessible
    STATUS current
    DESCRIPTION
        "Output Transport Stream Number."
::= { semIpConfigInsertionRateEntry 1 }

semIpConfigInsertionRate OBJECT-TYPE
    SYNTAX Integer32
    MAX-ACCESS read-write
    STATUS current
    DESCRIPTION
        "Insertion Rate for the transport stream for Host Ip data.
         Range is 0 Kbps to 2750 Kbps for each transport stream.
         Total for all transport streams must not exceed 10,000 Kbps.

         Once written, a save must be performed via the semSaveConfig
         parameter and the SEM must be rebooted for the change to take effect.

         @Range(min=0, max=2750)
         @Config(config=yes, reboot=yes)
         @Save(semSaveConfig, value=2)
         @File(config.ini, type='ini')
        "
::= { semIpConfigInsertionRateEntry 2 }


-- ------------------------------------------------------------------------------
--
-- semOutTransPidRemappingTable
--

semOutTransPidRemappingTable OBJECT-TYPE
    SYNTAX SEQUENCE OF SemOutTransPidRemappingEntry
    MAX-ACCESS not-accessible
    STATUS current
    DESCRIPTION
        "This is a table of configuration parameters for Output Transport
         PID Remapping."
::= { semOutTransConfig 6 }

semOutTransPidRemappingEntry OBJECT-TYPE
    SYNTAX SemOutTransPidRemappingEntry
    MAX-ACCESS not-accessible
    STATUS current
    DESCRIPTION
        "Output Transport PID Remapping Configuration Table Entry."
    INDEX { semOutTransPidRemappingStreamNum }
::= { semOutTransPidRemappingTable 1 }

SemOutTransPidRemappingEntry ::= SEQUENCE
    {
     semOutTransPidRemappingStreamNum  Integer32,
     semOutTransPidRemapping           EnableDisableTYPE,
     semOutTransPidsPerProgram         Integer32
    }

semOutTransPidRemappingStreamNum OBJECT-TYPE
    SYNTAX Integer32(1..16)
    MAX-ACCESS not-accessible
    STATUS current
    DESCRIPTION
        "Output Transport Stream Number."
::= { semOutTransPidRemappingEntry 1 }

semOutTransPidRemapping OBJECT-TYPE
    SYNTAX EnableDisableTYPE
    MAX-ACCESS read-write
    STATUS current
    DESCRIPTION
        "The PID Remapping enabled or disabled setting. When enabled, the SEM will determine
         the output PIDs from a predetermined range of PIDs for services and ancillary
         PIDs.  In addition, when PID remapping is enabled, the SEM is able to perform
         PID mask encryption (allows for encrypting large numbers of PIDs using fewer ACP
         resources).  When set to disabled, the output PIDs for all services and ancillary
         PIDs are the same as the input PID values.  In addition, PID mask encryption cannot
         be performed when PID Remapping is disabled.

         Once written, a save must be performed via the semSaveConfig
         parameter and the SEM must be rebooted for the change to take effect.

         @Config(config=yes, reboot=yes)
         @Save(semSaveConfig, value=2)
         @File(config.ini, type='ini')
        "
::= { semOutTransPidRemappingEntry 2 }

semOutTransPidsPerProgram OBJECT-TYPE
    SYNTAX Integer32
    MAX-ACCESS read-write
    STATUS current
    DESCRIPTION
        "The PID Remapping parameters are used at initialization to
         deterministically partition the range of output elementary PIDs
         that the SEM uses when remapping PIDs.  The available elementary
         PID range is broken up into services with an equal distribution
         of available PIDs as defined by these parameters.
         Specifically, the PIDs per Program parameter specifies how many
         PIDs are to be allocated for each program.  The elementary PID
         range consists of 4160 available PIDs.

         The number of PIDs per Program must be divisible by 16. The
         following shows the allowed values of PIDs per Program and the
         number of programs:
           PIDs Per    Number of
           Program     Programs
            200*       20
            192        21
            176        23
            160        26
            144        28
            128        32
            112        37
            96         43
            80         52
            64         65
            48         86
            32         130
            16         252

         Note: The maximum number of PIDs is 200, as this is the maximum that
         can be supported in 1 PMT. This is the only exception to the rule
         that the PIDs per program be divisible by 16.

         Once written, a save must be performed via the semSaveConfig
         parameter and the SEM must be rebooted for the change to take effect.

         @Range(min=16, max=200, step=16)
         @Config(config=yes, reboot=yes)
         @Save(semSaveConfig, value=2)
         @File(config.ini, type='ini')
        "
::= { semOutTransPidRemappingEntry 3 }


-- ------------------------------------------------------------------------------
--
-- semOutTransStatus
--
-- semOutTransStatusGeneral
--

semNumOutputProgramsPerTS OBJECT-TYPE
    SYNTAX Integer32
    MAX-ACCESS read-only
    STATUS current
    DESCRIPTION
        "Number of Output Programs supported per Output Transport Stream."
::= { semOutTransStatusGeneral 1 }


-- ------------------------------------------------------------------------------
--
-- semOutputClockStatusTable
--

semOutputClockStatusTable OBJECT-TYPE
    SYNTAX SEQUENCE OF SemOutputClockStatusEntry
    MAX-ACCESS not-accessible
    STATUS current
    DESCRIPTION
        "This is a table of status parameters for the eight
         SEM clocks."
::= { semOutTransStatus 2 }

semOutputClockStatusEntry OBJECT-TYPE
    SYNTAX SemOutputClockStatusEntry
    MAX-ACCESS not-accessible
    STATUS current
    DESCRIPTION
        "Output Clock Status Table Entry."
    INDEX { semOutputClockStatusNum }
::= { semOutputClockStatusTable 1 }

SemOutputClockStatusEntry ::= SEQUENCE
    {
     semOutputClockStatusNum            Integer32,
     semOutputClockStatusRate           Integer32
    }

semOutputClockStatusNum OBJECT-TYPE
    SYNTAX Integer32(1..8)
    MAX-ACCESS not-accessible
    STATUS current
    DESCRIPTION
        "Output Clock Number."
::= { semOutputClockStatusEntry 1 }

semOutputClockStatusRate OBJECT-TYPE
    SYNTAX Integer32 (0..206000000)
    MAX-ACCESS read-only
    STATUS current
    DESCRIPTION
        "Actual rate for this clock in bits per second (bps).
         Zero indicates clock not in use."
::= { semOutputClockStatusEntry 2 }


-- ------------------------------------------------------------------------------
--
-- semOutTransUtilization
--
-- semOutTransUtilizationGeneral
--

semOutTransUtilizationSamplePeriod OBJECT-TYPE
    SYNTAX Integer32
    MAX-ACCESS read-only
    STATUS current
    DESCRIPTION
        "Sample Period for Output Transport Stream Bandwidth Utilization
         Rate Monitoring.
         This parameter indicates the length of time in milliseconds the
         stream is monitored during a single sample.
         This can be used with semOutTransUtilizationNumSamples to
         determine the amount of time or percent of time the stream was
         monitored during a fifteen minute sampling interval."
::= { semOutTransUtilizationGeneral 1 }

semOutTransUtilizationLastIndexWritten OBJECT-TYPE
    SYNTAX Integer32 (0 | 2..97)
    MAX-ACCESS read-only
    STATUS current
    DESCRIPTION
        "When Output Transport Stream Bandwidth Utilization is enabled
         this parameter indicates the index of last rows of historic
         data written to semOutTransUtilizationTable.
         Zero indicates no Output Transport Streams have been monitored
         since SEM bootup, in the last 24 hours, or since the last flush
         was performed on all monitored transport streams."
::= { semOutTransUtilizationGeneral 2 }


-- ------------------------------------------------------------------------------
--
-- semOutTransUtilizationTable
--

semOutTransUtilizationTable OBJECT-TYPE
    SYNTAX SEQUENCE OF SemOutTransUtilizationEntry
    MAX-ACCESS not-accessible
    STATUS current
    DESCRIPTION
        "This is a table of status parameters containing bandwidth
         utilization for Output Transport Streams.  The sampling
         interval is up to fifteen minutes.  There is a rolling
         average as well as last sample, peak, and minimum information.

         Monitoring is performed for any Output Transport
         Stream that is enabled via semOutTransStreamEnable and
         has Rate Monitoring enabled via semOutTransUtilMonEnable.
         With the exception of semOutTransUtilizationError, data in
         semOutTransUtilizationTable will not be cleared when
         monitoring is disabled for the Output Transport Stream via
         semOutTransUtilMonEnable.  However, the data will be
         cleared when monitoring is re-enabled or the data rate is
         changed for the Output Transport Stream.

         This table is indexed by Output Transport Stream Number."
::= { semOutTransUtilization 2 }

semOutTransUtilizationEntry OBJECT-TYPE
    SYNTAX SemOutTransUtilizationEntry
    MAX-ACCESS not-accessible
    STATUS current
    DESCRIPTION
        "Output Transport Stream Bandwidth Utilization Table Entry."
    INDEX { semOutTransUtilizationStreamNum }
::= { semOutTransUtilizationTable 1 }

SemOutTransUtilizationEntry ::= SEQUENCE
    {
     semOutTransUtilizationStreamNum      Integer32,
     semOutTransUtilizationDataFlag       UtilizationSamplingTYPE,
     semOutTransUtilizationNumSamples     Integer32,
     semOutTransUtilizationError          UtilizationErrorTYPE,
     semOutTransUtilizationTime           Integer32,
     semOutTransUtilizationPercent        Integer32,
     semOutTransUtilizationAvgPercent     Integer32,
     semOutTransUtilizationMinPercent     Integer32,
     semOutTransUtilizationPeakPercent    Integer32,
     semOutTransUtilizationRate           Integer32,
     semOutTransUtilizationAvgRate        Integer32,
     semOutTransUtilizationMinRate        Integer32,
     semOutTransUtilizationPeakRate       Integer32
    }

semOutTransUtilizationStreamNum OBJECT-TYPE
    SYNTAX Integer32(1..16)
    MAX-ACCESS not-accessible
    STATUS current
    DESCRIPTION
        "Output Transport Stream Number."
::= { semOutTransUtilizationEntry 1 }

semOutTransUtilizationDataFlag OBJECT-TYPE
    SYNTAX UtilizationSamplingTYPE
    MAX-ACCESS read-only
    STATUS current
    DESCRIPTION
        "Flag to indicate whether the Output Transport Stream was monitored
         a full fifteen minute sampling interval and a complete set of samples
         was obtained.
         'samplingComplete'       - indicates sampling complete with good samples.
         'samplingIncomplete'     - indicates incomplete sampling.
                                    Example causes include:
                                      - Rate Monitoring was enabled/disabled or both,
                                        during the interval, or
                                      - OTS rate changed during the period."
::= { semOutTransUtilizationEntry 2 }

semOutTransUtilizationNumSamples OBJECT-TYPE
    SYNTAX Integer32
    MAX-ACCESS read-only
    STATUS current
    DESCRIPTION
        "Number of samples included in the data.
         This can be used with semOutTransUtilizationSamplePeriod
         to determine the amount of time or percent of time the
         stream was monitored during the sampling interval."
::= { semOutTransUtilizationEntry 3 }

semOutTransUtilizationError OBJECT-TYPE
    SYNTAX UtilizationErrorTYPE
    MAX-ACCESS read-only
    STATUS current
    DESCRIPTION
        "Indicates whether an 'alarmThresholdReached' error has occurred
         at least once during this sampling interval.  'overflow'
         conditions are reported via semOutTransStatusOverflow.
         This field is cleared when monitoring is disabled."
::= { semOutTransUtilizationEntry 4 }

semOutTransUtilizationTime OBJECT-TYPE
    SYNTAX Integer32
    MAX-ACCESS read-only
    STATUS current
    DESCRIPTION
        "Time in GPS seconds (semSystemTime) that this table row was saved.
         When GPS time is not available to the sem (semSystemTime=0) a clock
         maintained inside the SEM will be used.  This clock starts at GPS time
         zero when the sem is booted.  The SEM will use real GPS time if and
         when GPS time becomes available to the SEM."
::= { semOutTransUtilizationEntry 5 }

semOutTransUtilizationPercent OBJECT-TYPE
    SYNTAX Integer32 (0..100)
    MAX-ACCESS read-only
    STATUS current
    DESCRIPTION
        "Percent utilization of most recently taken sample."
::= { semOutTransUtilizationEntry 6 }

semOutTransUtilizationAvgPercent OBJECT-TYPE
    SYNTAX Integer32 (0..100)
    MAX-ACCESS read-only
    STATUS current
    DESCRIPTION
        "Average percent utilization over this sampling interval."
::= { semOutTransUtilizationEntry 7 }

semOutTransUtilizationMinPercent OBJECT-TYPE
    SYNTAX Integer32 (0..100)
    MAX-ACCESS read-only
    STATUS current
    DESCRIPTION
        "Minimum percent utilization for a sample during this
         sampling interval."
::= { semOutTransUtilizationEntry 8 }

semOutTransUtilizationPeakPercent OBJECT-TYPE
    SYNTAX Integer32 (0..100)
    MAX-ACCESS read-only
    STATUS current
    DESCRIPTION
        "Peak percent utilization for a sample during this
         sampling interval."
::= { semOutTransUtilizationEntry 9 }

semOutTransUtilizationRate OBJECT-TYPE
    SYNTAX Integer32
    MAX-ACCESS read-only
    STATUS current
    DESCRIPTION
        "Utilization of most recently taken sample
         in bits per second (bps)."
::= { semOutTransUtilizationEntry 10 }

semOutTransUtilizationAvgRate OBJECT-TYPE
    SYNTAX Integer32
    MAX-ACCESS read-only
    STATUS current
    DESCRIPTION
        "Average utilization for this sampling interval
         in bits per second (bps)."
::= { semOutTransUtilizationEntry 11 }

semOutTransUtilizationMinRate OBJECT-TYPE
    SYNTAX Integer32
    MAX-ACCESS read-only
    STATUS current
    DESCRIPTION
        "Minimum utilization for a sample during this
         sampling interval in bits per second (bps)."
::= { semOutTransUtilizationEntry 12 }

semOutTransUtilizationPeakRate OBJECT-TYPE
    SYNTAX Integer32
    MAX-ACCESS read-only
    STATUS current
    DESCRIPTION
        "Peak utilization for a sample during this
         sampling interval in bits per second (bps)."
::= { semOutTransUtilizationEntry 13 }


-- ------------------------------------------------------------------------------
--
-- semOutTransUtilizationHistoryTable
--

semOutTransUtilizationHistoryTable OBJECT-TYPE
    SYNTAX SEQUENCE OF SemOutTransUtilizationHistoryEntry
    MAX-ACCESS not-accessible
    STATUS current
    DESCRIPTION
        "This is a table of status parameters containing bandwidth
         utilization for Output Transport Streams.

         The table contains entries for any Output Transport
         Stream that is enabled via semOutTransStreamEnable and
         has Utilization Monitoring enabled via semOutTransUtilMonEnable.

         This table is indexed by Output Transport Stream Number
         and Utilization Index.

         There are up to twenty four hours worth of fifteen minute
         sampling interval snapshots of utilization data.  Therefore
         there may be from zero to 96 rows in the table for each of
         the monitored Output Transport Streams.

         When GPS time is available to the SEM:
         The SEM will output a row of data on the hour, at quarter
         past the hour, at half past the hour, and at three quarters
         past the hour.  The GPS time assigned to a row is the time
         at the end of its fifteen minute collection interval and is
         the time the row is added to the table.  00:00 hours is placed
         in index one, 00:15 hours in index two, etc., etc., 23:30 is
         placed in index 95, and 23:45 is placed in index 96.  This
         is the same for all SEMs that have GPS time available.  This
         allows a controller to use the same index for all SEMs to
         gather the historic data for a given 15 minute interval
         during a 24 hour period.

         When GPS time is NOT available to the SEM:
         The SEM will free run a clock beginning at GPS time zero.
         The time assigned is sysUpTime at end of the fifteen minute
         sampling interval to the nearest second and is the time the
         row is added to the table.  The historic utilization data
         table begins filling starting fifteen minutes after the SEM
         is up with the first set of data placed in Utilization Index
         two, since the free running clock time (sysUpTime to the
         nearest second) will be 00:15:00.

         After 24 hours new data will overwrite old data.

         Historic data for an Output Transport Stream can be flushed
         via semOutTransUtilMonFlush."
::= { semOutTransUtilization 3 }

semOutTransUtilizationHistoryEntry OBJECT-TYPE
    SYNTAX SemOutTransUtilizationHistoryEntry
    MAX-ACCESS not-accessible
    STATUS current
    DESCRIPTION
        "Output Transport Stream Bandwidth Utilization History Table Entry."
    INDEX { semOutTransUtilHistStreamNum, semOutTransUtilHistIndex }
::= { semOutTransUtilizationHistoryTable 1 }

SemOutTransUtilizationHistoryEntry ::= SEQUENCE
    {
     semOutTransUtilHistStreamNum      Integer32,
     semOutTransUtilHistIndex          Integer32,
     semOutTransUtilHistDataFlag       UtilizationSamplingTYPE,
     semOutTransUtilHistNumSamples     Integer32,
     semOutTransUtilHistError          UtilizationErrorTYPE,
     semOutTransUtilHistTime           Integer32,
     semOutTransUtilHistAvgPercent     Integer32,
     semOutTransUtilHistMinPercent     Integer32,
     semOutTransUtilHistPeakPercent    Integer32,
     semOutTransUtilHistAvgRate        Integer32,
     semOutTransUtilHistMinRate        Integer32,
     semOutTransUtilHistPeakRate       Integer32
    }

semOutTransUtilHistStreamNum OBJECT-TYPE
    SYNTAX Integer32(1..16)
    MAX-ACCESS not-accessible
    STATUS current
    DESCRIPTION
        "Output Transport Stream Number."
::= { semOutTransUtilizationHistoryEntry 1 }

semOutTransUtilHistIndex OBJECT-TYPE
    SYNTAX Integer32 (1..96)
    MAX-ACCESS not-accessible
    STATUS current
    DESCRIPTION
        "Index to a row of Output Transport Stream Bandwidth Utilization Data.
         Indices one through 96 may contain up to 24 hours worth of historic
         fifteen minute snapshots of utilization data.  Data will be in an
         entry if the Transport Stream and Rate Monitoring were enabled for
         part or all of the fifteen minute sampling interval."
::= { semOutTransUtilizationHistoryEntry 2 }

semOutTransUtilHistDataFlag OBJECT-TYPE
    SYNTAX UtilizationSamplingTYPE
    MAX-ACCESS read-only
    STATUS current
    DESCRIPTION
        "Flag to indicate whether the Output Transport Stream was monitored
         this entire fifteen minute sampling interval and a complete set of
         samples was obtained.
         'samplingComplete'       - indicates sampling complete with good samples
                                    for entire interval.
         'samplingIncomplete'     - indicates incomplete sampling for this interval.
                                    Example causes include:
                                      - Rate Monitoring was enabled/disabled or both,
                                        during the interval, or
                                      - OTS rate changed during the period.
         'completeNoTimeSource'   - indicates sampling complete with good samples
                                    for entire interval and the SEM has no source of
                                    actual GPS time.
         'incompleteNoTimeSource' - indicates incomplete sampling for this interval
                                    and the SEM has no source of actual GPS time."
::= { semOutTransUtilizationHistoryEntry 3 }

semOutTransUtilHistNumSamples OBJECT-TYPE
    SYNTAX Integer32
    MAX-ACCESS read-only
    STATUS current
    DESCRIPTION
        "Number of samples taken during this fifteen minute sampling
         interval.
         This can be used with semOutTransUtilHistSamplePeriod
         to determine the amount of time or percent of time the
         stream was monitored during the fifteen minute sampling
         interval."
::= { semOutTransUtilizationHistoryEntry 4 }

semOutTransUtilHistError OBJECT-TYPE
    SYNTAX UtilizationErrorTYPE
    MAX-ACCESS read-only
    STATUS current
    DESCRIPTION
        "Indicates whether an error has occurred at least once during
         this fifteen minute sampling interval."
::= { semOutTransUtilizationHistoryEntry 5 }

semOutTransUtilHistTime OBJECT-TYPE
    SYNTAX Integer32
    MAX-ACCESS read-only
    STATUS current
    DESCRIPTION
        "Time in GPS seconds (semSystemTime) that this table row was saved.
         When GPS time is not available to the sem (semSystemTime=0) a clock
         maintained inside the SEM will be used.  This clock starts at GPS time
         zero when the sem is booted.  The SEM will use real GPS time if and
         when GPS time becomes available to the SEM."
::= { semOutTransUtilizationHistoryEntry 6 }

semOutTransUtilHistAvgPercent OBJECT-TYPE
    SYNTAX Integer32 (0..100)
    MAX-ACCESS read-only
    STATUS current
    DESCRIPTION
        "Average percent utilization for this sampling interval."
::= { semOutTransUtilizationHistoryEntry 7 }

semOutTransUtilHistMinPercent OBJECT-TYPE
    SYNTAX Integer32 (0..100)
    MAX-ACCESS read-only
    STATUS current
    DESCRIPTION
        "Minimum percent utilization for a sample during this
         sampling interval."
::= { semOutTransUtilizationHistoryEntry 8 }

semOutTransUtilHistPeakPercent OBJECT-TYPE
    SYNTAX Integer32 (0..100)
    MAX-ACCESS read-only
    STATUS current
    DESCRIPTION
        "Peak percent utilization for a sample during this
         sampling interval."
::= { semOutTransUtilizationHistoryEntry 9 }

semOutTransUtilHistAvgRate OBJECT-TYPE
    SYNTAX Integer32
    MAX-ACCESS read-only
    STATUS current
    DESCRIPTION
        "Average utilization for this sampling interval in
         bits per second (bps)."
::= { semOutTransUtilizationHistoryEntry 10 }

semOutTransUtilHistMinRate OBJECT-TYPE
    SYNTAX Integer32
    MAX-ACCESS read-only
    STATUS current
    DESCRIPTION
        "Minimum utilization for a sample during this minute
         sampling interval in bits per second (bps)."
::= { semOutTransUtilizationHistoryEntry 11 }

semOutTransUtilHistPeakRate OBJECT-TYPE
    SYNTAX Integer32
    MAX-ACCESS read-only
    STATUS current
    DESCRIPTION
        "Peak utilization for a sample during this sampling
         interval in bits per second (bps)."
::= { semOutTransUtilizationHistoryEntry 12 }


-- ------------------------------------------------------------------------------
--
-- semOutTransStatistics
--
-- semOutTransStatisticsGeneral
--

-- No entries in this group at this time.


-- ------------------------------------------------------------------------------
--
-- semInsertPacketStatisticsTable
--
-- semOutTransStatisticsGeneral

semInsertPacketStatisticsTable OBJECT-TYPE
    SYNTAX SEQUENCE OF SemInsertPacketStatisticsEntry
    MAX-ACCESS not-accessible
    STATUS current
    DESCRIPTION
        "Table of Output Transport Stream Insert Packet Statistics.
         Indexed by Output Transport Stream number."
::= { semOutTransStatistics 2 }

semInsertPacketStatisticsEntry OBJECT-TYPE
    SYNTAX SemInsertPacketStatisticsEntry
    MAX-ACCESS not-accessible
    STATUS current
    DESCRIPTION
        "A row in the Output Transport Stream Insert Packet Statistics table."
    INDEX { semInsertPacketStatOutTransStreamNum }
::= { semInsertPacketStatisticsTable 1 }

SemInsertPacketStatisticsEntry ::= SEQUENCE
    {
     semInsertPacketStatOutTransStreamNum  Integer32,
     semInsertPacketStatTotPkts            Integer32,
     semInsertPacketStatNumPkts            Integer32
    }

semInsertPacketStatOutTransStreamNum OBJECT-TYPE
    SYNTAX Integer32 (1..16)
    MAX-ACCESS not-accessible
    STATUS current
    DESCRIPTION
        "Output Transport Stream Number."
::= { semInsertPacketStatisticsEntry 1 }

semInsertPacketStatTotPkts OBJECT-TYPE
    SYNTAX Integer32
    MAX-ACCESS read-only
    STATUS current
    DESCRIPTION
        "Total number of packets inserted."
::= { semInsertPacketStatisticsEntry 2 }

semInsertPacketStatNumPkts OBJECT-TYPE
    SYNTAX Integer32
    MAX-ACCESS read-only
    STATUS current
    DESCRIPTION
        "Number of packets inserted during the last monitoring
         period (currently 5 seconds)."
::= { semInsertPacketStatisticsEntry 3 }


-- ------------------------------------------------------------------------------
--
-- semIpInsertPacketStatisticsTable
--

semIpInsertPacketStatisticsTable OBJECT-TYPE
    SYNTAX SEQUENCE OF SemIpInsertPacketStatisticsEntry
    MAX-ACCESS not-accessible
    STATUS current
    DESCRIPTION
        "Table of Output Transport Stream IP Insert Packet Statistics.
         Indexed by Output Transport Stream number."
::= { semOutTransStatistics 3 }

semIpInsertPacketStatisticsEntry OBJECT-TYPE
    SYNTAX SemIpInsertPacketStatisticsEntry
    MAX-ACCESS not-accessible
    STATUS current
    DESCRIPTION
        "A row in the Output Transport Stream IP Insert Packet Statistics table."
    INDEX { semIpInsertPacketStatOutTransStreamNum }
::= { semIpInsertPacketStatisticsTable 1 }

SemIpInsertPacketStatisticsEntry ::= SEQUENCE
    {
     semIpInsertPacketStatOutTransStreamNum  Integer32,
     semIpInsertPacketStatTotPkts            Integer32,
     semIpInsertPacketStatNumPkts            Integer32,
     semIpInsertPacketStatTotDiscardPkts     Integer32,
     semIpInsertPacketStatNumDiscardPkts     Integer32
    }

semIpInsertPacketStatOutTransStreamNum OBJECT-TYPE
    SYNTAX Integer32 (1..16)
    MAX-ACCESS not-accessible
    STATUS current
    DESCRIPTION
        "Output Transport Stream Number."
::= { semIpInsertPacketStatisticsEntry 1 }

semIpInsertPacketStatTotPkts OBJECT-TYPE
    SYNTAX Integer32
    MAX-ACCESS read-only
    STATUS current
    DESCRIPTION
        "Total number of packets inserted on this Output
         Transport Stream."
::= { semIpInsertPacketStatisticsEntry 2 }

semIpInsertPacketStatNumPkts OBJECT-TYPE
    SYNTAX Integer32
    MAX-ACCESS read-only
    STATUS current
    DESCRIPTION
        "Number of packets inserted during the last monitoring
         period (currently 5 seconds) on this Output Transport
         Stream."
::= { semIpInsertPacketStatisticsEntry 3 }

semIpInsertPacketStatTotDiscardPkts OBJECT-TYPE
    SYNTAX Integer32
    MAX-ACCESS read-only
    STATUS current
    DESCRIPTION
        "Total number of IP packets discarded on this Output
         Transport Stream."
::= { semIpInsertPacketStatisticsEntry 4 }

semIpInsertPacketStatNumDiscardPkts OBJECT-TYPE
    SYNTAX Integer32
    MAX-ACCESS read-only
    STATUS current
    DESCRIPTION
        "Number of packets discarded during the last monitoring
         period (currently 5 seconds) on this Output Transport
         Stream.  See semHostIpPacketStatNumDiscardPkts to
         see which IP interface is the source of the packets.
         Packets will be discarded when there is not enough buffer
         space.  This may be due to buffer overflow or incorrect
         configuration of semIpConfigInsertionRate."
::= { semIpInsertPacketStatisticsEntry 5 }


-- ------------------------------------------------------------------------------
--
-- semOutTransStatusTable
--

semOutTransStatusTable OBJECT-TYPE
    SYNTAX SEQUENCE OF SemOutTransStatusEntry
    MAX-ACCESS not-accessible
    STATUS current
    DESCRIPTION
        "Table of Output Transport Status.
         Indexed by Output Transport Stream number."
::= { semOutTransStatus 5 }

semOutTransStatusEntry OBJECT-TYPE
    SYNTAX SemOutTransStatusEntry
    MAX-ACCESS not-accessible
    STATUS current
    DESCRIPTION
        "A row in the Output Transport Stream Status table."
    INDEX { semOutTransStatusStreamNum }
::= { semOutTransStatusTable 1 }

SemOutTransStatusEntry ::= SEQUENCE
    {
     semOutTransStatusStreamNum     Integer32,
     semOutTransStatusFault         INTEGER,
     semOutTransStatusOverflow      UtilizationErrorTYPE,
     semOutTransStatusCorrupted     INTEGER,
     semOutTransStatusIpAddr        IpAddress,
     semOutTransStatusUdpPort       Integer32,
     semOutTransStatusInterface     Integer32,
     semOutTransStatusProgramsPerTs Integer32
    }

semOutTransStatusStreamNum OBJECT-TYPE
    SYNTAX Integer32 (1..16)
    MAX-ACCESS not-accessible
    STATUS current
    DESCRIPTION
        "Output Transport Stream Number."
::= { semOutTransStatusEntry 1 }

semOutTransStatusFault OBJECT-TYPE
    SYNTAX INTEGER
        {
         ok(1),
         indeterminate(2),
         warning(3),
         minor(4),
         major(5),
         critical(6)
        }
    MAX-ACCESS read-only
    STATUS current
    DESCRIPTION
        "Highest current fault condition associated with this Output
         Transport Stream.  The following Alarms are included depending
         on the output type for the OTS:
            - semAlarmOtsOverflow
            - semAlarmOtsUtilizationFault
            - semAlarmOtsHostIpOverflow
            - semAlarmQamFault
            - semAlarmUpconverterFault "
::= { semOutTransStatusEntry 2 }

semOutTransStatusOverflow OBJECT-TYPE
    SYNTAX UtilizationErrorTYPE
    MAX-ACCESS read-only
    STATUS current
    DESCRIPTION
        "Indicates whether an 'overflow' error has occurred
         at least once during this sampling interval.
         'alarmThresholdReached' are reported via
         semOutTransUtilizationError."
::= { semOutTransStatusEntry 3 }

semOutTransStatusCorrupted OBJECT-TYPE
    SYNTAX INTEGER
        {
         notCorrupted (1),
         corrupted    (2)
        }
    MAX-ACCESS read-only
    STATUS current
    DESCRIPTION
        "Indicates whether the SEM has detected loss of MPEG
         synchronization on this output."
::= { semOutTransStatusEntry 4 }

semOutTransStatusIpAddr OBJECT-TYPE
    SYNTAX IpAddress
    MAX-ACCESS read-only
    STATUS current
    DESCRIPTION
        "The destination IP address for this output transport stream. This only applies
         when the output transport stream is a Gigabit Ethernet output. A value of
         0 indicates that no Gigabit Ethernet output stream has been configured."
::= { semOutTransStatusEntry 5 }

semOutTransStatusUdpPort OBJECT-TYPE
    SYNTAX Integer32
    MAX-ACCESS read-only
    STATUS current
    DESCRIPTION
        "The destination UDP port for this output transport stream.  This only applies
         when the output transport stream is a Gigabit Ethernet output and the
         semOutTransStatusIpAddr is non-zero."
::= { semOutTransStatusEntry 6 }

semOutTransStatusInterface OBJECT-TYPE
    SYNTAX Integer32
    MAX-ACCESS read-only
    STATUS current
    DESCRIPTION
        "The physical interface number of the output transport stream (relative 1).  This
         only applies when the output transport stream is a Gigabit Ethernet output and the
         semOutTransStatusIpAddr is non-zero."
::= { semOutTransStatusEntry 7 }

semOutTransStatusProgramsPerTs OBJECT-TYPE
    SYNTAX Integer32
    MAX-ACCESS read-only
    STATUS current
    DESCRIPTION
        "Number of Output Programs supported on this Output Transport Stream.
        "
::= { semOutTransStatusEntry 8 }


-- ------------------------------------------------------------------------------
--
-- semUdpMap
--
-- semUdpMapConfig
--
-- semUdpMapConfigGeneral
--

semUdpMapConfigGbePort OBJECT-TYPE
    SYNTAX Integer32 (1..3)
    MAX-ACCESS read-write
    STATUS current
    DESCRIPTION
        "Indicates which Gigabit Ethernet Interface port to use for any of the SEM
         UDP Port Mapping modes.

         Once written, the change to this parameter will take immediate
         effect and all mappings will be removed.  Mappings will not be
         re-added until semUdpMapConfigApplyChange is set to 'apply' for
         all transport streams.  In order for the change to persist through
         subsequent reboots or power cycles, the change must be saved via
         the semSaveConfig parameter.

         @Config(config=yes, reboot=no)
         @Save(semSaveConfig, value=2)
         @File(mancfg.ini, type='ini')
        "
::= { semUdpMapConfigGeneral 1 }

semUdpMapConfigBaseUdpOffset OBJECT-TYPE
    SYNTAX Integer32 ( 0 | 8192 | 16384 | 24576 | 32768 | 40960 | 49152 | 57344 )
    MAX-ACCESS read-write
    STATUS current
    DESCRIPTION
        "The UDP Base offset to use for opening input UDP ports on the
         selected Gigabit Ethernet interface.  As specified by the UDP
         Post Mapping Algorithm, this value is the three most significant
         bits of the 16 bit UDP address and is therefore limited to the
         following values:
            HEX     Decimal
            0x0     0
            0x2000  8192
            0x4000  16384
            0x6000  24576
            0x8000  32768
            0xA000  40960
            0xC000  49152
            0xE000  57344
         This offset is intended to keep the UDP Port values out of the
         well known port range when using UDP Port Mapping so it is
         recommended that zero not be used.  If zero is used, the UDP
         Ports may be in the well known port range, depending on the
         SEM physical output being used.  From 'TCP/IP Illustrated,
         Volume 1: The Protocols' by W. Richard Stevens:
           'Those services that can be provided by any implementation
            of TCP/IP have well- known port numbers between 1 and 1023.
            The well-known ports are managed by the Internet Assigned
            Numbers Authority (IANA).  Most TCP/IP implementations
            allocate ephemeral port numbers between 1024 and 5000.  The
            port numbers above 5000 are intended for other services
            (those that aren't well known across the Internet).'
         Therefore, the user would be advised to keep the port numbers
         above 5000.

         This parameter applies to semDeviceOperatingMode of 'udpMapping' only.

         Once written, the change to this parameter will take immediate
         effect and all mappings will be removed.  Mappings will not be
         re-added until semUdpMapConfigApplyChange is set to 'apply' for
         all transport streams.  In order for the change to persist through
         subsequent reboots or power cycles, the change must be saved via
         the semSaveConfig parameter.

         @Config(config=yes, reboot=no)
         @Save(semSaveConfig, value=2)
         @File(mancfg.ini, type='ini')
        "
::= { semUdpMapConfigGeneral 2 }

semUdpMapConfigInSvcPreEncryption OBJECT-TYPE
    SYNTAX EncryptedTYPE
    MAX-ACCESS read-write
    STATUS current
    DESCRIPTION
        "Indicates whether input services are pre-encrypted or clear.  If
         pre-encrypted, setting this flag will cause the SEM to pass through
         ECM PIDs for all services, pass through the PIT message, and the
         output PMT will contain a GI CA ECM descriptor (referencing the ECM
         PID). When PID Remapping is enabled, pre-encryption for any service
         is only valid when the input ECM PID is on a different PID than the
         associated PMT PID.  If this flag is set to pre-encryption and an
         input service is not pre-encrypted, then the setting of this flag has
         no affect on the output service.

         Once written, the change to this parameter will take immediate
         effect and all mappings will be removed.  Mappings will not be
         re-added until semUdpMapConfigApplyChange is set to 'apply' for
         all transport streams.  In order for the change to persist through
         subsequent reboots or power cycles, the change must be saved via
         the semSaveConfig parameter.

         @Config(config=yes, reboot=no)
         @Save(semSaveConfig, value=2)
         @File(mancfg.ini, type='ini')
        "
::= { semUdpMapConfigGeneral 3 }

semUdpMapConfigTsIdOffset OBJECT-TYPE
    SYNTAX Integer32 (0..1)
    MAX-ACCESS read-write
    STATUS current
    DESCRIPTION
        "Used as part of the Standardized UDP Port calculation. Transport Stream
         index can be relative 0 or relative 1 based. The transport stream index
         represents the output QAM port number that will be used.

         This parameter applies to semDeviceOperatingMode of 'standardizedUdpMapping'
         only.

         Once written, the change to this parameter will take immediate
         effect and all mappings will be removed.  Mappings will not be
         re-added until semUdpMapConfigApplyChange is set to 'apply' for
         all transport streams.  In order for the change to persist through
         subsequent reboots or power cycles, the change must be saved via
         the semSaveConfig parameter.

         @Config(config=yes, reboot=no)
         @Save(semSaveConfig, value=2)
         @File(mancfg.ini, type='ini')
        "
::= { semUdpMapConfigGeneral 4 }

semUdpMapConfigModeBits OBJECT-TYPE
    SYNTAX Integer32 (0..3)
    MAX-ACCESS read-write
    STATUS current
    DESCRIPTION
        "Used as part of the Standardized UDP Port calculation. This is the value
         that will be placed in the two MSBs of the port number (bits 14 and 15).
         These two bits represent the mode value.

         This parameter applies to semDeviceOperatingMode of 'standardizedUdpMapping'
         only.

         Once written, the change to this parameter will take immediate
         effect and all mappings will be removed.  Mappings will not be
         re-added until semUdpMapConfigApplyChange is set to 'apply' for
         all transport streams.  In order for the change to persist through
         subsequent reboots or power cycles, the change must be saved via
         the semSaveConfig parameter.

         @Config(config=yes, reboot=no)
         @Save(semSaveConfig, value=2)
         @File(mancfg.ini, type='ini')
        "
::= { semUdpMapConfigGeneral 5 }


-- ------------------------------------------------------------------------------
--
-- semUdpMapConfigTable
--

semUdpMapConfigTable OBJECT-TYPE
    SYNTAX SEQUENCE OF SemUdpMapConfigEntry
    MAX-ACCESS not-accessible
    STATUS current
    DESCRIPTION
        "Table of UDP Mapping Mode configuration data.

         @Config(config=yes, reboot=no)
         @Save(semSaveConfig, value=2)
         @File(mancfg.ini, type='ini')
        "
::= { semUdpMapConfig 2 }

semUdpMapConfigEntry OBJECT-TYPE
    SYNTAX SemUdpMapConfigEntry
    MAX-ACCESS not-accessible
    STATUS current
    DESCRIPTION
        "UDP Mapping Mode Configuration Table Entry."
    INDEX { semUdpMapConfigOutTransStreamNum }
::= { semUdpMapConfigTable 1 }

SemUdpMapConfigEntry ::= SEQUENCE
    {
     semUdpMapConfigOutTransStreamNum   Integer32,
     semUdpMapConfigApplyChange         ApplyDataToDeviceTYPE,
     semUdpMapConfigStartProgramNumber  Integer32,
     semUdpMapConfigNumPrograms         Integer32,
     semUdpMapConfigOutPatTsId          Integer32,
     semUdpMapConfigOutIpAddr           IpAddress,
     semUdpMapConfigOutUdpPort          Integer32
    }

semUdpMapConfigOutTransStreamNum OBJECT-TYPE
    SYNTAX Integer32 (1..16)
    MAX-ACCESS not-accessible
    STATUS current
    DESCRIPTION
        "The SEM output transport stream number."
::= { semUdpMapConfigEntry 1 }

semUdpMapConfigApplyChange OBJECT-TYPE
    SYNTAX ApplyDataToDeviceTYPE
    MAX-ACCESS read-write
    STATUS current
    DESCRIPTION
        "The Apply for the Dynamic UDP Port Mapping Table.

         This parameter MUST be set to 'apply' in order for any of the data
         in the semUdpMapConfigTable to take effect in the SEM.  This parameter
         MUST be set LAST after all other data in the semUdpMapConfigTable has
         been configured.
        "
::= { semUdpMapConfigEntry 2 }

semUdpMapConfigStartProgramNumber OBJECT-TYPE
    SYNTAX Integer32
    MAX-ACCESS read-write
    STATUS current
    DESCRIPTION
        "Indicates the first program number in a sequential range of programs
         that are to be routed to the same output transport stream.

         Once written, the change to this parameter will only take immediate
         effect after semUdpMapConfigApplyChange is set to 'apply'.  In order for the
         change to persist through subsequent reboots or power cycles, the
         change must be saved via the semSaveConfig parameter.

         @Range(min=0)
         @Commit(param=semUdpMapConfigApplyChange, value=2)
        "
::= { semUdpMapConfigEntry 3 }

semUdpMapConfigNumPrograms OBJECT-TYPE
    SYNTAX Integer32
    MAX-ACCESS read-write
    STATUS current
    DESCRIPTION
        "Indicates the number of programs that can be mapped to this output
         transport stream.  For each programmed mapped to this output transport
         stream, 1 UDP port is opened. A single program transport stream is mapped
         from each UDP port to this output transport stream.

         Once written, the change to this parameter will only take immediate
         effect after semUdpMapConfigApplyChange is set to 'apply'.  In order for the
         change to persist through subsequent reboots or power cycles, the
         change must be saved via the semSaveConfig parameter.

         @Range(min=0)
         @Commit(param=semUdpMapConfigApplyChange, value=2)
        "
::= { semUdpMapConfigEntry 4 }

semUdpMapConfigOutPatTsId OBJECT-TYPE
    SYNTAX Integer32
    MAX-ACCESS read-write
    STATUS current
    DESCRIPTION
        "Output Transport Stream ID to use for the output PAT in this Output
         Transport Stream when in UDP Port Mapping mode.

         Once written, the change to this parameter will only take immediate
         effect after semUdpMapConfigApplyChange is set to 'apply'.  In order for the
         change to persist through subsequent reboots or power cycles, the
         change must be saved via the semSaveConfig parameter.

         @Range(min=0, max=65535)
         @Commit(param=semUdpMapConfigApplyChange, value=2)
        "
::= { semUdpMapConfigEntry 5 }

semUdpMapConfigOutIpAddr OBJECT-TYPE
    SYNTAX IpAddress
    MAX-ACCESS read-write
    STATUS current
    DESCRIPTION
        "The destination IP address for this output transport stream. This only applies
         when the output transport stream is a Gigabit Ethernet output.

         Once written, the change to this parameter will only take immediate
         effect after semUdpMapConfigApplyChange is set to 'apply'.  In order for the
         change to persist through subsequent reboots or power cycles, the
         change must be saved via the semSaveConfig parameter.

         @Commit(param=semUdpMapConfigApplyChange, value=2)
        "
::= { semUdpMapConfigEntry 6 }

semUdpMapConfigOutUdpPort OBJECT-TYPE
    SYNTAX Integer32
    MAX-ACCESS read-write
    STATUS current
    DESCRIPTION
        "The destination UDP Port for this output transport stream. This only applies
         when the output transport stream is a Gigabit Ethernet output.

         Once written, the change to this parameter will only take immediate
         effect after semUdpMapConfigApplyChange is set to 'apply'.  In order for the
         change to persist through subsequent reboots or power cycles, the
         change must be saved via the semSaveConfig parameter.

         @Range(min=0, max=65535)
         @Commit(param=semUdpMapConfigApplyChange, value=2)
        "
::= { semUdpMapConfigEntry 7 }


-- ------------------------------------------------------------------------------
--
-- semUdpMapStatus
--

semUdpMapInvalidApplyText OBJECT-TYPE
    SYNTAX DisplayString (SIZE (0..80))
    MAX-ACCESS read-only
    STATUS current
    DESCRIPTION
        "When semUdpMapConfigApplyChange is set to applyNotInProgressInvalidData
         this entry contains a text description of what was wrong with the data.
         This entry contains the description for the most recent apply of a PID
         Mapping table entry that was invalid."
::= { semUdpMapStatus 1 }


-- ------------------------------------------------------------------------------
--
-- semSimulcrypt
--
-- semSimConfig
--
-- semSimConfigGeneral
--

semSimIpInterfaceSelect OBJECT-TYPE
    SYNTAX SemHostEnetTYPE
    MAX-ACCESS read-write
    STATUS current
    DESCRIPTION
        "Configures which host processor Ethernet interface will be
         used for Simulcrypt messaging protocol.

         The following values are possible:
         hostEnet1 (1)   <= Use ENET1 for simulcrypt communications
         hostEnet2 (2)   <= Use ENET2 for simulcrypt communications

         The GIGE interfaces are not available for Simulcrypt.

         Once written, a save must be performed via the semSaveConfig
         parameter and the SEM must be rebooted for the change to take
         effect.

         @Config(config=yes, reboot=yes)
         @Save(semSaveConfig, value=2)
         @File(config.ini, type='ini')
        "
::= { semSimConfigGeneral 1 }


-- ------------------------------------------------------------------------------
--
-- semSimStatus
--
-- semSimStatusGeneral
--

semSimInstalled OBJECT-TYPE
    SYNTAX InstalledTYPE
    MAX-ACCESS read-only
    STATUS current
    DESCRIPTION
        "It is a prerequisite for simulcrypt operating mode that the
         SEM be equipped with a simulcrypt enabled ACP module. The
         simulcrypt enabled ACP module has additional MC21 units to
         support control word generation.

         This read-only value indicates whether the ACP module is
         capable of supporting Simulcrypt, from a strictly hardware
         perspective."
::= { semSimStatusGeneral 1 }


-- ------------------------------------------------------------------------------
--
-- semRemuxStatus
--

-- No entries in this group at this time.


-- ------------------------------------------------------------------------------
--
-- semPsiTable
--

semPsiTable OBJECT-TYPE
    SYNTAX SEQUENCE OF SemPsiEntry
    MAX-ACCESS not-accessible
    STATUS current
    DESCRIPTION
        "The following table contains a list of messages that are either being extracted
         from the input side or being inserted to the output side of the sem.  On the
         input side all extracted messages that are being used by the SEM are displayed.
         On the output side, only PATs, PMTs, and CATs are displayed.  These messages
         were either given to the sem when it is in external mode or created by the sem
         when it is in internal mode."
::= { semRemuxStatus 2 }

semPsiEntry OBJECT-TYPE
    SYNTAX SemPsiEntry
    MAX-ACCESS not-accessible
    STATUS current
    DESCRIPTION
        "PSI Table Entry."
    INDEX { semPsiTableType, semPsiId, semPsiPid, semPsiMessageType,
           semPsiProgramNumber, semPsiSegment, semPsiPart }
::= { semPsiTable 1 }

SemPsiEntry ::= SEQUENCE
    {
     semPsiTableType     INTEGER,
     semPsiId            Integer32,
     semPsiPid           Integer32,
     semPsiMessageType   Integer32,
     semPsiProgramNumber Integer32,
     semPsiSegment       Integer32,
     semPsiPart          Integer32,
     semPsiBody          DisplayString
    }

semPsiTableType OBJECT-TYPE
    SYNTAX INTEGER
        {
         inputPsiTable (1),
         outputPsiTable (2),
         unknownPsiTable (3)
        }
    MAX-ACCESS not-accessible
    STATUS current
    DESCRIPTION
        "Indicates whether this message comes from the input or output side of the sem."
::= { semPsiEntry 1 }

semPsiId OBJECT-TYPE
    SYNTAX Integer32 (0..65535)
    MAX-ACCESS not-accessible
    STATUS current
    DESCRIPTION
        "Indicates the input or output id for which this message applies"
::= { semPsiEntry 2 }

semPsiPid OBJECT-TYPE
    SYNTAX Integer32 (0..8191)
    MAX-ACCESS not-accessible
    STATUS current
    DESCRIPTION
        "Indicates the PID that this message is contained in."
::= { semPsiEntry 3 }

semPsiMessageType OBJECT-TYPE
    SYNTAX Integer32 (0..255)
    MAX-ACCESS not-accessible
    STATUS current
    DESCRIPTION
        "Indicates the message type of this message"
::= { semPsiEntry 4 }

semPsiProgramNumber OBJECT-TYPE
    SYNTAX Integer32
    MAX-ACCESS not-accessible
    STATUS current
    DESCRIPTION
        "Indicates the Program Number which this message is part of.  When a
         message is not specifically related to a program, this value is 0."
::= { semPsiEntry 5 }

semPsiSegment OBJECT-TYPE
    SYNTAX Integer32
    MAX-ACCESS not-accessible
    STATUS current
    DESCRIPTION
        "Indicates the segment number of this message.  Useful for PAT messages.
         Otherwise this is 0."
::= { semPsiEntry 6 }

semPsiPart OBJECT-TYPE
    SYNTAX Integer32
    MAX-ACCESS not-accessible
    STATUS current
    DESCRIPTION
        " Since a message can be 1024 bytes long the message may divided into parts.
          Each part of the message is indexed using this index."
::= { semPsiEntry 7 }

semPsiBody OBJECT-TYPE
    SYNTAX DisplayString
    MAX-ACCESS read-only
    STATUS current
    DESCRIPTION
        "  "
::= { semPsiEntry 8 }


-- ------------------------------------------------------------------------------
--
-- semManRemuxStatus
--

semManRemuxMapInvalidApplyText OBJECT-TYPE
    SYNTAX DisplayString (SIZE (0..80))
    MAX-ACCESS read-only
    STATUS current
    DESCRIPTION
        "When semManRemuxMapApplyChange is set to applyNotInProgressInvalidData
         this entry contains a text description of what was wrong with the data.
         This entry contains the description for the most recent apply of a
         table entry that was invalid."
::= { semManRemuxStatus 1 }

semManRemuxOutTsInvalidApplyText OBJECT-TYPE
    SYNTAX DisplayString (SIZE (0..80))
    MAX-ACCESS read-only
    STATUS current
    DESCRIPTION
        "When semManRemuxOutTsApplyChange is set to applyNotInProgressInvalidData
         this entry contains a text description of what was wrong with the data.
         This entry contains the description for the most recent apply of a
         table entry that was invalid."
::= { semManRemuxStatus 2 }


-- ------------------------------------------------------------------------------
--
-- semRemusStatusGeneral
--

semMaxInternalServiceMappings OBJECT-TYPE
    SYNTAX Integer32
    MAX-ACCESS read-only
    STATUS current
    DESCRIPTION
        "Maximum service mappings when in an internal semDeviceOperatingMode.
         See description of semDeviceOperatingMode for more information on
         internal modes."
::= { semRemuxStatusGeneral 1 }

semMaxInternalPidMappings OBJECT-TYPE
    SYNTAX Integer32
    MAX-ACCESS read-only
    STATUS current
    DESCRIPTION
        "Maximum PID mappings when in an internal semDeviceOperatingMode.
         See description of semDeviceOperatingMode for more information on
         internal modes."
::= { semRemuxStatusGeneral 2 }


-- ------------------------------------------------------------------------------
--
-- semManRemuxConfig
--
-- semManRemuxMapTable
--

semManRemuxMapTable OBJECT-TYPE
    SYNTAX SEQUENCE OF SemManRemuxMapEntry
    MAX-ACCESS not-accessible
    STATUS current
    DESCRIPTION
        "Table of data for Manual Remultiplexing.

         External SNMP managers should not write this table when semDeviceOperatingMode
         is 'isaSdv'.  The SEM writes to this table in this mode and the external
         SNMP manager should consider this table to be a read-only status table.

         Writes to any of these fields do not take effect until the
         parameter semManRemuxMapApplyChange, is written.
         Additionally, in order for the change to persist through
         subsequent reboots or power cycles, the change must be saved via
         the semSaveConfig parameter.

         @Config(config=yes, reboot=no)
         @Save(semSaveConfig, value=2)
         @File(mancfg.ini, type='ini')
        "
::= { semManRemuxConfig 1 }

semManRemuxMapEntry OBJECT-TYPE
    SYNTAX SemManRemuxMapEntry
    MAX-ACCESS not-accessible
    STATUS current
    DESCRIPTION
        "Manual Remultiplexing Table Entry."
    INDEX { semManRemuxMapIndex }
::= { semManRemuxMapTable 1 }

SemManRemuxMapEntry ::= SEQUENCE
    {
     semManRemuxMapIndex               Integer32,
     semManRemuxMapApplyChange         ApplyDataToDeviceTYPE,
     semManRemuxMapEnable              EnableDisableTYPE,
     semManRemuxMapPhysInType          INTEGER,
     semManRemuxMapPhysInPort          Integer32,
     semManRemuxMapInputUdp            Integer32,
     semManRemuxMapInputProgNum        Integer32,
     semManRemuxMapInputPid            Integer32,
     semManRemuxMapOutTransStreamNum   Integer32,
     semManRemuxMapOutputProgNum       Integer32,
     semManRemuxMapOutputPid           Integer32,
     semManRemuxMapPassThrough         EnableDisableTYPE,
     semManRemuxMapInSvcPreEncryption  EncryptedTYPE
    }

semManRemuxMapIndex OBJECT-TYPE
    SYNTAX Integer32 (1..384)
    MAX-ACCESS not-accessible
    STATUS current
    DESCRIPTION
        "The index of the Manual Remultiplexing Table."
::= { semManRemuxMapEntry 1 }

semManRemuxMapApplyChange OBJECT-TYPE
    SYNTAX ApplyDataToDeviceTYPE
    MAX-ACCESS read-write
    STATUS current
    DESCRIPTION
        "The Apply for the row off data in the Manual Remultiplexing Map Table.

         This parameter MUST be set to 'apply' in order for any of the data
         in the row to take effect in the SEM.  This parameter MUST be set
         LAST after all other data in the row has been configured.
        "
::= { semManRemuxMapEntry 2 }

semManRemuxMapEnable OBJECT-TYPE
    SYNTAX EnableDisableTYPE
    MAX-ACCESS read-write
    STATUS current
    DESCRIPTION
        "Indicates that this Manual Mapping is enabled or disabled.

         Once written, the change to this parameter will only take immediate
         effect after semManRemuxMapApplyChange is set to 'apply'.  In order for the
         change to persist through subsequent reboots or power cycles, the
         change must be saved via the semSaveConfig parameter.

         @Commit(param=semManRemuxMapApplyChange, value=2)
        "
::= { semManRemuxMapEntry 3 }

semManRemuxMapPhysInType OBJECT-TYPE
    SYNTAX INTEGER
        {
         gbe      (1),
         asi      (2),
         hostEnet (3)
        }
    MAX-ACCESS read-write
    STATUS current
    DESCRIPTION
        "Input Type of input from which to obtain data.

         Once written, the change to this parameter will only take immediate
         effect after semManRemuxMapApplyChange is set to 'apply'.  In order for the
         change to persist through subsequent reboots or power cycles, the
         change must be saved via the semSaveConfig parameter.

         @Commit(param=semManRemuxMapApplyChange, value=2)
        "
::= { semManRemuxMapEntry 4 }

semManRemuxMapPhysInPort OBJECT-TYPE
    SYNTAX Integer32
    MAX-ACCESS read-write
    STATUS current
    DESCRIPTION
        "Number of the input port, of type configured by PhysInType,
         from which to obtain data.

         Once written, the change to this parameter will only take immediate
         effect after semManRemuxMapApplyChange is set to 'apply'.  In order for the
         change to persist through subsequent reboots or power cycles, the
         change must be saved via the semSaveConfig parameter.

         @Range(min=0)
         @Commit(param=semManRemuxMapApplyChange, value=2)
        "
::= { semManRemuxMapEntry 5 }

semManRemuxMapInputUdp OBJECT-TYPE
    SYNTAX Integer32
    MAX-ACCESS read-write
    STATUS current
    DESCRIPTION
        "Input UDP Port from which to obtain data.  This parameter is
         for use with UDP based input interfaces, otherwise is ignored.

         Once written, the change to this parameter will only take immediate
         effect after semManRemuxMapApplyChange is set to 'apply'.  In order for the
         change to persist through subsequent reboots or power cycles, the
         change must be saved via the semSaveConfig parameter.

         @Range(min=0, max=65535)
         @Commit(param=semManRemuxMapApplyChange, value=2)
        "
::= { semManRemuxMapEntry 6 }

semManRemuxMapInputProgNum OBJECT-TYPE
    SYNTAX Integer32
    MAX-ACCESS read-write
    STATUS current
    DESCRIPTION
        "Input MPEG Program Number to multiplex. A value of 0 can be used as
         a wild card. This will cause the SEM to map the first program listed in
         the input PAT to the specified output (regardless of input program number).

         Once written, the change to this parameter will only take immediate
         effect after semManRemuxMapApplyChange is set to 'apply'.  In order for the
         change to persist through subsequent reboots or power cycles, the
         change must be saved via the semSaveConfig parameter.

         @Range(min=0)
         @Commit(param=semManRemuxMapApplyChange, value=2)
        "
::= { semManRemuxMapEntry 7 }

semManRemuxMapInputPid OBJECT-TYPE
    SYNTAX Integer32
    MAX-ACCESS read-write
    STATUS obsolete
    DESCRIPTION
        "Not supported.
        "
::= { semManRemuxMapEntry 8 }

semManRemuxMapOutTransStreamNum OBJECT-TYPE
    SYNTAX Integer32 (0..16)
    MAX-ACCESS read-write
    STATUS current
    DESCRIPTION
        "Output Transport Stream Number of the output on which to place data.
         This serves as an index into the semOutTransStreamTable.
         Zero is only valid if the semManRemuxMapTable entry is not being used.

         Once written, the change to this parameter will only take immediate
         effect after semManRemuxMapApplyChange is set to 'apply'.  In order for the
         change to persist through subsequent reboots or power cycles, the
         change must be saved via the semSaveConfig parameter.

         @Commit(param=semManRemuxMapApplyChange, value=2)
        "
::= { semManRemuxMapEntry 9 }

semManRemuxMapOutputProgNum OBJECT-TYPE
    SYNTAX Integer32
    MAX-ACCESS read-write
    STATUS current
    DESCRIPTION
        "Output Program number to use for the program.

         Once written, the change to this parameter will only take immediate
         effect after semManRemuxMapApplyChange is set to 'apply'.  In order for the
         change to persist through subsequent reboots or power cycles, the
         change must be saved via the semSaveConfig parameter.

         @Range(min=0)
         @Commit(param=semManRemuxMapApplyChange, value=2)
        "
::= { semManRemuxMapEntry 10 }

semManRemuxMapOutputPid OBJECT-TYPE
    SYNTAX Integer32
    MAX-ACCESS read-write
    STATUS obsolete
    DESCRIPTION
        "Not supported.
        "
::= { semManRemuxMapEntry 11 }

semManRemuxMapPassThrough OBJECT-TYPE
    SYNTAX EnableDisableTYPE
    MAX-ACCESS read-write
    STATUS current
    DESCRIPTION
        "Transport Stream pass through enable.  If enabled, the entire
         input transport stream will be passed through to the specified output.
         Once written, the change to this parameter will only take immediate
         effect after semManRemuxMapApplyChange is set to 'apply'.  In order for the
         change to persist through subsequent reboots or power cycles, the
         change must be saved via the semSaveConfig parameter.

         @Commit(param=semManRemuxMapApplyChange, value=2)
        "
::= { semManRemuxMapEntry 12 }

semManRemuxMapInSvcPreEncryption OBJECT-TYPE
    SYNTAX EncryptedTYPE
    MAX-ACCESS read-write
    STATUS current
    DESCRIPTION
        "Indicates whether the input service is pre-encrypted or clear.  If
         pre-encrypted, setting this flag will cause the SEM to pass through
         ECM PIDs for this service, pass through the PIT message, and the
         output PMT will contain a GI CA ECM descriptor (referencing the ECM
         PID). When PID Remapping is enabled, pre-encryption for a service is
         only valid when the input ECM PID is on a different PID than the
         associated PMT PID. If this flag is set to pre-encryption and the
         input service is not pre-encrypted, then the setting of this flag has
         no affect on the output service.

         Once written, the change to this parameter will only take immediate
         effect after semManRemuxMapApplyChange is set to 'apply'.  In order for the
         change to persist through subsequent reboots or power cycles, the
         change must be saved via the semSaveConfig parameter.

         @Commit(param=semManRemuxMapApplyChange, value=2)
        "
::= { semManRemuxMapEntry 13 }


-- ------------------------------------------------------------------------------
--
-- semManRemuxOutTsTable
--

semManRemuxOutTsTable OBJECT-TYPE
    SYNTAX SEQUENCE OF SemManRemuxOutTsEntry
    MAX-ACCESS not-accessible
    STATUS current
    DESCRIPTION
        "Table of Manual Remultiplexing data that is applicable
         on an Output Transport Stream basis.

         @Config(config=yes, reboot=no)
         @Save(semSaveConfig, value=2)
         @File(mancfg.ini, type='ini')
        "
::= { semManRemuxConfig 2 }

semManRemuxOutTsEntry OBJECT-TYPE
    SYNTAX SemManRemuxOutTsEntry
    MAX-ACCESS not-accessible
    STATUS current
    DESCRIPTION
        "Manual Remultiplexing Out TS Table Entry."
    INDEX { semManRemuxOutTsOutTransStreamNum }
::= { semManRemuxOutTsTable 1 }

SemManRemuxOutTsEntry ::= SEQUENCE
    {
     semManRemuxOutTsOutTransStreamNum  Integer32,
     semManRemuxOutTsApplyChange        ApplyDataToDeviceTYPE,
     semManRemuxOutTsPatTsId            Integer32,
     semManRemuxOutTsOutputIp           IpAddress,
     semManRemuxOutTsOutputUdp          Integer32
    }

semManRemuxOutTsOutTransStreamNum OBJECT-TYPE
    SYNTAX Integer32 (1..16)
    MAX-ACCESS not-accessible
    STATUS current
    DESCRIPTION
        "The SEM output transport stream number."
::= { semManRemuxOutTsEntry 1 }

semManRemuxOutTsApplyChange OBJECT-TYPE
    SYNTAX ApplyDataToDeviceTYPE
    MAX-ACCESS read-write
    STATUS current
    DESCRIPTION
        "The Apply for the row off data in the Manual Remultiplexing Output
         Transport Stream Table.

         This parameter MUST be set to 'apply' in order for any of the data
         in the row to take effect in the SEM.  This parameter MUST be set
         LAST after all other data in the row has been configured.
        "
::= { semManRemuxOutTsEntry 2 }

semManRemuxOutTsPatTsId OBJECT-TYPE
    SYNTAX Integer32
    MAX-ACCESS read-write
    STATUS current
    DESCRIPTION
        "Output Transport Stream ID to use for the output PAT in this Output
         Transport Stream when in Manual Remultiplexing mode.

         Once written, the change to this parameter will only take immediate
         effect after semManRemuxOutTsApplyChange is set to 'apply'.  In order for the
         change to persist through subsequent reboots or power cycles, the
         change must be saved via the semSaveConfig parameter.

         @Range(min=0)
         @Commit(param=semManRemuxOutTsApplyChange, value=2)
        "
::= { semManRemuxOutTsEntry 3 }

semManRemuxOutTsOutputIp OBJECT-TYPE
    SYNTAX IpAddress
    MAX-ACCESS read-write
    STATUS current
    DESCRIPTION
        "Output IP address on which to place data. This parameter is
         for use with IP based output interfaces, otherwise is ignored.

         Once written, the change to this parameter will only take immediate
         effect after semManRemuxOutTsApplyChange is set to 'apply'.  In order for the
         change to persist through subsequent reboots or power cycles, the
         change must be saved via the semSaveConfig parameter.

         @Commit(param=semManRemuxOutTsApplyChange, value=2)
        "
::= { semManRemuxOutTsEntry 4 }

semManRemuxOutTsOutputUdp OBJECT-TYPE
    SYNTAX Integer32
    MAX-ACCESS read-write
    STATUS current
    DESCRIPTION
        "Output UDP port on which to place data. This parameter is
         for use with UDP based output interfaces, otherwise is ignored.

         Once written, the change to this parameter will only take immediate
         effect after semManRemuxOutTsApplyChange is set to 'apply'.  In order for the
         change to persist through subsequent reboots or power cycles, the
         change must be saved via the semSaveConfig parameter.

         @Range(min=0, max=65535)
         @Commit(param=semManRemuxOutTsApplyChange, value=2)
        "
::= { semManRemuxOutTsEntry 5 }


-- ------------------------------------------------------------------------------
--
-- semAsiDemux
--
-- semAsiDemuxConfig
--
-- semAsiDemuxConfigGeneral
--

semAsiDemuxConfigInSvcPreEncryption OBJECT-TYPE
    SYNTAX EncryptedTYPE
    MAX-ACCESS read-write
    STATUS current
    DESCRIPTION
        "Indicates whether the input services are pre-encrypted or clear. If
         pre-encrypted, setting this flag will cause the SEM to pass through
         ECM PIDs for all services, pass through the PIT message, and the
         output PMT will contain a GI CA ECM descriptor (referencing the ECM
         PID). When PID Remapping is enabled, pre-encryption for any service
         is only valid when the input ECM PID is on a different PID than the
         associated PMT PID.  If this flag is set to pre-encryption and an
         input service is not pre-encrypted, then the setting of this flag has
         no affect on the output service.

         Once written, the change to this parameter will take immediate
         effect and all mappings will be removed.  Mappings will not be
         re-added until semAsiDemuxConfigApplyChange is set to 'apply' for
         all transport streams.  In order for the change to persist through
         subsequent reboots or power cycles, the change must be saved via
         the semSaveConfig parameter.

         @Config(config=yes, reboot=no)
         @Save(semSaveConfig, value=2)
         @File(mancfg.ini, type='ini')
        "
::= { semAsiDemuxConfigGeneral 1 }


-- ------------------------------------------------------------------------------
--
-- semAsiDemuxConfigTable
--

semAsiDemuxConfigTable OBJECT-TYPE
    SYNTAX SEQUENCE OF SemAsiDemuxConfigEntry
    MAX-ACCESS not-accessible
    STATUS current
    DESCRIPTION
        "Table of ASI Demultiplexing Mode configuration data.

         @Config(config=yes, reboot=no)
         @Save(semSaveConfig, value=2)
         @File(mancfg.ini, type='ini')
        "
::= { semAsiDemuxConfig 2 }

semAsiDemuxConfigEntry OBJECT-TYPE
    SYNTAX SemAsiDemuxConfigEntry
    MAX-ACCESS not-accessible
    STATUS current
    DESCRIPTION
        "ASI Demultiplexing Mode Configuration Table Entry."
    INDEX { semAsiDemuxConfigOutTransStreamNum }
::= { semAsiDemuxConfigTable 1 }

SemAsiDemuxConfigEntry ::= SEQUENCE
    {
     semAsiDemuxConfigOutTransStreamNum   Integer32,
     semAsiDemuxConfigApplyChange         ApplyDataToDeviceTYPE,
     semAsiDemuxConfigAsiInputPort        Integer32,
     semAsiDemuxConfigStartProgramNumber  Integer32,
     semAsiDemuxConfigNumPrograms         Integer32,
     semAsiDemuxConfigOutPatTsId          Integer32,
     semAsiDemuxConfigOutIpAddr           IpAddress,
     semAsiDemuxConfigOutUdpPort          Integer32
    }

semAsiDemuxConfigOutTransStreamNum OBJECT-TYPE
    SYNTAX Integer32 (1..16)
    MAX-ACCESS not-accessible
    STATUS current
    DESCRIPTION
        "The SEM output transport stream number."
::= { semAsiDemuxConfigEntry 1 }

semAsiDemuxConfigApplyChange OBJECT-TYPE
    SYNTAX ApplyDataToDeviceTYPE
    MAX-ACCESS read-write
    STATUS current
    DESCRIPTION
        "The Apply for the ASI Demultiplexing table.

         This parameter MUST be set to 'apply' in order for any of the data
         in the semAsiDemuxConfigTable to take effect in the SEM.  This parameter
         MUST be set LAST after all other data in the semAsiDemuxConfigTable has
         been configured.
        "
::= { semAsiDemuxConfigEntry 2 }

semAsiDemuxConfigAsiInputPort OBJECT-TYPE
    SYNTAX Integer32
    MAX-ACCESS read-write
    STATUS current
    DESCRIPTION
        "Indicates the ASI input transport stream that will be routed to output
         transport streams.  Routing is done in user-defined groups of sequential
         program numbers.

         Once written, the change to this parameter will only take immediate
         effect after semAsiDemuxConfigApplyChange is set to 'apply'.  In order for the
         change to persist through subsequent reboots or power cycles, the
         change must be saved via the semSaveConfig parameter.

         @Range(min=0)
         @Commit(param=semAsiDemuxConfigApplyChange, value=2)
        "
::= { semAsiDemuxConfigEntry 3 }

semAsiDemuxConfigStartProgramNumber OBJECT-TYPE
    SYNTAX Integer32
    MAX-ACCESS read-write
    STATUS current
    DESCRIPTION
        "Indicates the first program number in a sequential range of programs
         that are to be routed to the same output transport stream.

         Once written, the change to this parameter will only take immediate
         effect after semAsiDemuxConfigApplyChange is set to 'apply'.  In order for the
         change to persist through subsequent reboots or power cycles, the
         change must be saved via the semSaveConfig parameter.

         @Range(min=0)
         @Commit(param=semAsiDemuxConfigApplyChange, value=2)
        "
::= { semAsiDemuxConfigEntry 4 }

semAsiDemuxConfigNumPrograms OBJECT-TYPE
    SYNTAX Integer32
    MAX-ACCESS read-write
    STATUS current
    DESCRIPTION
        "Indicates the number of programs in a sequential range of programs
         that are to be routed to the same output transport stream.

         Once written, the change to this parameter will only take immediate
         effect after semAsiDemuxConfigApplyChange is set to 'apply'.  In order for the
         change to persist through subsequent reboots or power cycles, the
         change must be saved via the semSaveConfig parameter.

         @Range(min=0)
         @Commit(param=semAsiDemuxConfigApplyChange, value=2)
        "
::= { semAsiDemuxConfigEntry 5 }

semAsiDemuxConfigOutPatTsId OBJECT-TYPE
    SYNTAX Integer32
    MAX-ACCESS read-write
    STATUS current
    DESCRIPTION
        "Output Transport Stream ID to use for the output PAT in this Output
         Transport Stream when in ASI Demultiplexing mode.

         Once written, the change to this parameter will only take immediate
         effect after semAsiDemuxConfigApplyChange is set to 'apply'.  In order for the
         change to persist through subsequent reboots or power cycles, the
         change must be saved via the semSaveConfig parameter.

         @Range(min=0)
         @Commit(param=semAsiDemuxConfigApplyChange, value=2)
        "
::= { semAsiDemuxConfigEntry 6 }

semAsiDemuxConfigOutIpAddr OBJECT-TYPE
    SYNTAX IpAddress
    MAX-ACCESS read-write
    STATUS current
    DESCRIPTION
        "The Output IP address for this output transport stream.

         Once written, the change to this parameter will only take immediate
         effect after semAsiDemuxConfigApplyChange is set to 'apply'.  In order for the
         change to persist through subsequent reboots or power cycles, the
         change must be saved via the semSaveConfig parameter.

         @Commit(param=semAsiDemuxConfigApplyChange, value=2)
        "
::= { semAsiDemuxConfigEntry 7 }

semAsiDemuxConfigOutUdpPort OBJECT-TYPE
    SYNTAX Integer32
    MAX-ACCESS read-write
    STATUS current
    DESCRIPTION
        "The Output UDP Port for this output transport stream.

         Once written, the change to this parameter will only take immediate
         effect after semAsiDemuxConfigApplyChange is set to 'apply'.  In order for the
         change to persist through subsequent reboots or power cycles, the
         change must be saved via the semSaveConfig parameter.

         @Range(min=0, max=65535)
         @Commit(param=semAsiDemuxConfigApplyChange, value=2)
        "
::= { semAsiDemuxConfigEntry 8 }


-- ------------------------------------------------------------------------------
--
-- semAsiDemuxStatus
--

semAsiDemuxInvalidApplyText OBJECT-TYPE
    SYNTAX DisplayString (SIZE (0..80))
    MAX-ACCESS read-only
    STATUS current
    DESCRIPTION
        "When semAsiDemuxConfigApplyChange is set to applyNotInProgressInvalidData
         this entry contains a text description of what was wrong with the data.
         This entry contains the description for the most recent apply of a PID
         Mapping table entry that was invalid."
::= { semAsiDemuxStatus 1 }


-- ------------------------------------------------------------------------------
--
-- semPsip
--
-- semPsipConfig
--
-- semPsipConfigGeneral
--

semPsipMgtMsgInsertionPeriod OBJECT-TYPE
    SYNTAX Unsigned32 (150..'ffffffff'h)
    MAX-ACCESS read-write
    STATUS current
    DESCRIPTION
        "Message insertion period in milliseconds for the PSIP Master Guide
         Table (MGT).
         This message is sent on the PSIP Base PID.
         This is the time between start of insertion of the first packet
         of the message.  For the packet insertion period refer to
         semPsipBasePidPacketInsertionPeriod.

         Once written, the change to this parameter will take immediate
         effect.  However, in order for the change to persist through
         subsequent reboots or power cycles, the change must be saved via
         the semSaveConfig parameter.

         @Config(config=yes, reboot=no)
         @Save(semSaveConfig, value=2)
         @File(config.ini, type='ini')
        "
::= { semPsipConfigGeneral 1 }


semPsipSttMsgInsertionPeriod OBJECT-TYPE
    SYNTAX Unsigned32 (1000..'ffffffff'h)
    MAX-ACCESS read-write
    STATUS current
    DESCRIPTION
        "Message insertion period in milliseconds for the PSIP System Time
         Table (STT).
         This message is sent on the PSIP Base PID.
         This is the time between start of insertion of the first packet
         of the message.  For the packet insertion period refer to
         semPsipBasePidPacketInsertionPeriod.

         Once written, the change to this parameter will take immediate
         effect.  However, in order for the change to persist through
         subsequent reboots or power cycles, the change must be saved via
         the semSaveConfig parameter.

         @Config(config=yes, reboot=no)
         @Save(semSaveConfig, value=2)
         @File(config.ini, type='ini')
        "
::= { semPsipConfigGeneral 2 }

semPsipCvctMsgInsertionPeriod OBJECT-TYPE
    SYNTAX Unsigned32 (400..'ffffffff'h)
    MAX-ACCESS read-write
    STATUS current
    DESCRIPTION
        "Message insertion period in milliseconds for the PSIP Cable Virtual
         Channel Table (CVCT).
         This message is sent on the PSIP Base PID.
         This is the time between start of insertion of the first packet
         of the message.  For the packet insertion period refer to
         semPsipBasePidPacketInsertionPeriod.

         Once written, the change to this parameter will take immediate
         effect.  However, in order for the change to persist through
         subsequent reboots or power cycles, the change must be saved via
         the semSaveConfig parameter.

         @Config(config=yes, reboot=no)
         @Save(semSaveConfig, value=2)
         @File(config.ini, type='ini')
        "
::= { semPsipConfigGeneral 3 }

semPsipRrtMsgInsertionPeriod OBJECT-TYPE
    SYNTAX Unsigned32 (60000..'ffffffff'h)
    MAX-ACCESS read-write
    STATUS current
    DESCRIPTION
        "Message insertion period in milliseconds for the PSIP Rating Region
         Table (RRT).
         This message is sent on the PSIP Base PID.
         This is the time between start of insertion of the first packet
         of the message.  For the packet insertion period refer to
         semPsipBasePidPacketInsertionPeriod.

         Once written, the change to this parameter will take immediate
         effect.  However, in order for the change to persist through
         subsequent reboots or power cycles, the change must be saved via
         the semSaveConfig parameter.

         @Config(config=yes, reboot=no)
         @Save(semSaveConfig, value=2)
         @File(config.ini, type='ini')
        "
::= { semPsipConfigGeneral 4 }

semPsipBasePidPacketInsertionPeriod OBJECT-TYPE
    SYNTAX Unsigned32 (1..'ffffffff'h)
    MAX-ACCESS read-write
    STATUS current
    DESCRIPTION
        "Packet insertion period in milliseconds for Base PID packets.
         Messages sent on the PSIP Base PID include the MGT, SST,
         CVCT and RRT.
         This is the minimum time between packet insertions.  The
         actual packet insertion period could be delayed depending
         on SEM processor load.

         Once written, the change to this parameter will take immediate
         effect.  However, in order for the change to persist through
         subsequent reboots or power cycles, the change must be saved via
         the semSaveConfig parameter.

         @Config(config=yes, reboot=no)
         @Save(semSaveConfig, value=2)
         @File(config.ini, type='ini')
        "
::= { semPsipConfigGeneral 5 }

semPsipNumEitPerOutputStream OBJECT-TYPE
    SYNTAX Unsigned32(0..4)
    MAX-ACCESS read-write
    STATUS current
    DESCRIPTION
        "Number of Event Information Tables per Output Transport Stream.

         Once written, a save must be performed via the semSaveConfig
         parameter and the SEM must be rebooted for the change to take effect.

         @Config(config=yes, reboot=yes)
         @Save(semSaveConfig, value=2)
         @File(config.ini, type='ini')
        "
::= { semPsipConfigGeneral 6 }


-- ------------------------------------------------------------------------------
--
-- semPsipConfigTable
--

semPsipConfigTable OBJECT-TYPE
    SYNTAX SEQUENCE OF SemPsipConfigEntry
    MAX-ACCESS not-accessible
    STATUS current
    DESCRIPTION
        "This is a table of PSIP configuration parameters for the
         Output Transport Streams."
::= { semPsipConfig 2 }

semPsipConfigEntry OBJECT-TYPE
    SYNTAX SemPsipConfigEntry
    MAX-ACCESS not-accessible
    STATUS current
    DESCRIPTION
        "PSIP Configuration Table Entry."
    INDEX { semPsipConfigOutStreamNum }
::= { semPsipConfigTable 1 }

SemPsipConfigEntry ::= SEQUENCE
    {
     semPsipConfigOutStreamNum         Integer32,
     semPsipConfigEnable               EnableDisableTYPE
    }

semPsipConfigOutStreamNum OBJECT-TYPE
    SYNTAX Integer32(1..16)
    MAX-ACCESS not-accessible
    STATUS current
    DESCRIPTION
        "Output Transport Stream Number."
::= { semPsipConfigEntry 1 }

semPsipConfigEnable OBJECT-TYPE
    SYNTAX EnableDisableTYPE
    MAX-ACCESS read-write
    STATUS current
    DESCRIPTION
        "This parameter indicates that PSIP is enabled for the Output
         Transport Stream.

         Once written, a save must be performed via the semSaveConfig
         parameter and the SEM must be rebooted for the change to take effect.

         @Config(config=yes, reboot=yes)
         @Save(semSaveConfig, value=2)
         @File(config.ini, type='ini')
        "
::= { semPsipConfigEntry 2 }


-- ------------------------------------------------------------------------------
--
-- semPsipEitConfigTable
--

semPsipEitConfigTable OBJECT-TYPE
    SYNTAX SEQUENCE OF SemPsipEitConfigEntry
    MAX-ACCESS not-accessible
    STATUS current
    DESCRIPTION
        "This is a table of PSIP Event Information Table
         configuration parameters."
::= { semPsipConfig 3 }

semPsipEitConfigEntry OBJECT-TYPE
    SYNTAX SemPsipEitConfigEntry
    MAX-ACCESS not-accessible
    STATUS current
    DESCRIPTION
        "PSIP EIT Configuration Table Entry."
    INDEX { semPsipEitConfigEitIndex }
::= { semPsipEitConfigTable 1 }

SemPsipEitConfigEntry ::= SEQUENCE
    {
     semPsipEitConfigEitIndex               Integer32,
     semPsipEitConfigMsgInsertionPeriod     Unsigned32,
     semPsipEitConfigPacketInsertionPeriod  Unsigned32
    }

semPsipEitConfigEitIndex OBJECT-TYPE
    SYNTAX Integer32(1..4)
    MAX-ACCESS not-accessible
    STATUS current
    DESCRIPTION
        "EIT index.  This index is one greater than the EIT Number
         which is zero based."
::= { semPsipEitConfigEntry 1 }

semPsipEitConfigMsgInsertionPeriod OBJECT-TYPE
    SYNTAX Unsigned32 (500..'ffffffff'h)
    MAX-ACCESS read-write
    STATUS current
    DESCRIPTION
        "Message insertion period in milliseconds for the PSIP Event
         Information Table (EIT).
         This is the time between start of insertion of the first packet
         of the message.  For the packet insertion period refer to
         semPsipBasePidPacketInsertionPeriod.

         Once written, the change to this parameter will take immediate
         effect.  However, in order for the change to persist through
         subsequent reboots or power cycles, the change must be saved via
         the semSaveConfig parameter.

         @Config(config=yes, reboot=no)
         @Save(semSaveConfig, value=2)
         @File(config.ini, type='ini')
        "
::= { semPsipEitConfigEntry 2 }

semPsipEitConfigPacketInsertionPeriod OBJECT-TYPE
    SYNTAX Unsigned32 (1..'ffffffff'h)
    MAX-ACCESS read-write
    STATUS current
    DESCRIPTION
        "Packet insertion period in milliseconds for a packet of the PSIP
         Event Information Table (EIT) message.
         This is the minimum time between packet insertions.  The
         actual packet insertion period could be delayed depending
         on SEM processor load.

         Once written, the change to this parameter will take immediate
         effect.  However, in order for the change to persist through
         subsequent reboots or power cycles, the change must be saved via
         the semSaveConfig parameter.

         @Config(config=yes, reboot=no)
         @Save(semSaveConfig, value=2)
         @File(config.ini, type='ini')
        "
::= { semPsipEitConfigEntry 3 }


-- ------------------------------------------------------------------------------
--
-- semPsipStatus
--
-- semPsipStatusGeneral
--

semPsipInputCount OBJECT-TYPE
    SYNTAX Integer32
    MAX-ACCESS read-only
    STATUS current
    DESCRIPTION
        "Number of input ports that may contain PSIP data.  Zero
         indicates PSIP is not supported by this SEM."
::= { semPsipStatusGeneral 1 }


-- ------------------------------------------------------------------------------
--
-- semDvs208Eas
--
-- semDvs208EasConfig
--
-- semDvs208EasConfigGeneral
--

semDvs208EasEnable OBJECT-TYPE
    SYNTAX EnableDisableTYPE
    MAX-ACCESS read-write
    STATUS current
    DESCRIPTION
        "This parameter indicates that DVS-208 EAS is enabled.

         Once written, a save must be performed via the semSaveConfig
         parameter and the SEM must be rebooted for the change to take effect.

         @Config(config=yes, reboot=yes)
         @Save(semSaveConfig, value=2)
         @File(config.ini, type='ini')
        "
::= { semDvs208EasConfigGeneral 1 }

semDvs208EasHostEnet OBJECT-TYPE
    SYNTAX SemHostEnetTYPE
    MAX-ACCESS read-write
    STATUS current
    DESCRIPTION
        "This parameter indicates the Host Fast Ethernet interface on which
         to receive DVS-208 EAS messages.

         Once written, a save must be performed via the semSaveConfig
         parameter and the SEM must be rebooted for the change to take effect.

         @Config(config=yes, reboot=yes)
         @Save(semSaveConfig, value=2)
         @File(config.ini, type='ini')
        "
::= { semDvs208EasConfigGeneral 2 }

semDvs208EasUdpPort OBJECT-TYPE
    SYNTAX Integer32(1033..65535)
    MAX-ACCESS read-write
    STATUS current
    DESCRIPTION
        "This parameter indicates the UDP port on which to receive DVS-208
         EAS messages.

         Once written, a save must be performed via the semSaveConfig
         parameter and the SEM must be rebooted for the change to take effect.

         @Config(config=yes, reboot=yes)
         @Save(semSaveConfig, value=2)
         @File(config.ini, type='ini')
        "
::= { semDvs208EasConfigGeneral 3 }

semDvs208EasMulticastRcvIpAddr OBJECT-TYPE
    SYNTAX IpAddress
    MAX-ACCESS read-write
    STATUS current
    DESCRIPTION
        "This parameter indicates the Multicast IP Receive address on which
         to receive DVS-208 EAS messages. If a valid multicast IP address,
         the EAS messages will be received via singlecast, network broadcast,
         and multicast. If 0.0.0.0, then EAS messages will be received via
         network broadcast and singlecast only.

         Once written, a save must be performed via the semSaveConfig
         parameter and the SEM must be rebooted for the change to take effect.

         @Config(config=yes, reboot=yes)
         @Save(semSaveConfig, value=2)
         @File(config.ini, type='ini')
        "
::= { semDvs208EasConfigGeneral 4 }


-- ------------------------------------------------------------------------------
--
-- semDvs208EasStatus
--
-- semDvs208EasStatusGeneral
--

semDvs208EasNumRcvMsgs OBJECT-TYPE
    SYNTAX Unsigned32
    MAX-ACCESS read-only
    STATUS current
    DESCRIPTION
        "Total number of EAS messages received."
::= { semDvs208EasStatusGeneral 1 }

semDvs208EasNumInvalRcvMsgs OBJECT-TYPE
    SYNTAX Unsigned32
    MAX-ACCESS read-only
    STATUS current
    DESCRIPTION
        "Total number of Invalid EAS messages received (invalid CRC).
         These messages are discarded."
::= { semDvs208EasStatusGeneral 2 }


-- ------------------------------------------------------------------------------
--
-- semEntitlements
--

semEntTransEncryptMcDes OBJECT-TYPE
    SYNTAX EntitlementTYPE
    MAX-ACCESS read-only
    STATUS current
    DESCRIPTION
        "This read only status variable defines whether or not this SEM is authorized
         to use DES for the transport encryption mode. This setting is determined
         by the entitlements granted at the factory."
::= { semEntTransportEncrypt 2 }

semEntTransEncryptCsaV1 OBJECT-TYPE
    SYNTAX EntitlementTYPE
    MAX-ACCESS read-only
    STATUS current
    DESCRIPTION
        "This read only status variable defines whether or not this SEM is authorized
         to use CSA v1 for the transport encryption mode. This setting is determined
         by the entitlements granted at the factory."
::= { semEntTransportEncrypt 4 }

semEntControlWordSharing OBJECT-TYPE
    SYNTAX EntitlementTYPE
    MAX-ACCESS read-only
    STATUS current
    DESCRIPTION
        "This read only status variable defines whether or not this SEM is authorized
         to distribute control words in a simulcrypt configuration. This setting is
         determined by the entitlements granted at the factory."
::= { semEntControlWordDelivery 1 }

semEntControlWordClear OBJECT-TYPE
    SYNTAX EntitlementTYPE
    MAX-ACCESS read-only
    STATUS current
    DESCRIPTION
        "This read only status variable defines whether or not this SEM is authorized
         to distribute clear text control words in a simulcrypt configuration. This
         setting is determined by the entitlements granted at the factory."
::= { semEntControlWordDelivery 2 }


-- ------------------------------------------------------------------------------
--
-- semPidMapConfig
--
-- semPidMapTable
--

semPidMapTable OBJECT-TYPE
    SYNTAX SEQUENCE OF SemPidMapEntry
    MAX-ACCESS not-accessible
    STATUS current
    DESCRIPTION
        "Table of data for Pid Mapping.

         Writes to any of these fields do not take effect until the
         parameter semPidMapApplyChange, is written.
         Additionally, in order for the change to persist through
         subsequent reboots or power cycles, the change must be saved via
         the semSaveConfig parameter.

         @Config(config=yes, reboot=no)
         @Save(semSaveConfig, value=2)
         @File(mancfg.ini, type='ini')
        "
::= { semPidMapConfig 1 }

semPidMapEntry OBJECT-TYPE
    SYNTAX SemPidMapEntry
    MAX-ACCESS not-accessible
    STATUS current
    DESCRIPTION
        "Pid Mapping Table Entry."
    INDEX { semPidMapIndex }
::= { semPidMapTable 1 }

SemPidMapEntry ::= SEQUENCE
    {
     semPidMapIndex             Integer32,
     semPidMapApplyChange       ApplyDataToDeviceTYPE,
     semPidMapEnable            EnableDisableTYPE,
     semPidMapPhysInType        INTEGER,
     semPidMapPhysInPort        Integer32,
     semPidMapInputUdp          Integer32,
     semPidMapInputPid          Integer32,
     semPidMapOutTransStreamNum Integer32,
     semPidMapOutputPid         Integer32
    }

semPidMapIndex OBJECT-TYPE
    SYNTAX Integer32 (1..128)
    MAX-ACCESS not-accessible
    STATUS current
    DESCRIPTION
        "Index of Pid Mapping Table."
::= { semPidMapEntry 1 }

semPidMapApplyChange OBJECT-TYPE
    SYNTAX ApplyDataToDeviceTYPE
    MAX-ACCESS read-write
    STATUS current
    DESCRIPTION
        "The Apply for the row of data in the Pid Map Table.

         This parameter MUST be set to 'apply' in order for any of the data
         in the row to take effect in the SEM.  This parameter MUST be set
         LAST after all other data in the row has been configured.
        "
::= { semPidMapEntry 2 }

semPidMapEnable OBJECT-TYPE
    SYNTAX EnableDisableTYPE
    MAX-ACCESS read-write
    STATUS current
    DESCRIPTION
        "Indicates whether this Pid Mapping is enabled or disabled.

         Once written, the change to this parameter will only take immediate
         effect after semPidMapApplyChange is set to 'apply'.  In order for the
         change to persist through subsequent reboots or power cycles, the
         change must be saved via the semSaveConfig parameter.

         @Commit(param=semPidMapApplyChange, value=2)
        "
::= { semPidMapEntry 3 }

semPidMapPhysInType OBJECT-TYPE
    SYNTAX INTEGER
        {
         gbe       (1),
         asi       (2),
         hostEnet  (3)
        }
    MAX-ACCESS read-write
    STATUS current
    DESCRIPTION
        "Input Type of input from which to obtain data.

         Once written, the change to this parameter will only take immediate
         effect after semPidMapApplyChange is set to 'apply'.  In order for the
         change to persist through subsequent reboots or power cycles, the
         change must be saved via the semSaveConfig parameter.

         @Commit(param=semPidMapApplyChange, value=2)
        "
::= { semPidMapEntry 4 }

semPidMapPhysInPort OBJECT-TYPE
    SYNTAX Integer32
    MAX-ACCESS read-write
    STATUS current
    DESCRIPTION
        "Number of the input, of type configured by PhysInType,
         from which to obtain data.

         Once written, the change to this parameter will only take immediate
         effect after semPidMapApplyChange is set to 'apply'.  In order for the
         change to persist through subsequent reboots or power cycles, the
         change must be saved via the semSaveConfig parameter.

         @Range(min=0)
         @Commit(param=semPidMapApplyChange, value=2)
        "
::= { semPidMapEntry 5 }

semPidMapInputUdp OBJECT-TYPE
SYNTAX Integer32
    MAX-ACCESS read-write
    STATUS current
    DESCRIPTION
        "Input UDP Port from which to obtain data.  This parameter is
         for use with UDP based input interfaces, otherwise is ignored.

         Once written, the change to this parameter will only take immediate
         effect after semPidMapApplyChange is set to 'apply'.  In order for the
         change to persist through subsequent reboots or power cycles, the
         change must be saved via the semSaveConfig parameter.

         @Range(min=0, max=65535)
         @Commit(param=semPidMapApplyChange, value=2)
        "
::= { semPidMapEntry 6 }

semPidMapInputPid OBJECT-TYPE
    SYNTAX Integer32
    MAX-ACCESS read-write
    STATUS current
    DESCRIPTION
        "Input MPEG PID to multiplex.

         Once written, the change to this parameter will only take immediate
         effect after semPidMapApplyChange is set to 'apply'.  In order for the
         change to persist through subsequent reboots or power cycles, the
         change must be saved via the semSaveConfig parameter.

         @Range(min=0)
         @Commit(param=semPidMapApplyChange, value=2)
        "
::= { semPidMapEntry 7 }

semPidMapOutTransStreamNum OBJECT-TYPE
    SYNTAX Integer32 (0..16)
    MAX-ACCESS read-write
    STATUS current
    DESCRIPTION
        "Output Transport Stream Number of the output on which to place data.
         This serves as an index into the semOutTransStreamTable.
         Zero is only valid if the semPidMapTable entry is not being used.

         Once written, the change to this parameter will only take immediate
         effect after semPidMapApplyChange is set to 'apply'.  In order for the
         change to persist through subsequent reboots or power cycles, the
         change must be saved via the semSaveConfig parameter.

         @Commit(param=semPidMapApplyChange, value=2)
        "
::= { semPidMapEntry 8 }

semPidMapOutputPid OBJECT-TYPE
    SYNTAX Integer32
    MAX-ACCESS read-write
    STATUS current
    DESCRIPTION
        "Output PID to use for the data.

         Once written, the change to this parameter will only take immediate
         effect after semPidMapApplyChange is set to 'apply'.  In order for the
         change to persist through subsequent reboots or power cycles, the
         change must be saved via the semSaveConfig parameter.

         @Range(min=0)
         @Commit(param=semPidMapApplyChange, value=2)
        "
::= { semPidMapEntry 9 }


-- ------------------------------------------------------------------------------
--
-- semPidMapStatus
--

semPidMapInvalidApplyText OBJECT-TYPE
    SYNTAX DisplayString (SIZE (0..80))
    MAX-ACCESS read-only
    STATUS current
    DESCRIPTION
        "When semPidMapApplyChange is set to applyNotInProgressInvalidData this
         entry contains a text description of what was wrong with the data.
         This entry contains the description for the most recent apply of a
         table entry that was invalid."
::= { semPidMapStatus 1 }


-- ------------------------------------------------------------------------------
--
-- semInternalControlOfEncryption
--
-- semIceConfig
--
-- semIceConfigGeneral
--

-- No entries in this group at this time.


-- ------------------------------------------------------------------------------
--
-- semIceProgramConfig
--

semIceProgramConfigApplyChange OBJECT-TYPE
    SYNTAX ApplyDataToDeviceTYPE
    MAX-ACCESS read-write
    STATUS current
    DESCRIPTION
        "The Apply for any entries in the semIceProgramConfig group.

         This parameter MUST be set to 'apply' in order for any of the data
         in the semIceProgramConfig group to take effect in the SEM.  This
         parameter MUST be set LAST after all other data in the group has
         been configured.

         In general, any change to the semIceProgramConfig parameters will
         cause all currently mapped programs to be stopped and restarted. This
         will cause a momentary loss of service on all SEM outputs.

         Once written, the change to this parameter will take immediate effect.

         @Config(config=no, reboot=no)
        "
::= { semIceProgramConfig 1 }

semIceSetDefault OBJECT-TYPE
    SYNTAX INTEGER
        {
         notSettingToDefault (1),
         setToDefault        (2)
        }
    MAX-ACCESS read-write
    STATUS current
    DESCRIPTION
        "This parameter is used to set all data in the semIceProgramConfig
         group to their default values except semIceCommonTierEncryptionEnable
         and semIceEncryptionMode.

         Once written, the change to this parameter will only take immediate
         effect after semIceProgramConfigApplyChange is set to 'apply'.

         @Commit(param=semIceProgramConfigApplyChange, value=2)
         @Config(config=no, reboot=no)
        "
::= { semIceProgramConfig 2 }

semIceCommonTierEncryptionEnable OBJECT-TYPE
    SYNTAX EnableDisableTYPE
    MAX-ACCESS read-write
    STATUS current
    DESCRIPTION
        "This parameter is used to enable or disable the Common Tier Encryption (CTE).

         CTE cannot be enabled unless the SEM has been licensed for CTE and the ACP
         module is present (semAcpModuleInstalled).

         This parameter is not changed by semIceSetDefault.

         This parameter only applies when the SEM is in an internal
         semDeviceOperatingMode.  When the SEM is in an external
         semDeviceOperatingMode this parameter is ignored.

         Once written, the change to this parameter will only take immediate
         effect after semIceProgramConfigApplyChange is set to 'apply'.  In
         order for the change to persist through subsequent reboots or power
         cycles, the change must be saved via the semSaveConfig parameter.

         @Commit(param=semIceProgramConfigApplyChange, value=2)
         @Config(config=yes, reboot=no)
         @Save(semSaveConfig, value=2)
         @File(config.ini, type='ini')
        "
::= { semIceProgramConfig 3 }

semIceEncryptionMode OBJECT-TYPE
    SYNTAX INTEGER
        {
         clear (1),
         fpk   (2),
         full  (3)
        }
    MAX-ACCESS read-write
    STATUS current
    DESCRIPTION
        "This parameter is used to set the Global Encryption Mode.
           - 'clear' - The SEM performs no encryption of output programs.
                       Selecting this will clear ICE alarms semAlarmIceFullEncryptFailure,
                       semAlarmIceEmmServerCommFailure, and semAlarmIceEmmServerInvalidResponse.

           - 'fpk'   - The SEM will use Fixed Program Key (FPK) encryption. The SEM
                       will not attempt to get Entitlement Management Messages (EMMs)
                       nor will it alarm if EMM Server (EMMS) communication fails.
                       Selecting this will clear ICE alarms semAlarmIceFullEncryptFailure,
                       semAlarmIceEmmServerCommFailure, and semAlarmIceEmmServerInvalidResponse.

           - 'full'  - The SEM will use Full encryption. The SEM will only be able to
                       encrypt programs in Full encryption mode if the SEM is able to
                       communicate with an EMM Server. If unable to communicate with
                       an EMMS, then the SEM will encrypt programs using FPK mode. The
                       SEM will alarm if EMMS communication fails.

         This parameter is not changed by semIceSetDefault.

         This parameter can only be set to 'clear' unless semIceCommonTierEncryptionEnable
         is set to 'enabled'.

         This parameter applies to all programs on the SEM. If pre-encryption is
         enabled and fpk or full is selected, then the SEM will only encrypt those
         programs that are not already pre-encrypted.  Pre-encryption is determined
         by the presence of a GI CA ECM descriptor on the input service PMT.

         This parameter only applies when the SEM is in an internal
         semDeviceOperatingMode.  When the SEM is in an external
         semDeviceOperatingMode this parameter is ignored.

         Once written, the change to this parameter will only take immediate
         effect after semIceProgramConfigApplyChange is set to 'apply'.  In
         order for the change to persist through subsequent reboots or power
         cycles, the change must be saved via the semSaveConfig parameter.

         @Commit(param=semIceProgramConfigApplyChange, value=2)
         @Config(config=yes, reboot=no)
         @Save(semSaveConfig, value=2)
         @File(config.ini, type='ini')
        "
::= { semIceProgramConfig 4 }

semIceCciLevel OBJECT-TYPE
    SYNTAX INTEGER
        {
         notDefined (1),
         copyFreely (2),
         copyOnce   (3),
         copyNever  (4)
        }
    MAX-ACCESS read-write
    STATUS current
    DESCRIPTION
        "Internal Control of Encryption (ICE) Copy Control Information (CCI)
         Level setting for PRK messages.
           - notDefined - CCI is not defined, settop box applications can
                          configure CCI
           - copyFreely - program can be copied
           - copyOnce   - program can be copied once
           - copyNever  - program can never be copied

         This parameter applies to all programs on the SEM.

         This parameter only applies when the SEM is in an internal
         semDeviceOperatingMode and semIceEncryptionMode is set to 'fpk' or 'full'.

         Once written, the change to this parameter will only take immediate
         effect after semIceProgramConfigApplyChange is set to 'apply'.  In
         order for the change to persist through subsequent reboots or power
         cycles, the change must be saved via the semSaveConfig parameter.

         @Commit(param=semIceProgramConfigApplyChange, value=2)
         @Config(config=yes, reboot=no)
         @Save(semSaveConfig, value=2)
         @File(config.ini, type='ini')
        "
::= { semIceProgramConfig 5 }

semIceCciLevelSource OBJECT-TYPE
    SYNTAX INTEGER
        {
         input      (1),
         configured (2)
        }
    MAX-ACCESS read-write
    STATUS current
    DESCRIPTION
        "Internal Control of Encryption (ICE) Copy Control Information (CCI)
         Level, APS level, and CIT source setting for PRK messages.
           - 'input'      - The CCI, APS, and CIT levels for each output service will be the
                            CCI, APS, CIT levels of the associated input service. If the
                            input service does not contain a DTCP descriptor,
                            then the semIceCciLevel value will be used.

           - 'configured' - Always use user configured semIceCciLevel value
                            (input CCI, APS, and CIT level are ignored).

         This parameter applies to all programs on the SEM.

         This parameter only applies when the SEM is in an internal
         semDeviceOperatingMode and semIceEncryptionMode is set to 'fpk' or 'full'.

         Once written, the change to this parameter will only take immediate
         effect after semIceProgramConfigApplyChange is set to 'apply'.  In
         order for the change to persist through subsequent reboots or power
         cycles, the change must be saved via the semSaveConfig parameter.

         @Commit(param=semIceProgramConfigApplyChange, value=2)
         @Config(config=yes, reboot=no)
         @Save(semSaveConfig, value=2)
         @File(config.ini, type='ini')
        "
::= { semIceProgramConfig 6 }

semIceApsLevel OBJECT-TYPE
    SYNTAX INTEGER
        {
         notDefined       (1),
         off              (2),
         splitBurstOn     (3),
         splitBurst2Line  (4),
         splitBurst4Line  (5)
        }
    MAX-ACCESS read-write
    STATUS current
    DESCRIPTION
        "Internal Control of Encryption (ICE) Analog Protection System (APS)
         Level setting for PRK messages.  Defines what copy protection encoding
         will be applied to the analog composite output by the settop box.
           - notDefined      - analog protection is not defined, settop box
                               applications can configure APS
           - off             - no analog protection
           - splitBurstOn    - split burst on
           - splitBurst2Line - 2 line split burst on
           - splitBurst4Line - 4 line split burst on

         It should also be noted that the SEM will set Tier Type based on
         semIceApsLevel setting.  The SEM will set tier type to subscription
         with right to tape when semIceApsLevel is 'off' or 'notDefined'.
         The SEM will set tier type to subscription without right to tape when
         semIceApsLevel is 'splitBurstOff', 'splitBurst2Line', or 'splitBurst4Line'.

         This parameter applies to all programs on the SEM.

         This parameter only applies when the SEM is in an internal
         semDeviceOperatingMode and semIceEncryptionMode is set to 'fpk' or 'full'.

         Once written, the change to this parameter will only take immediate
         effect after semIceProgramConfigApplyChange is set to 'apply'.  In
         order for the change to persist through subsequent reboots or power
         cycles, the change must be saved via the semSaveConfig parameter.

         @Commit(param=semIceProgramConfigApplyChange, value=2)
         @Config(config=yes, reboot=no)
         @Save(semSaveConfig, value=2)
         @File(config.ini, type='ini')
        "
::= { semIceProgramConfig 7 }

semIceTier OBJECT-TYPE
    SYNTAX Integer32(0..16777215)
    MAX-ACCESS read-write
    STATUS current
    DESCRIPTION
        "Internal Control of Encryption (ICE) Program Tier.  Identifies the
         tier number for which access is granted.  Range is 0 to 16777215.
         65535 is reserved and cannot be selected.

         This parameter applies to all programs on the SEM.

         It should also be noted that the SEM will set Tier Type based on
         semIceApsLevel setting.  Refer to semIceApsLevel description
         for more details.

         This parameter only applies when the SEM is in an internal
         semDeviceOperatingMode and semIceEncryptionMode is set to 'fpk' or 'full'.

         Once written, the change to this parameter will only take immediate
         effect after semIceProgramConfigApplyChange is set to 'apply'.  In
         order for the change to persist through subsequent reboots or power
         cycles, the change must be saved via the semSaveConfig parameter.

         @Commit(param=semIceProgramConfigApplyChange, value=2)
         @Config(config=yes, reboot=no)
         @Save(semSaveConfig, value=2)
         @File(config.ini, type='ini')
        "
::= { semIceProgramConfig 8 }

semIceEpochDuration OBJECT-TYPE
    SYNTAX Integer32(1..24)
    MAX-ACCESS read-write
    STATUS current
    DESCRIPTION
        "Internal Control of Encryption (ICE) Epoch Duration.  Duration in
         hours for the program epoch.  Specifies the number of hours for
         each program epoch.

         This parameter applies to all programs on the SEM.

         This parameter only applies when the SEM is in an internal
         semDeviceOperatingMode and semIceEncryptionMode is set to 'fpk' or 'full'.

         Once written, the change to this parameter will only take immediate
         effect after semIceProgramConfigApplyChange is set to 'apply'.  In
         order for the change to persist through subsequent reboots or power
         cycles, the change must be saved via the semSaveConfig parameter.

         @Commit(param=semIceProgramConfigApplyChange, value=2)
         @Config(config=yes, reboot=no)
         @Save(semSaveConfig, value=2)
         @File(config.ini, type='ini')
        "
::= { semIceProgramConfig 9 }

semIceConstrainedImageTrigger OBJECT-TYPE
    SYNTAX EnableDisableTYPE
    MAX-ACCESS read-write
    STATUS current
    DESCRIPTION
        "Internal Control of Encryption (ICE) Constrained Image Trigger (CIT).
         If set to 'enabled' the settop box is notified not to allow a high
         quality digital output unless the receiving device also adheres to
         CIT processing. If the semIceApsLevel is set to 'notDefined', the
         setting of the CIT value has no affect (CIT and APS are only used
         when APS is set to a defined value).

         This parameter applies to all programs on the SEM.

         This parameter only applies when the SEM is in an internal
         semDeviceOperatingMode and semIceEncryptionMode is set to 'fpk' or 'full'.

         Once written, the change to this parameter will only take immediate
         effect after semIceProgramConfigApplyChange is set to 'apply'.  In
         order for the change to persist through subsequent reboots or power
         cycles, the change must be saved via the semSaveConfig parameter.

         @Commit(param=semIceProgramConfigApplyChange, value=2)
         @Config(config=yes, reboot=no)
         @Save(semSaveConfig, value=2)
         @File(config.ini, type='ini')
        "
::= { semIceProgramConfig 10 }


-- ------------------------------------------------------------------------------
--
-- semIceEmmConfig
--

semIceEmmConfigApplyChange OBJECT-TYPE
    SYNTAX ApplyDataToDeviceTYPE
    MAX-ACCESS read-write
    STATUS current
    DESCRIPTION
        "The Apply for any entries in the semIceEmmConfig group.

         The parameters in the semIceEmmConfig group only apply when the SEM is
         in an internal semDeviceOperatingMode and semIceEncryptionMode is set
         to 'full'.

         This parameter MUST be set to 'apply' in order for any of the data
         in the semIceEmmConfig group to take effect in the SEM.  This
         parameter MUST be set LAST after all other data in the group has
         been configured.

         Once written, the change to this parameter will take immediate effect.

         @Config(config=no, reboot=no)
        "
::= { semIceEmmConfig 1 }

semIceEmmSetDefault OBJECT-TYPE
    SYNTAX INTEGER
        {
         notSettingToDefault (1),
         setToDefault        (2)
        }
    MAX-ACCESS read-write
    STATUS current
    DESCRIPTION
        "This parameter is used to set all data in the semIceEmmConfig
         group to their default values except for semIceEmmServerIpAddr.
         It should also be noted that EMM Refresh and alarms and
         error/failure counts are not reset to defaults.

         Once written, the change to this parameter will only take immediate
         effect after semIceEmmConfigApplyChange is set to 'apply'.

         @Commit(param=semIceEmmConfigApplyChange, value=2)
         @Config(config=no, reboot=no)
        "
::= { semIceEmmConfig 2 }

semIceEmmPollInterval OBJECT-TYPE
    SYNTAX Integer32(15..1440)
    MAX-ACCESS read-write
    STATUS current
    DESCRIPTION
        "Internal Control of Encryption (ICE) Entitlement Management Message
         (EMM) Polling Interval.  Duration is in minutes for EMM Polling. This
         is the time period that the SEM will poll for CSN/State information.
         After receiving the CSN/State information, the SEM will determine if it
         needs to retrieve new EMMs from the EMMS. If the SEM is unable to
         communicate with the EMMS, then the SEM will revert to a 15 minute polling
         period until communication with the EMMS is re-established.

         This parameter only applies when the SEM is in an internal
         semDeviceOperatingMode and semIceEncryptionMode is set to 'full'.

         Once written, the change to this parameter will only take immediate
         effect after semIceEmmConfigApplyChange is set to 'apply'.  In
         order for the change to persist through subsequent reboots or power
         cycles, the change must be saved via the semSaveConfig parameter.

         @Commit(param=semIceEmmConfigApplyChange, value=2)
         @Config(config=yes, reboot=no)
         @Save(semSaveConfig, value=2)
         @File(config.ini, type='ini')
        "
::= { semIceEmmConfig 3 }

semIceEmmPollRandomization OBJECT-TYPE
    SYNTAX Integer32(0..10)
    MAX-ACCESS read-write
    STATUS current
    DESCRIPTION
        "Internal Control of Encryption (ICE) Entitlement Management Message
         (EMM) Polling Randomization Time.  Maximum time in minutes to delay
         polling at startup in order to avoid having many SEMs polling the
         EMM Server (EMMS) simultaneously.  The actual delay time will be
         randomly calculated by the SEM and will be no greater than this value.
         A value of zero means no delay and the SEM will poll immediately at
         startup.

         This parameter only applies when the SEM is in an internal
         semDeviceOperatingMode and semIceEncryptionMode is set to 'full'.

         Once written, the change to this parameter will only take immediate
         effect after semIceEmmConfigApplyChange is set to 'apply'.  In
         order for the change to persist through subsequent reboots or power
         cycles, the change must be saved via the semSaveConfig parameter.

         @Commit(param=semIceEmmConfigApplyChange, value=2)
         @Config(config=yes, reboot=no)
         @Save(semSaveConfig, value=2)
         @File(config.ini, type='ini')
        "
::= { semIceEmmConfig 4 }

semIceEmmPollTimeout OBJECT-TYPE
    SYNTAX Integer32(1..30)
    MAX-ACCESS read-write
    STATUS current
    DESCRIPTION
        "Internal Control of Encryption (ICE) Entitlement Management Message
         (EMM) Polling Timeout.  The time in seconds that the SEM will wait
         for a response from the EMM Server (EMMS).

         This parameter only applies when the SEM is in an internal
         semDeviceOperatingMode and semIceEncryptionMode is set to 'full'.

         Once written, the change to this parameter will only take immediate
         effect after semIceEmmConfigApplyChange is set to 'apply'.  In
         order for the change to persist through subsequent reboots or power
         cycles, the change must be saved via the semSaveConfig parameter.

         @Commit(param=semIceEmmConfigApplyChange, value=2)
         @Config(config=yes, reboot=no)
         @Save(semSaveConfig, value=2)
         @File(config.ini, type='ini')
        "
::= { semIceEmmConfig 5 }

semIceEmmPollRetryCount OBJECT-TYPE
    SYNTAX Integer32(1..30)
    MAX-ACCESS read-write
    STATUS current
    DESCRIPTION
        "Internal Control of Encryption (ICE) Entitlement Management Message (EMM)
         Polling Retry Count.  The number of times the SEM will attempt to
         communicate with the EMM Server (EMMS). A semAlarmIceEmmServerCommFailure
         or semAlarmIceEmmServerInvalidResponse will be issued after last retry.

         This parameter only applies when the SEM is in an internal
         semDeviceOperatingMode and semIceEncryptionMode is set to 'full'.

         Once written, the change to this parameter will only take immediate
         effect after semIceEmmConfigApplyChange is set to 'apply'.  In
         order for the change to persist through subsequent reboots or power
         cycles, the change must be saved via the semSaveConfig parameter.

         @Commit(param=semIceEmmConfigApplyChange, value=2)
         @Config(config=yes, reboot=no)
         @Save(semSaveConfig, value=2)
         @File(config.ini, type='ini')
        "
::= { semIceEmmConfig 6 }

semIceEmmRefresh OBJECT-TYPE
    SYNTAX INTEGER
        {
         refreshNotInProgress (1),
         refresh              (2)
        }
    MAX-ACCESS read-write
    STATUS current
    DESCRIPTION
        "Internal Control of Encryption (ICE) Entitlement Management Message
         (EMM) Refresh.  Setting to 'refresh' forces the SEM to retrieve new
         EMMs (forces the SEM to perform an EMM rollover sequence).

         This parameter only applies when the SEM is in an internal
         semDeviceOperatingMode and semIceEncryptionMode is set to 'full'.

         Once written, the change to this parameter will only take immediate
         effect after semIceEmmConfigApplyChange is set to 'apply'.

         @Commit(param=semIceEmmConfigApplyChange, value=2)
         @Config(config=no, reboot=no)
        "
::= { semIceEmmConfig 7 }

semIceEmmFullEncryptExpirationTime OBJECT-TYPE
    SYNTAX Integer32(1..30)
    MAX-ACCESS read-write
    STATUS current
    DESCRIPTION
        "Internal Control of Encryption (ICE) Full Encryption Time.  Duration
         is in days.  This is the amount of days that the SEM will keep all
         programs in full encryption mode after communication with the EMMS
         fails.  The SEM will switch to FPK encryption mode at the end of
         this time period.  The duration start time is based on the time when
         the SEM was last able to successfully communicate with the EMMS.

         This parameter applies to all programs on the SEM.

         This parameter only applies when the SEM is in an internal
         semDeviceOperatingMode and semIceEncryptionMode is set to 'full'.

         Once written, the change to this parameter will only take immediate
         effect after semIceEmmConfigApplyChange is set to 'apply'.  In
         order for the change to persist through subsequent reboots or power
         cycles, the change must be saved via the semSaveConfig parameter.

         @Commit(param=semIceEmmConfigApplyChange, value=2)
         @Config(config=yes, reboot=no)
         @Save(semSaveConfig, value=2)
         @File(config.ini, type='ini')
        "
::= { semIceEmmConfig 8 }

semIceEmmServerIpAddr OBJECT-TYPE
    SYNTAX IpAddress
    MAX-ACCESS read-write
    STATUS current
    DESCRIPTION
        "Internal Control of Encryption (ICE) Entitlement Management Message
         Server (EMMS) IP Address.  Class A, B, or C IP address of the EMMS.
         Changing this parameter will cause the SEM to perform an EMM rollover
         sequence.

         This parameter is not changed by semIceEmmSetDefault.

         This parameter only applies when the SEM is in an internal
         semDeviceOperatingMode and semIceEncryptionMode is set to 'full'.

         Once written, the change to this parameter will only take immediate
         effect after semIceEmmConfigApplyChange is set to 'apply'.  In
         order for the change to persist through subsequent reboots or power
         cycles, the change must be saved via the semSaveConfig parameter.

         @Commit(param=semIceEmmConfigApplyChange, value=2)
         @Config(config=yes, reboot=no)
         @Save(semSaveConfig, value=2)
         @File(config.ini, type='ini')
        "
::= { semIceEmmConfig 9 }

semIceEmmServerTcpPort OBJECT-TYPE
    SYNTAX Integer32
    MAX-ACCESS read-write
    STATUS current
    DESCRIPTION
        "Internal Control of Encryption (ICE) Entitlement Management Message
         Server (EMMS) TCP Port 0 to 65535.  TCP Port of the EMM server.
         Changing this parameter will cause the SEM to perform an EMM rollover
         sequence.

         The user would be advised to keep the port numbers above 5000 to
         avoid the well known port range.  From 'TCP/IP Illustrated,
         Volume 1: The Protocols' by W. Richard Stevens:
           'Those services that can be provided by any implementation
            of TCP/IP have well- known port numbers between 1 and 1023.
            The well-known ports are managed by the Internet Assigned
            Numbers Authority (IANA).  Most TCP/IP implementations
            allocate ephemeral port numbers between 1024 and 5000.  The
            port numbers above 5000 are intended for other services
            (those that aren't well known across the Internet).'

         This parameter only applies when the SEM is in an internal
         semDeviceOperatingMode and semIceEncryptionMode is set to 'full'.

         Once written, the change to this parameter will only take immediate
         effect after semIceEmmConfigApplyChange is set to 'apply'.  In
         order for the change to persist through subsequent reboots or power
         cycles, the change must be saved via the semSaveConfig parameter.

         @Range(min=0, max=65535)
         @Commit(param=semIceEmmConfigApplyChange, value=2)
         @Config(config=yes, reboot=no)
         @Save(semSaveConfig, value=2)
         @File(config.ini, type='ini')
        "
::= { semIceEmmConfig 10 }

semIceEmmServerErrorCountReset OBJECT-TYPE
    SYNTAX ResetStatisticsTYPE
    MAX-ACCESS read-write
    STATUS current
    DESCRIPTION
        "Internal Control of Encryption (ICE) Entitlement Management Message
         Server (EMMS) Error Count reset.  Setting to 'reset' resets
         semIceEmmServerCommErrorCount and semIceEmmServerInvalidResponseCount.
         The SEM will set this back to 'resetNotInProgress' after resetting
         the data.

         This parameter only applies when the SEM is in an internal
         semDeviceOperatingMode and semIceEncryptionMode is set to 'full'.

         Once written, the change to this parameter will only take immediate
         effect after semIceEmmConfigApplyChange is set to 'apply'.

         @Commit(param=semIceEmmConfigApplyChange, value=2)
         @Config(config=no, reboot=no)
        "
::= { semIceEmmConfig 11 }

semIceEmmFullEncryptFailureCountReset OBJECT-TYPE
    SYNTAX ResetStatisticsTYPE
    MAX-ACCESS read-write
    STATUS current
    DESCRIPTION
        "Internal Control of Encryption (ICE) Full Encryption Failure Count Reset.
         Setting to 'reset' resets the semIceFullEncryptFailureCount.  The SEM
         will set this back to 'resetNotInProgress' after resetting the data.

         This parameter only applies when the SEM is in an internal
         semDeviceOperatingMode and semIceEncryptionMode is set to 'full'.

         Once written, the change to this parameter will only take immediate
         effect after semIceEmmConfigApplyChange is set to 'apply'.

         @Commit(param=semIceEmmConfigApplyChange, value=2)
         @Config(config=no, reboot=no)
        "
::= { semIceEmmConfig 12 }

semIceEmmServerCommAlarmClear OBJECT-TYPE
    SYNTAX ClearAlarmTYPE
    MAX-ACCESS read-write
    STATUS current
    DESCRIPTION
        "Internal Control of Encryption (ICE) Entitlement Management Message
         Server (EMMS) Communication Failure Alarm Clear.  Setting to 'clearAlarm'
         clears semAlarmIceEmmServerCommFailure.
         The SEM will set this back to 'clearAlarmNotInProgress'
         after clearing the alarm.

         This parameter only applies when the SEM is in an internal
         semDeviceOperatingMode and semIceEncryptionMode is set to 'full'.

         Once written, the change to this parameter will only take immediate
         effect after semIceEmmConfigApplyChange is set to 'apply'.

         @Commit(param=semIceEmmConfigApplyChange, value=2)
         @Config(config=no, reboot=no)
        "
::= { semIceEmmConfig 13 }

semIceEmmServerInvalRespAlarmClear OBJECT-TYPE
    SYNTAX ClearAlarmTYPE
    MAX-ACCESS read-write
    STATUS current
    DESCRIPTION
        "Internal Control of Encryption (ICE) Entitlement Management Message
         Server (EMMS) Invalid Response Alarm Clear.  Setting to 'clearAlarm'
         clears semAlarmIceEmmServerInvalidResponse.
         The SEM will set this back to 'clearAlarmNotInProgress'
         after clearing the alarm.

         This parameter only applies when the SEM is in an internal
         semDeviceOperatingMode and semIceEncryptionMode is set to 'full'.

         Once written, the change to this parameter will only take immediate
         effect after semIceEmmConfigApplyChange is set to 'apply'.

         @Commit(param=semIceEmmConfigApplyChange, value=2)
         @Config(config=no, reboot=no)
        "
::= { semIceEmmConfig 14 }


-- ------------------------------------------------------------------------------
--
-- semIceStatus
--
-- semIceStatusGeneral
--
-- semIceProgramStatus
--

semIceCurrentEncryptionMode OBJECT-TYPE
    SYNTAX INTEGER
        {
         clear (1),
         fpk   (2),
         full  (3)
        }
    MAX-ACCESS read-only
    STATUS current
    DESCRIPTION
        "Internal Control of Encryption (ICE) Current Mode of Encryption.  This
         parameter reflects the current encryption mode of the SEM.  The current
         encryption mode is based on the semIceEncryptionMode setting and the
         status of all the ACPs.  This parameter reflects the highest encryption
         mode that the SEM is capable of being in.

           - 'clear' - The SEM is considered to be in clear mode when
                       semIceEncryptionMode is set to 'clear'.

           - 'fpk'   - The SEM is considered to be in Fixed Program Key
                       (FPK) mode when semIceEncryptionMode is set to 'fpk',
                       or when semIceEncryptionMode is set to 'full' and the
                       status of one or more ACPs indicates that full
                       encryption is not available.

           - 'full'  - The SEM is considered to be in Full encryption mode
                       when semIceEncryptionMode is set to 'full' and the
                       status of all ACPs indicate that full encryption is
                       available.

         This parameter only applies when the SEM is in an internal semDeviceOperatingMode
         and semIceCommonTierEncryptionEnable is set to 'enabled'."
::= { semIceProgramStatus 1 }

semIceCurrentEpochNumber OBJECT-TYPE
    SYNTAX Integer32(0..255)
    MAX-ACCESS read-only
    STATUS current
    DESCRIPTION
        "Internal Control of Encryption (ICE) Current Epoch Number.  This
         is the current epoch number used by the SEM when generating and
         inserting PRK and PIT messages.

         This parameter applies to all programs on the SEM.

         This parameter only applies when the SEM is in an internal
         semDeviceOperatingMode and semIceEncryptionMode is set to 'fpk'
         or 'full'."
::= { semIceProgramStatus 2 }

semIceEpochExpirationTime OBJECT-TYPE
    SYNTAX Integer32
    MAX-ACCESS read-only
    STATUS current
    DESCRIPTION
        "Internal Control of Encryption (ICE) Epoch Expiration Time. Time in
         seconds until the current program epoch will expire.

         This parameter applies to all programs on the SEM.

         This parameter only applies when the SEM is in an internal
         semDeviceOperatingMode and semIceEncryptionMode is set to 'fpk'
         or 'full'."
::= { semIceProgramStatus 3 }

semIceEncryptionModeTableSize OBJECT-TYPE
    SYNTAX Integer32
    MAX-ACCESS read-only
    STATUS current
    DESCRIPTION
        "Internal Control of Encryption (ICE) Encryption Mode Table Size.
         This is the maximum number of rows in the Encryption Mode Table
         and is the limit on semIceStatusEncryptionModeIndex.

         This parameter only applies when the SEM is in an internal
         semDeviceOperatingMode and semIceEncryptionMode is set to 'fpk'
         or 'full'."
::= { semIceProgramStatus 4 }


-- ------------------------------------------------------------------------------
--
-- semIceStatusEncryptionModeTable
--

semIceStatusEncryptionModeTable OBJECT-TYPE
    SYNTAX SEQUENCE OF SemIceStatusEncryptionModeEntry
    MAX-ACCESS not-accessible
    STATUS current
    DESCRIPTION
        "Internal Control of Encryption (ICE) Encryption Mode Table.
         This table contains the most recent ICE Encryption Mode
         changes.  It is a fixed size table.

         This table only applies when the SEM is in an internal
         semDeviceOperatingMode."
::= { semIceStatus 3 }

semIceStatusEncryptionModeEntry OBJECT-TYPE
    SYNTAX SemIceStatusEncryptionModeEntry
    MAX-ACCESS not-accessible
    STATUS current
    DESCRIPTION
        "Internal Control of Encryption (ICE) Encryption Mode Table Entry."
    INDEX { semIceStatusEncryptionModeIndex }
::= { semIceStatusEncryptionModeTable 1 }

SemIceStatusEncryptionModeEntry ::= SEQUENCE
    {
     semIceStatusEncryptionModeIndex  Integer32,
     semIceStatusEncryptionMode       INTEGER,
     semIceStatusEncryptionModeTime   Integer32,
     semIceStatusEncryptionModeReason INTEGER
    }

semIceStatusEncryptionModeIndex OBJECT-TYPE
    SYNTAX Integer32
    MAX-ACCESS not-accessible
    STATUS current
    DESCRIPTION
        "Index of Internal Control of Encryption (ICE) Encryption Mode Table.
         Size of table can be found in semIceStatusEncryptionModeTableSize."
::= { semIceStatusEncryptionModeEntry 1 }

semIceStatusEncryptionMode OBJECT-TYPE
    SYNTAX INTEGER
        {
         clear (1),
         fpk   (2),
         full  (3)
        }
    MAX-ACCESS read-only
    STATUS current
    DESCRIPTION
        "Internal Control of Encryption (ICE) Mode of Encryption.

         This parameter only applies when the SEM is in an internal
         semDeviceOperatingMode."
::= { semIceStatusEncryptionModeEntry 2 }

semIceStatusEncryptionModeTime OBJECT-TYPE
    SYNTAX Integer32
    MAX-ACCESS read-only
    STATUS current
    DESCRIPTION
        "Internal Control of Encryption (ICE) Mode Time.  This is the time
         in GPS seconds that the transition to semIceStatusEncryptionMode
         took place.

         This parameter only applies when the SEM is in an internal
         semDeviceOperatingMode."
::= { semIceStatusEncryptionModeEntry 3 }

semIceStatusEncryptionModeReason OBJECT-TYPE
    SYNTAX INTEGER
        {
         configuration (1),
         noEmm         (2),
         receivedEmm   (3),
         lostEmm       (4)
        }
    MAX-ACCESS read-only
    STATUS current
    DESCRIPTION
        "Internal Control of Encryption (ICE) Mode Reason.  This is the reason
         transition to semIceStatusEncryptionMode took place.
           - 'configuration' - The user configured this state.
           - 'noEmm'         - The SEM did not receive EMMs at startup and entered
                               this state.
           - 'receivedEmm'   - The SEM received EMMs that allowed transition to
                               this state.
           - 'lostEmm'       - The SEM lost EMM communication that caused transition
                               to this state.

         This parameter only applies when the SEM is in an internal
         semDeviceOperatingMode."
::= { semIceStatusEncryptionModeEntry 4 }


-- ------------------------------------------------------------------------------
--
-- semIceEmmStatus
--
-- semIceEmmStatusGeneral
--

semIceEmmCurrentCsn OBJECT-TYPE
    SYNTAX Integer32(0..255)
    MAX-ACCESS read-only
    STATUS current
    DESCRIPTION
        "Internal Control of Encryption (ICE) Entitlement Management Message (EMM)
         Current EMM Category Sequence Number (CSN). This is the current CSN that
         the SEM is using for encrypting all programs.

         This parameter applies to all programs on the SEM.

         This parameter only applies when the SEM is in an internal
         semDeviceOperatingMode and semIceEncryptionMode is set to 'full'."
::= { semIceEmmStatusGeneral 1 }

semIceEmmNextPollTime OBJECT-TYPE
    SYNTAX Integer32
    MAX-ACCESS read-only
    STATUS current
    DESCRIPTION
        "Internal Control of Encryption (ICE) Entitlement Management Message (EMM)
         Next Poll Time. Time in seconds until the next EMM polling period.

         This parameter only applies when the SEM is in an internal
         semDeviceOperatingMode and semIceEncryptionMode is set to 'full'."
::= { semIceEmmStatusGeneral 2 }

semIceEmmFullEncryptStopTime OBJECT-TYPE
    SYNTAX Integer32
    MAX-ACCESS read-only
    STATUS current
    DESCRIPTION
        "Internal Control of Encryption (ICE) Entitlement Management Message (EMM)
         Full Encryption Stop Time.  When there is an EMM communication failure
         or invalid response, this is the time in seconds until all programs will
         revert from Full encryption to FPK mode. If this number is negative, then
         this represents the amount of time since the SEM reverted from Full to FPK
         encryption mode.

         This parameter applies to all programs on the SEM.

         This parameter only applies when the SEM is in an internal
         semDeviceOperatingMode and semIceEncryptionMode is set to 'full'."
::= { semIceEmmStatusGeneral 3 }

semIceEmmLastRolloverTime OBJECT-TYPE
    SYNTAX Integer32
    MAX-ACCESS read-only
    STATUS current
    DESCRIPTION
        "Internal Control of Encryption (ICE) Entitlement Management Message (EMM)
         Last Rollover Time.  Time in GPS seconds at the start of the last successful
         EMM rollover sequence.

         This parameter only applies when the SEM is in an internal
         semDeviceOperatingMode and semIceEncryptionMode is set to 'full'."
::= { semIceEmmStatusGeneral 4 }

semIceEmmServerCommErrorCount OBJECT-TYPE
    SYNTAX Counter32
    MAX-ACCESS read-only
    STATUS current
    DESCRIPTION
        "Internal Control of Encryption (ICE) Entitlement Management Message Server
         (EMMS) Communication Error Count.  Count of errors that result in a
         semAlarmIceEmmServerCommFailure.

         This parameter can be reset using semIceEmmServerErrorCountReset.

         This parameter only applies when the SEM is in an internal
         semDeviceOperatingMode and semIceEncryptionMode is set to 'full'."
::= { semIceEmmStatusGeneral 5 }

semIceEmmServerInvalidResponseCount OBJECT-TYPE
    SYNTAX Counter32
    MAX-ACCESS read-only
    STATUS current
    DESCRIPTION
        "Internal Control of Encryption (ICE) Entitlement Management Message Server
         (EMMS) Invalid Response Error Count.  Count of errors that result in a
         semAlarmIceEmmServerInvalidResponse.

         This parameter can be reset using semIceEmmServerErrorCountReset.

         This parameter only applies when the SEM is in an internal
         semDeviceOperatingMode and semIceEncryptionMode is set to 'full'."
::= { semIceEmmStatusGeneral 6 }

semIceEmmFullEncryptFailureCount OBJECT-TYPE
    SYNTAX Counter32
    MAX-ACCESS read-only
    STATUS current
    DESCRIPTION
        "Internal Control of Encryption (ICE) Encryption Failure Count.
         Count of times the SEM reverted to FPK mode causing a
         semAlarmIceFullEncryptFailure.

         This parameter can be reset using semIceFullEncryptFailureCountReset.

         This parameter applies to all programs on the SEM.

         This parameter only applies when the SEM is in an internal
         semDeviceOperatingMode and semIceEncryptionMode is set to 'full'."
::= { semIceEmmStatusGeneral 7 }

semIceEmmStatusTableSize OBJECT-TYPE
    SYNTAX Integer32
    MAX-ACCESS read-only
    STATUS current
    DESCRIPTION
        "Internal Control of Encryption (ICE) Entitlement Management Message (EMM)
         Status Table Size.  This is the maximum number of rows in the EMM Status
         Table and is the limit on semIceEmmStatusTblIndex.

         This parameter only applies when the SEM is in an internal
         semDeviceOperatingMode and semIceEncryptionMode is set to 'full'."
::= { semIceEmmStatusGeneral 8 }


-- ------------------------------------------------------------------------------
--
-- semIceEmmStatusTable
--

semIceEmmStatusTable OBJECT-TYPE
    SYNTAX SEQUENCE OF SemIceEmmStatusEntry
    MAX-ACCESS not-accessible
    STATUS current
    DESCRIPTION
        "Internal Control of Encryption (ICE) Entitlement Management Message (EMM)
         Status Table.  This table contains the most recent ICE EMM Server
         (EMMS) Responses.  It is a fixed size table.

         This table only applies when the SEM is in an internal
         semDeviceOperatingMode and semIceEncryptionMode is set to 'full'."
::= { semIceEmmStatus 2 }

semIceEmmStatusEntry OBJECT-TYPE
    SYNTAX SemIceEmmStatusEntry
    MAX-ACCESS not-accessible
    STATUS current
    DESCRIPTION
        "Internal Control of Encryption (ICE) Entitlement Management Message (EMM)
         Status Table Entry."
    INDEX { semIceEmmStatusTblIndex }
::= { semIceEmmStatusTable 1 }

SemIceEmmStatusEntry ::= SEQUENCE
    {
     semIceEmmStatusTblIndex          Integer32,
     semIceEmmStatusTblCsn            Integer32,
     semIceEmmStatusTblState          INTEGER,
     semIceEmmStatusTblTime           Integer32,
     semIceEmmStatusTblServerError    Unsigned32,
     semIceEmmStatusTblAcpUnitAddress DisplayString
    }

semIceEmmStatusTblIndex OBJECT-TYPE
    SYNTAX Integer32
    MAX-ACCESS not-accessible
    STATUS current
    DESCRIPTION
        "Index of Internal Control of Encryption (ICE) Entitlement Management
         Message (EMM) Status Table.
         Size of table can be found in semIceEmmStatusTableSize."
::= { semIceEmmStatusEntry 1 }

semIceEmmStatusTblCsn OBJECT-TYPE
    SYNTAX Integer32(0..255)
    MAX-ACCESS read-only
    STATUS current
    DESCRIPTION
        "Internal Control of Encryption (ICE) Category Sequence Number (CSN).

         This parameter only applies when the SEM is in an internal
         semDeviceOperatingMode and semIceEncryptionMode is set to 'full'."
::= { semIceEmmStatusEntry 2 }

semIceEmmStatusTblState OBJECT-TYPE
    SYNTAX INTEGER
        {
         transitionComplete (1),
         transitionStart    (2),
         startOfNewEpoch    (3)
        }
    MAX-ACCESS read-only
    STATUS current
    DESCRIPTION
        "Internal Control of Encryption (ICE) Category Epoch Transition (CET) State.

         This parameter only applies when the SEM is in an internal
         semDeviceOperatingMode and semIceEncryptionMode is set to 'full'."
::= { semIceEmmStatusEntry 3 }

semIceEmmStatusTblTime OBJECT-TYPE
    SYNTAX Integer32
    MAX-ACCESS read-only
    STATUS current
    DESCRIPTION
        "Internal Control of Encryption (ICE) EMM Status Time.  This is the time
         in GPS seconds that this row was written.

         This parameter only applies when the SEM is in an internal
         semDeviceOperatingMode and semIceEncryptionMode is set to 'full'."
::= { semIceEmmStatusEntry 4 }

semIceEmmStatusTblServerError OBJECT-TYPE
    SYNTAX Unsigned32
    MAX-ACCESS read-only
    STATUS current
    DESCRIPTION
        "Internal Control of Encryption (ICE) Entitlement Management Message
         (EMM) Server Error.  This is the error code reported to the SEM by
         the EMM Server.  Zero indicates no error.

         This parameter only applies when the SEM is in an internal
         semDeviceOperatingMode and semIceEncryptionMode is set to 'full'."
::= { semIceEmmStatusEntry 5 }

semIceEmmStatusTblAcpUnitAddress OBJECT-TYPE
    SYNTAX DisplayString (SIZE (20))
    MAX-ACCESS read-only
    STATUS current
    DESCRIPTION
        "Internal Control of Encryption (ICE) Entitlement Management Message
         (EMM) ACP Unit Address.  This is the ACP address of the ACP associated
         with the error reported in semIceEmmStatusTblServerError.
         If no address is contained in this entry, the error reported in
         semIceEmmStatusTblServerError applies to all ACPs or to the entire
         SEM.

         Format is decimal digits grouped in 3-5-5-3 human readable format.
         A typical address would look like: '123-45678-87654-321'.

         This parameter only applies when the SEM is in an internal
         semDeviceOperatingMode and semIceEncryptionMode is set to 'full'."
::= { semIceEmmStatusEntry 6 }


-- ------------------------------------------------------------------------------
--
-- semIsaSdv
--
-- semIsaSdvConfig
--
-- semIsaSdvConfigGeneral
--

semIsaSdvGbePort OBJECT-TYPE
    SYNTAX Integer32 (1..3)
    MAX-ACCESS read-write
    STATUS current
    DESCRIPTION
        "Indicates which Gigabit Ethernet Interface port to use for
         ISA SDV mappings.  This port is NOT used for statically mapped
         Broadcast and VOD services. Only Switched Digital Video (SDV)
         services will use the configured GigE port. This parameter is only
         applicable when the SEM is in semDeviceOperatingMode 'isaSdv'.

         Once written, the change to this parameter will take immediate
         effect and any bindings (mappings) that are already started will
         not be affected by a SDV GigE port change. Only new bindings/mappings
         will use the new setting.  In order for the change to persist through
         subsequent reboots or power cycles, the change must be saved via
         the semSaveConfig parameter.

         @Config(config=yes, reboot=no)
         @Save(semSaveConfig, value=2)
         @File(config.ini, type='ini')
        "
::= { semIsaSdvConfigGeneral 1 }

semIsaSdvDataCarouselProgram OBJECT-TYPE
    SYNTAX Integer32
    MAX-ACCESS read-write
    STATUS current
    DESCRIPTION
        "Indicates which Input Program Number to use for the Data
         Carousel.  The data carousel in ISA SDV mode is on a fixed
         PMT PID along with a fixed component PID. In order to maintain
         these PID values, the SEM will check for a specific input service
         number defined by this parameter. This service mapping is assumed
         to be the Data Carousel mapping. The SEM will maintain the PMT PID
         value along with the component PID value.  To facilitate this mapping,
         the Data Carousel input/output program number is configurable.
           - Data Carousel Service Number Default: 0xF38F (62351)

         The PMT PID and component PID will be determined by the SEM by
         analyzing the PAT and PMT based on the program number configured. A
         program number of zero (0) indicates that there is no data carousel.

         This parameter is only applicable when the SEM is in
         semDeviceOperatingMode 'isaSdv'.

         Once written, the change to this parameter will take immediate
         effect.  In order for the change to persist through subsequent
         reboots or power cycles, the change must be saved via the
         semSaveConfig parameter.

         @Config(config=yes, reboot=no)
         @Save(semSaveConfig, value=2)
         @File(config.ini, type='ini')
        "
::= { semIsaSdvConfigGeneral 2 }


-- ------------------------------------------------------------------------------
--
-- semIsaSdvStatus
--
-- semIsaSdvStatusGeneral
--

-- No entries in this group at this time.


-- ------------------------------------------------------------------------------
--
-- semIsaSdvSessionStatTable
--

semIsaSdvSessionStatTable OBJECT-TYPE
    SYNTAX SEQUENCE OF SemIsaSdvSessionStatEntry
    MAX-ACCESS not-accessible
    STATUS current
    DESCRIPTION
        "Table of ISA Switched Digital Video Session status.  This table
         contains 384 rows.

         The index into this table matches the index into semManRemuxMapTable.
         These tables in ISA SDV mode are all kept in sync (row per row).

         This table only applies when the SEM is in semDeviceOperatingMode
         'isaSdv'.
        "
::= { semIsaSdvStatus 2 }

semIsaSdvSessionStatEntry OBJECT-TYPE
    SYNTAX SemIsaSdvSessionStatEntry
    MAX-ACCESS not-accessible
    STATUS current
    DESCRIPTION
        "ISA Switched Digital Video Session Status Table Entry."
    INDEX { semIsaSdvSessionStatIndex }
::= { semIsaSdvSessionStatTable 1 }

SemIsaSdvSessionStatEntry ::= SEQUENCE
    {
     semIsaSdvSessionStatIndex               Integer32,
     semIsaSdvSessionStatInputGbePort        Integer32,
     semIsaSdvSessionStatInputUdpPort        Integer32,
     semIsaSdvSessionStatInputProgramNum     Integer32,
     semIsaSdvSessionStatMulticastIpAddr     IpAddress,
     semIsaSdvSessionStatSourceIpAddr1       IpAddress,
     semIsaSdvSessionStatSourceIpAddr2       IpAddress,
     semIsaSdvSessionStatSourceIpAddr3       IpAddress,
     semIsaSdvSessionStatOutputQamPort       Integer32,
     semIsaSdvSessionStatOutputProgramNum    Integer32,
     semIsaSdvSessionStatProgramBandwidth    Integer32,
     semIsaSdvSessionStatSessionType         INTEGER,
     semIsaSdvSessionStatSessionIdWord1      Unsigned32,
     semIsaSdvSessionStatSessionIdWord2      Unsigned32,
     semIsaSdvSessionStatSessionIdWord3      Unsigned32,
     semIsaSdvSessionStatManagerIpAddr       IpAddress
    }

semIsaSdvSessionStatIndex OBJECT-TYPE
    SYNTAX Integer32 (1..384)
    MAX-ACCESS not-accessible
    STATUS current
    DESCRIPTION
        "The ISA Switched Digital Video Session Status table index.
        "
::= { semIsaSdvSessionStatEntry 1 }

semIsaSdvSessionStatInputGbePort OBJECT-TYPE
    SYNTAX Integer32(0..3)
    MAX-ACCESS read-only
    STATUS current
    DESCRIPTION
        "The Gigabit Ethernet physical port on which packets are being received
         on semIsaSdvSessionStatInputUdpPort.
         Zero indicates this row of the table is not in use.
        "
::= { semIsaSdvSessionStatEntry 2 }

semIsaSdvSessionStatInputUdpPort OBJECT-TYPE
    SYNTAX Integer32
    MAX-ACCESS read-only
    STATUS current
    DESCRIPTION
        "The Gigabit Ethernet Input UDP Port (range is 0 to 65535).
        "
::= { semIsaSdvSessionStatEntry 3 }

semIsaSdvSessionStatInputProgramNum OBJECT-TYPE
    SYNTAX Integer32
    MAX-ACCESS read-only
    STATUS current
    DESCRIPTION
        "The Gigabit Ethernet Input Program Number. A value of
         zero (0) indicates that the input is an SPTS and the first
         program listed in the input PAT will be mapped by the SEM.
        "
::= { semIsaSdvSessionStatEntry 4 }

semIsaSdvSessionStatMulticastIpAddr OBJECT-TYPE
    SYNTAX IpAddress
    MAX-ACCESS read-only
    STATUS current
    DESCRIPTION
        "The Gigabit Ethernet Receive Multicast IP Address.
        "
::= { semIsaSdvSessionStatEntry 5 }

semIsaSdvSessionStatSourceIpAddr1 OBJECT-TYPE
    SYNTAX IpAddress
    MAX-ACCESS read-only
    STATUS current
    DESCRIPTION
        "The Gigabit Ethernet IGMP v3 Source IP Address 1. This is
         the primary source IP when IGMP v3 is supported. The SEM
         currently only supports 1 source IP address per mapping.
        "
::= { semIsaSdvSessionStatEntry 6 }

semIsaSdvSessionStatSourceIpAddr2 OBJECT-TYPE
    SYNTAX IpAddress
    MAX-ACCESS read-only
    STATUS current
    DESCRIPTION
        "The Gigabit Ethernet IGMP v3 Source IP Address 2. This
         IP address is currently unsupported by the SEM.
        "
::= { semIsaSdvSessionStatEntry 7 }

semIsaSdvSessionStatSourceIpAddr3 OBJECT-TYPE
    SYNTAX IpAddress
    MAX-ACCESS read-only
    STATUS current
    DESCRIPTION
        "The Gigabit Ethernet IGMP v3 Source IP Address 3.  This
         IP address is currently unsupported by the SEM.
        "
::= { semIsaSdvSessionStatEntry 8 }

semIsaSdvSessionStatOutputQamPort OBJECT-TYPE
    SYNTAX Integer32
    MAX-ACCESS read-only
    STATUS current
    DESCRIPTION
        "The Output QAM Port (1-8 v8, 1-12 v12).
        "
::= { semIsaSdvSessionStatEntry 9 }

semIsaSdvSessionStatOutputProgramNum OBJECT-TYPE
    SYNTAX Integer32
    MAX-ACCESS read-only
    STATUS current
    DESCRIPTION
        "The Output Program Number (1 - 65535).
        "
::= { semIsaSdvSessionStatEntry 10 }

semIsaSdvSessionStatProgramBandwidth OBJECT-TYPE
    SYNTAX Integer32
    MAX-ACCESS read-only
    STATUS current
    DESCRIPTION
        "The Expected Program Bandwidth (bps). This is the bandwidth
         of the program as defined in the service mapping. A value of
         0 indicates that the program BW is unknown.
        "
::= { semIsaSdvSessionStatEntry 11 }

semIsaSdvSessionStatSessionType OBJECT-TYPE
    SYNTAX INTEGER
        {
         noSession      (0),
         sdv            (1),
         vodOrBroadcast (2)
        }
    MAX-ACCESS read-only
    STATUS current
    DESCRIPTION
        "The Type of session (SDV binding or VOD/Broadcast session).
         1 = Switched Digital Video (SDV)
         2 = VOD or Broadcast
        "
::= { semIsaSdvSessionStatEntry 12 }

semIsaSdvSessionStatSessionIdWord1 OBJECT-TYPE
    SYNTAX Unsigned32
    MAX-ACCESS read-only
    STATUS current
    DESCRIPTION
        "The Session ID Word 1.

         Session IDs are 10 byte character arrays.  Session IDs are
         be stored as 3 4-byte words (3 ulongs) in this MIB. First
         2 Bytes are always 0, next 10 contain the session ID.

         Session ID is broken up as follows:
            Word 1: 00:01 = 0x0000 (unused)
            Word 1: 02:03 = 1st 2 bytes of session ID (1st 2 bytes of MAC address)
            Word 2: 00:03 = Next 4 bytes (these 4 plus 1st 2 are the MAC address of manager)
            Word 3: 00:03 = Last 4 bytes (unique number assigned by manager)
        "
::= { semIsaSdvSessionStatEntry 13 }

semIsaSdvSessionStatSessionIdWord2 OBJECT-TYPE
    SYNTAX Unsigned32
    MAX-ACCESS read-only
    STATUS current
    DESCRIPTION
        "The Session ID Word 2.

         Session IDs are 10 byte character arrays.  Session IDs are
         be stored as 3 4-byte words (3 Unsigned32) in this MIB. First
         2 Bytes are always 0, next 10 contain the session ID.

         Session ID is broken up as follows:
            Word 1: 00:01 = 0x0000 (unused)
            Word 1: 02:03 = 1st bytes of session ID (1st 2 bytes of MAC address)
            Word 2: 00:03 = Next 4 bytes (these 4 plus 1st 2 are the MAC address of manager)
            Word 3: 00:03 = Last 4 bytes (unique number assigned by manager)
        "
::= { semIsaSdvSessionStatEntry 14 }

semIsaSdvSessionStatSessionIdWord3 OBJECT-TYPE
    SYNTAX Unsigned32
    MAX-ACCESS read-only
    STATUS current
    DESCRIPTION
        "The Session ID Word 3.

         Session IDs are 10 byte character arrays.  Session IDs are
         be stored as 3 4-byte words (3 Unsigned32) in this MIB. First
         2 Bytes are always 0, next 10 contain the session ID.

         Session ID is broken up as follows:
            Word 1: 00:01 = 0x0000 (unused)
            Word 1: 02:03 = 1st bytes of session ID (1st 2 bytes of MAC address)
            Word 2: 00:03 = Next 4 bytes (these 4 plus 1st 2 are the MAC address of manager)
            Word 3: 00:03 = Last 4 bytes (unique number assigned by manager)
        "
::= { semIsaSdvSessionStatEntry 15 }

semIsaSdvSessionStatManagerIpAddr OBJECT-TYPE
    SYNTAX IpAddress
    MAX-ACCESS read-only
    STATUS current
    DESCRIPTION
        "The IP address of the SDV, VOD, or Broadcast manager sending session
         commands.
        "
::= { semIsaSdvSessionStatEntry 16 }


-- ------------------------------------------------------------------------------
--
-- semIsaSdvQamStatTable
--

semIsaSdvQamStatTable OBJECT-TYPE
    SYNTAX SEQUENCE OF SemIsaSdvQamStatEntry
    MAX-ACCESS not-accessible
    STATUS current
    DESCRIPTION
        "Table of ISA Switched Digital Video QAM status.  This table
         is indexed by QAM port number and contains 12 rows.

         This table only applies when the SEM is in semDeviceOperatingMode
         'isaSdv'.
        "
::= { semIsaSdvStatus 3 }

semIsaSdvQamStatEntry OBJECT-TYPE
    SYNTAX SemIsaSdvQamStatEntry
    MAX-ACCESS not-accessible
    STATUS current
    DESCRIPTION
        "ISA Switched Digital Video QAM Status Table Entry."
    INDEX { semIsaSdvQamStatQamPortNum }
::= { semIsaSdvQamStatTable 1 }

SemIsaSdvQamStatEntry ::= SEQUENCE
    {
     semIsaSdvQamStatQamPortNum          Integer32,
     semIsaSdvQamStatQamEnabled          EnableDisableTYPE,
     semIsaSdvQamStatOutTransStreamNum   Integer32,
     semIsaSdvQamStatNumSdvSessions      Integer32,
     semIsaSdvQamStatNumVodBcSessions    Integer32,
     semIsaSdvQamStatSdvGroupBandwidth   Unsigned32
    }

semIsaSdvQamStatQamPortNum OBJECT-TYPE
    SYNTAX Integer32 (1..12)
    MAX-ACCESS not-accessible
    STATUS current
    DESCRIPTION
        "The ISA Switched Digital Video QAM Status table index.
        "
::= { semIsaSdvQamStatEntry 1 }

semIsaSdvQamStatQamEnabled OBJECT-TYPE
    SYNTAX EnableDisableTYPE
    MAX-ACCESS read-only
    STATUS current
    DESCRIPTION
        "Indicates whether the QAM Port is enabled.
        "
::= { semIsaSdvQamStatEntry 2 }

semIsaSdvQamStatOutTransStreamNum OBJECT-TYPE
    SYNTAX Integer32
    MAX-ACCESS read-only
    STATUS current
    DESCRIPTION
        "The Output Transport Stream Number of the QAM Port (1-16).
        "
::= { semIsaSdvQamStatEntry 3 }

semIsaSdvQamStatNumSdvSessions OBJECT-TYPE
    SYNTAX Integer32
    MAX-ACCESS read-only
    STATUS current
    DESCRIPTION
        "The Number of reserved SDV sessions on this QAM Port. This is the
         number of SDV sessions that have been reserved by the manager. Each
         SDV session requires that a manager reserve a QAM. This is the count
         of SDV sessions reserved (not the actual number of active SDV sessions).
        "
::= { semIsaSdvQamStatEntry 4 }

semIsaSdvQamStatNumVodBcSessions OBJECT-TYPE
    SYNTAX Integer32
    MAX-ACCESS read-only
    STATUS current
    DESCRIPTION
        "The Number of VOD/Broadcast sessions on this QAM Port. This
         is the number of VOD/Broadcast sessions active on a QAM Port. Since
         VOD and Broadcast sessions are not required to be reserved for an
         output, this is the count of active VOD and Broadcast sessions on
         a specific QAM.
        "
::= { semIsaSdvQamStatEntry 5 }

semIsaSdvQamStatSdvGroupBandwidth OBJECT-TYPE
    SYNTAX Unsigned32
    MAX-ACCESS read-only
    STATUS current
    DESCRIPTION
        "The Group BW for SDV sessions (not used for VOD/Broadcast sessions).
         This is the total amount of BW allocated for all SDV sessions on a Port.
         The total SDV BW for a port is defined by the session manager. The manager
         reserves this BW for future SDV sessions. This is not the BW of current
         active SDV sessions, but the total BW reserved by the manager for SDV sessions.
        "
::= { semIsaSdvQamStatEntry 6 }


-- ------------------------------------------------------------------------------
--
-- semAlarms
--

semAlarmHardwareFault OBJECT-TYPE
    SYNTAX INTEGER
        {
         ok(1),
         indeterminate(2),
         warning(3),
         minor(4),
         major(5),
         critical(6)
        }
    MAX-ACCESS read-only
    STATUS current
    DESCRIPTION
        "Indicates that a Hardware related error occurred.  Examples include
         missing or uncommunicative HW, failures in initialization of HW, and
         failures to configure HW.  These can occur at startup or when the
         system is operational.  Types of HW Faults include:  Application File(s)
         Download failure; SPI Interface Initialization failure; PCI Interface
         Initialization failure; GigE Configuration failure; MUX Configuration
         failure; QAM Module Communication failure; Upconverter Module
         Communication failure; Unsupported/Incorrect HW/FW Version (QAM, UC,
         ACP); Encryption Entitlement Certificate(s) not found; Fatal Host
         Firmware Exception.

         'critical' indicates a fatal error occurred that prevents the SEM
          from performing operational requirements.

         'warning' indicates an error that does not prevent the SEM from
         performing operational requirements "
::= { semAlarms 8000 }

semAlarmInvalidInitData OBJECT-TYPE
    SYNTAX INTEGER
        {
         ok(1),
         indeterminate(2),
         warning(3),
         minor(4),
         major(5),
         critical(6)
        }
    MAX-ACCESS read-only
    STATUS current
    DESCRIPTION
        "Set when invalid Initialization data (ini files) is encountered.
         This alarm can be cleared by semConfAlarmClearInvalInitData."
::= { semAlarms 8001 }

semAlarmZeroSystemTime OBJECT-TYPE
    SYNTAX INTEGER
        {
         ok(1),
         indeterminate(2),
         warning(3),
         minor(4),
         major(5),
         critical(6)
        }
    MAX-ACCESS read-only
    STATUS current
    DESCRIPTION
        "'major' indicates that the SEM has not received a time
         update within approximately 70 seconds of last reboot.
         This alarm is initially set approximately 70 seconds after
         power up and is cleared upon receiving the first time update.
         Not Applicable when semTimeSource is 'internal'."
::= { semAlarms 8002 }

semAlarmMissingTimeUpdate OBJECT-TYPE
    SYNTAX INTEGER
        {
         ok(1),
         indeterminate(2),
         warning(3),
         minor(4),
         major(5),
         critical(6)
        }
    MAX-ACCESS read-only
    STATUS current
    DESCRIPTION
        "'warning' indicates SEM has not received a time update for
         more than 600 seconds (10 minutes).  This alarm is not applicable
         until the SEM has received its first time update.
         Not Applicable when semTimeSource is 'internal'."
::= { semAlarms 8003 }

semAlarmCommandTableEmpty OBJECT-TYPE
    SYNTAX INTEGER
        {
         ok(1),
         indeterminate(2),
         warning(3),
         minor(4),
         major(5),
         critical(6)
        }
    MAX-ACCESS read-only
    STATUS current
    DESCRIPTION
        "'warning' indicates Command Table is empty.
         Not applicable when SEM is internally controlled."
::= { semAlarms 8004 }

semAlarmCommandTableNearFull OBJECT-TYPE
    SYNTAX INTEGER
        {
         ok(1),
         indeterminate(2),
         warning(3),
         minor(4),
         major(5),
         critical(6)
        }
    MAX-ACCESS read-only
    STATUS current
    DESCRIPTION
        "'warning' indicates Command Table >= 90% full, and < 98% full.
         'minor' indicates Command Table >= 98% full.
         The checks for this are maximum number of commands and amount
         of available NVRAM storage.  SEM can handle 10000 Commands and
         23000 blocks at 64-bytes per block of NVRAM storage.
         Not applicable when SEM is internally controlled."
::= { semAlarms 8005 }

semAlarmServiceInError OBJECT-TYPE
    SYNTAX INTEGER
        {
         ok(1),
         indeterminate(2),
         warning(3),
         minor(4),
         major(5),
         critical(6)
        }
    MAX-ACCESS read-only
    STATUS current
    DESCRIPTION
        "'major' indicates that a command is currently in error (unable
         to fully continue processing). However, this is only for very
         specific errors where the error could be caused by either the
         input stream being invalid or another command along with the
         input stream is causing the error. For example, if mapping an
         input service to an output and that PMT is not referenced in
         the PAT, or the number of PIDs in the PMT is greater than the
         number of PIDs supported, then the command is in error. This
         error condition would be cleared if a new PAT is received
         referencing the PMT or in the other case, if a new PMT is
         received referencing a valid number of PIDs.
         Not applicable when SEM is internally controlled."
::= { semAlarms 8006 }

semAlarmWaitingForExtractedMessage OBJECT-TYPE
    SYNTAX INTEGER
        {
         ok(1),
         indeterminate(2),
         warning(3),
         minor(4),
         major(5),
         critical(6)
        }
    MAX-ACCESS read-only
    STATUS current
    DESCRIPTION
        "'major' indicates that one or more commands has been waiting for
         an extracted message (i.e. PAT, PMT) for more than 60 seconds.
         Alarm is cleared after all commands waiting for extracted messages
         have received all messages.
         Not applicable when SEM is internally controlled."
::= { semAlarms 8007 }

semAlarmLossOfPhysicalInput OBJECT-TYPE
    SYNTAX INTEGER
        {
         ok(1),
         indeterminate(2),
         warning(3),
         minor(4),
         major(5),
         critical(6)
        }
    MAX-ACCESS read-only
    STATUS current
    DESCRIPTION
        "'critical' indicates that one or more physical interfaces that are
         configured as enabled to receive input have a failure.
         Physical input interfaces can be disabled to prevent this alarm
         when no input is connected.
         This alarm may also be disabled by semConfAlarmEnableLossOfPhysIn."
::= { semAlarms 8008 }

semAlarmServiceNotAuthorized OBJECT-TYPE
    SYNTAX INTEGER
        {
         ok(1),
         indeterminate(2),
         warning(3),
         minor(4),
         major(5),
         critical(6)
        }
    MAX-ACCESS read-only
    STATUS current
    DESCRIPTION
        "'major' indicates one or more services that have been commanded to be
         in Full Encryption Mode and are not authorized.  Authorized status is
         based on the status returned from each ACP.
         Not applicable when SEM is internally controlled."
::= { semAlarms 8009 }

semAlarmTemperatureFault OBJECT-TYPE
    SYNTAX INTEGER
        {
         ok(1),
         indeterminate(2),
         warning(3),
         minor(4),
         major(5),
         critical(6)
        }
    MAX-ACCESS read-only
    STATUS current
    DESCRIPTION
        "'critical' indicates one or more temperature sensors is sensing a
         high temperature condition (greater than 60 degrees Celsius)"
::= { semAlarms 8010 }

semAlarmFanFault OBJECT-TYPE
    SYNTAX INTEGER
        {
         ok(1),
         indeterminate(2),
         warning(3),
         minor(4),
         major(5),
         critical(6)
        }
    MAX-ACCESS read-only
    STATUS current
    DESCRIPTION
        "'major' indicates one fan has reduced RPM readings.
         'critical' indicates two or more fans have reduced RPM readings.
         NOTES:
           1) SEM fan status monitoring takes place at approximately 5 second intervals.
           2) One fan is monitored each status cycle.  Each fan is monitored every 15 seconds.
           3) Low fan is below 7500 RPM
           4) Stopped fan is below 1000 RPM
           5) Low fan must be detected for three consecutive readings to cause alarm (45 seconds).
           6) Stopped fan reading will cause alarm immediately.
        "
::= { semAlarms 8011 }

semAlarmGigeFailOver OBJECT-TYPE
    SYNTAX INTEGER
        {
         ok(1),
         indeterminate(2),
         warning(3),
         minor(4),
         major(5),
         critical(6)
        }
    MAX-ACCESS read-only
    STATUS current
    DESCRIPTION
        "'major' indicates Gigabit Ethernet Fail Over when in Redundant Mode.

         This alarm applies to Gigabit Ethernet Interface Redundancy.
        "
::= { semAlarms 8012 }

semAlarmOtsUtilizationFault OBJECT-TYPE
    SYNTAX INTEGER
        {
         ok(1),
         indeterminate(2),
         warning(3),
         minor(4),
         major(5),
         critical(6)
        }
    MAX-ACCESS read-only
    STATUS current
    DESCRIPTION
        "Output Transport Stream Utilization Threshold Alarm.
         'minor' when semOutTransUtilMonAlarmThreshold is met or
         exceeded for semOutTransUtilMonSetAlarmDelay for one or
         more OTS.  The alarm will clear after all monitored OTS
         remain below semOutTransUtilMonAlarmThreshold for
         semOutTransUtilMonClearAlarmDelay.  This alarm will only
         be set when one or more OTS are enabled to be monitored
         via semOutTransUtilMonEnable."
::= { semAlarms 8013 }

semAlarmGigeRedundantModeThreshold OBJECT-TYPE
    SYNTAX INTEGER
        {
         ok(1),
         indeterminate(2),
         warning(3),
         minor(4),
         major(5),
         critical(6)
        }
    MAX-ACCESS read-only
    STATUS current
    DESCRIPTION
        "'minor' indicates Gigabit Ethernet Packet Counts differ by more than
         semGbeRedunModeThreshold for more than semGbeRedunModeMonPeriod when
         in Redundant Mode.

         This alarm applies to Gigabit Ethernet Interface Redundancy.
        "
::= { semAlarms 8014 }

semAlarmSimulcryptCommunicationFault OBJECT-TYPE
    SYNTAX INTEGER
        {
         ok(1),
         indeterminate(2),
         warning(3),
         minor(4),
         major(5),
         critical(6)
        }
    MAX-ACCESS read-only
    STATUS current
    DESCRIPTION
        "'major' indicates that one or more simulcrypt interfaces is having
         a communication failure.  Failures connecting to defined ECMGs and
         failures receiving data from EMMGs can cause this failure.
         Applicable only when semDeviceOperatingMode is 'simulcrypt1'.
         Consult bcsSimulcryptScs and bcsSimulcryptMux MIBs for additional
         status."
::= { semAlarms 8015 }

semAlarmQamFault OBJECT-TYPE
    SYNTAX INTEGER
        {
         ok(1),
         indeterminate(2),
         warning(3),
         minor(4),
         major(5),
         critical(6)
        }
    MAX-ACCESS read-only
    STATUS current
    DESCRIPTION
        "QAM Fault Alarm.

         'critical' when any or all of the QAM errors
         enumerated in semQamStatusError occur on any QAM.

         The alarm will clear after all QAM faults clear on
         all outputs.

         The current alarm status on a QAM basis can be
         found in semQamStatusFault."
::= { semAlarms 8016 }

semAlarmUpconverterFault OBJECT-TYPE
    SYNTAX INTEGER
        {
         ok(1),
         indeterminate(2),
         warning(3),
         minor(4),
         major(5),
         critical(6)
        }
    MAX-ACCESS read-only
    STATUS current
    DESCRIPTION
        "Upconverter Fault Alarm.

         'critical' when any or all of the Upconverter errors
         enumerated in semUpConvStatusUpConvError occur on
         any Upconverter.

         The alarm will clear after all Upconverter faults clear on
         all outputs.

         The current alarm status on a Upconverter basis can be
         found in semUpConvStatusFault."
::= { semAlarms 8017 }

semAlarmOtsHostIpOverflow OBJECT-TYPE
    SYNTAX INTEGER
        {
         ok(1),
         indeterminate(2),
         warning(3),
         minor(4),
         major(5),
         critical(6)
        }
    MAX-ACCESS read-only
    STATUS current
    DESCRIPTION
        "Output Transport Stream Host IP Insert Packet Overflow Alarm.
         'critical' when Host IP insert packets are being dropped.
         semIpInsertPacketStatNumDiscardPkts indicates which Output
         Transport Streams are experiencing dropped IP packets.
         semHostIpPacketStatNumDiscardPkts indicates which Host IP
         interface is the source of the packets that were dropped.
         The alarm will clear after all OTS are clear."
::= { semAlarms 8018 }

semAlarmOtsOverflow OBJECT-TYPE
    SYNTAX INTEGER
        {
         ok(1),
         indeterminate(2),
         warning(3),
         minor(4),
         major(5),
         critical(6)
        }
    MAX-ACCESS read-only
    STATUS current
    DESCRIPTION
        "Output Transport Stream Overflow Alarm.
         'critical' when semOutTransStatusOverflow occurs.
         The alarm will clear after all OTS
         semOutTransStatusOverflow clear."
::= { semAlarms 8019 }

semAlarmIceEmmServerCommFailure OBJECT-TYPE
    SYNTAX INTEGER
        {
         ok(1),
         indeterminate(2),
         warning(3),
         minor(4),
         major(5),
         critical(6)
        }
    MAX-ACCESS read-only
    STATUS current
    DESCRIPTION
        "Internal Control of Encryption (ICE) Entitlement Management
         Message Server (EMMS) Communication Failure Alarm.
         'major' when communication between the SEM and EMMS fails.
         The alarm will clear when communication with the EMM Server
         is restored or by semIceEmmServerCommAlarmClear.
         This alarm only applies when the SEM is in an internal
         semDeviceOperatingMode and semIceEncryptionMode is set to 'full'."
::= { semAlarms 8020 }

semAlarmIceEmmServerInvalidResponse OBJECT-TYPE
    SYNTAX INTEGER
        {
         ok(1),
         indeterminate(2),
         warning(3),
         minor(4),
         major(5),
         critical(6)
        }
    MAX-ACCESS read-only
    STATUS current
    DESCRIPTION
        "Internal Control of Encryption (ICE) Entitlement Management
         Message Server (EMMS) Invalid Response Alarm.
         'major' when the SEM receives an invalid response or error
         from the EMMS.
         The alarm will clear when the reason for the invalid response
         or error is corrected or by semIceEmmServerInvalRespAlarmClear.
         This alarm only applies when the SEM is in an internal
         semDeviceOperatingMode and semIceEncryptionMode is set to 'full'."
::= { semAlarms 8021 }

semAlarmIceFullEncryptFailure OBJECT-TYPE
    SYNTAX INTEGER
        {
         ok(1),
         indeterminate(2),
         warning(3),
         minor(4),
         major(5),
         critical(6)
        }
    MAX-ACCESS read-only
    STATUS current
    DESCRIPTION
        "Internal Control of Encryption (ICE) Encryption Failure Alarm.
         'major' when the SEM is configured to be in full encryption
         and cannot be.
         The alarm will clear when the SEM returns to full encryption or
         the user configures the SEM to no longer be in full encryption mode.

         This alarm only applies when the SEM is in an internal
         semDeviceOperatingMode and semIceEncryptionMode is set to 'full'."
::= { semAlarms 8022 }

semAlarmQamPortFault OBJECT-TYPE
    SYNTAX INTEGER
        {
         ok(1),
         indeterminate(2),
         warning(3),
         minor(4),
         major(5),
         critical(6)
        }
    MAX-ACCESS read-only
    STATUS current
    DESCRIPTION
        "QAM Port Fault Alarm.

         'critical' when any or all of the QAM and Upconverter errors
         enumerated in semQamStatusPortError occur on any QAM Port.

         The alarm will clear after all QAM faults clear on all QAM Ports.

         The current alarm status on a QAM port basis can be found in
         semQamStatusPortFault."
::= { semAlarms 8023 }

semAlarmGbeBufferFullness OBJECT-TYPE
    SYNTAX INTEGER
        {
         ok(1),
         indeterminate(2),
         warning(3),
         minor(4),
         major(5),
         critical(6)
        }
    MAX-ACCESS read-only
    STATUS current
    DESCRIPTION
        "Gigabit Ethernet Frame Buffer Fullness Alarm.
         This alarm is used to inform the user when one or more Gigabit Ethernet
         Frame buffers are about to or have overflowed.  The overflow level is
         based on the actual input data rate.

         'major' when the frame buffer crosses a user specified threshold
         (semGbeBufferAlarmThreshold).  Cleared when the buffer level drops
         below the threshold.

         'critical' when the frame buffer is completely full and frames are being
         dropped.  Cleared when the overflow condition stops.

         A Major alarm, depending on the threshold setting, indicates that the
         SEM is getting close to overflowing it's internal Gigabit Ethernet
         frame buffers.  A Critical alarm indicates that the frame buffer levels
         have overflowed.  This will cause loss of packets and may result in
         tiling and other output anomalies."
::= { semAlarms 8024 }

semAlarmGbeInputStreamLowBitRate OBJECT-TYPE
    SYNTAX INTEGER
        {
         ok(1),
         indeterminate(2),
         warning(3),
         minor(4),
         major(5),
         critical(6)
        }
    MAX-ACCESS read-only
    STATUS current
    DESCRIPTION
        "Gigabit Ethernet Input Stream Low Bit Rate Alarm.
         This alarm is used to inform the user when one or more Gigabit Ethernet
         Input Streams as configured in semGbeInputUdpConfigTable have a low
         bit rate condition.  For alarm status of each stream refer to entry
         semGbeStatInUdpLowBitRateAlarm.

         'critical' when one or more stream bit rates are below their
         semGbeInUdpConfLowAlarmBitRate.  Clears when all streams have been
         restored to at or above their configured semGbeInUdpConfLowAlarmBitRate.
         Also cleared by semConfAlarmClearGbeInStreamLowBitRate.
        "
::= { semAlarms 8025 }

semAlarmGbeMptsRedundPrimaryThreshold OBJECT-TYPE
    SYNTAX INTEGER
        {
         ok(1),
         indeterminate(2),
         warning(3),
         minor(4),
         major(5),
         critical(6)
        }
    MAX-ACCESS read-only
    STATUS current
    DESCRIPTION
        "Gigabit Ethernet Input MPTS Redundant Primary Stream Below Threshold Alarm.
         This alarm is used to inform the user when one or more Gigabit Ethernet
         Input Streams configured in semGbeInputUdpConfigTable as being the Primary
         stream of a Redundant Pair are below the configured threshold.
         bit rate condition.  For alarm status of each stream refer to entry
         semGbeStatInUdpMptsRedundPriAlarm.

         'critical' when one or more stream bit rates are below their threshold
         as specified in semGbeInUdpConfMptsRedundThreshold.  Clears when all
         streams have been restored to at or above their configured
         semGbeInUdpConfMptsRedundThreshold.  Also cleared by
         semConfAlarmClearGbeMptsRedundThreshold.
        "
::= { semAlarms 8026 }

semAlarmGbeMptsRedundFailOver OBJECT-TYPE
    SYNTAX INTEGER
        {
         ok(1),
         indeterminate(2),
         warning(3),
         minor(4),
         major(5),
         critical(6)
        }
    MAX-ACCESS read-only
    STATUS current
    DESCRIPTION
        "Gigabit Ethernet Input MPTS Redundant Fail Over Alarm.
         This alarm is used to inform the user when one or more Gigabit Ethernet
         Input Streams configured in semGbeInputUdpConfigTable as being the Primary
         stream of a Redundant Pair have Failed Over to the Secondary stream.
         For alarm status of each stream refer to entry semGbeStatInUdpMptsRedundFailAlarm.

         'critical' when one or more Redundant Primary streams have failed over to
         the Secondary.  Clears when all Primary streams have been restored and the
         SEM has switched back to the Primary from the Secondary.  Also cleared by
         semConfAlarmClearGbeMptsRedundFailOver.
        "
::= { semAlarms 8027 }

semAlarmGbeInputStreamHighBitRate OBJECT-TYPE
    SYNTAX INTEGER
        {
         ok(1),
         indeterminate(2),
         warning(3),
         minor(4),
         major(5),
         critical(6)
        }
    MAX-ACCESS read-only
    STATUS current
    DESCRIPTION
        "Gigabit Ethernet Input Stream High Bit Rate Alarm.
         This alarm is used to inform the user when one or more Gigabit Ethernet
         Input Streams as configured in semGbeInputUdpConfigTable have a high
         bit rate condition.  For alarm status of each stream refer to entry
         semGbeStatInUdpHighBitRateAlarm.

         'critical' when one or more stream bit rates are above their
         semIsaSdvSessionStatProgramBandwidth.  Clears when all streams have been
         restored to at or above their semIsaSdvSessionStatProgramBandwidth.
         Also cleared when disabled by semConfAlarmEnableGbeInHighBitRate.
        "
::= { semAlarms 8028 }


-- --------------------------------------------
--

semEventHardwareError OBJECT-TYPE
    SYNTAX Unsigned32
    MAX-ACCESS read-only
    STATUS current
    DESCRIPTION
        "Count of SEM Hardware errors."
::= { semEvents 8100 }

semEventInvalidInitDataError OBJECT-TYPE
    SYNTAX Unsigned32
    MAX-ACCESS read-only
    STATUS current
    DESCRIPTION
        "Count of SEM Initialization Data errors (ini files)."
::= { semEvents 8101 }

semEventInvalidConfigDataError OBJECT-TYPE
    SYNTAX Unsigned32
    MAX-ACCESS read-only
    STATUS current
    DESCRIPTION
        "Count of SEM Configuration errors (via SNMP)."
::= { semEvents 8102 }

semEventLoadDeviceError OBJECT-TYPE
    SYNTAX Unsigned32
    MAX-ACCESS read-only
    STATUS current
    DESCRIPTION
        "Count of Load SEM Command errors."
::= { semEvents 8103 }

semEventPhysicalInputError OBJECT-TYPE
    SYNTAX Unsigned32
    MAX-ACCESS read-only
    STATUS current
    DESCRIPTION
        "Count of SEM Physical Input errors."
::= { semEvents 8104 }

semEventOtsUtilizationError OBJECT-TYPE
    SYNTAX Unsigned32
    MAX-ACCESS read-only
    STATUS current
    DESCRIPTION
        "Count of SEM Output Transport Stream Utilization Faults."
::= { semEvents 8105 }

semEventGbeBufferReset OBJECT-TYPE
    SYNTAX Unsigned32
    MAX-ACCESS read-only
    STATUS current
    DESCRIPTION
        "Number of Gigabit Ethernet Frame Buffer resets."
::= { semEvents 8106 }

semEventEmUserLoginFailed OBJECT-TYPE
    SYNTAX Unsigned32
    MAX-ACCESS read-only
    STATUS current
    DESCRIPTION
        "Event to indicate SEM EM User login failed 5 times."
::= { semEvents 8107 }

semEventNewControllerObserved OBJECT-TYPE
    SYNTAX Unsigned32
    MAX-ACCESS read-only
    STATUS current
    DESCRIPTION
        "Event to indicate that the SEM is in multi-controller
         mode and has received a LOAD SEM message from a new
         controller."
::= { semEvents 8108 }


-- ------------------------------------------------------------------------------
--
-- semErrorStatus
--
-- semHwErrorTable
--

semHwErrorTable OBJECT-TYPE
    SYNTAX SEQUENCE OF SemHwErrorEntry
    MAX-ACCESS not-accessible
    STATUS current
    DESCRIPTION
        "Table of Hardware Errors that have occurred.
         Maximum of 20 errors will be recorded.
        "
::= { semErrorStatus 1 }

semHwErrorEntry OBJECT-TYPE
    SYNTAX SemHwErrorEntry
    MAX-ACCESS not-accessible
    STATUS current
    DESCRIPTION
        "Hardware Error Table Entry."
    INDEX { semHwErrorIndex }
::= { semHwErrorTable 1 }

SemHwErrorEntry ::= SEQUENCE
    {
     semHwErrorIndex          Integer32,
     semHwErrorCode           Integer32,
     semHwErrorData           Integer32,
     semHwErrorDescription    DisplayString,
     semHwErrorTimeLogged     TimeTicks
    }

semHwErrorIndex OBJECT-TYPE
    SYNTAX Integer32
    MAX-ACCESS not-accessible
    STATUS current
    DESCRIPTION
        "Index to HW Error table entry."
::= { semHwErrorEntry 1 }

semHwErrorCode OBJECT-TYPE
    SYNTAX Integer32
    MAX-ACCESS read-only
    STATUS current
    DESCRIPTION
        "Error Code of HW Error.  Refer to manual."
::= { semHwErrorEntry 2 }

semHwErrorData OBJECT-TYPE
    SYNTAX Integer32
    MAX-ACCESS read-only
    STATUS current
    DESCRIPTION
        "Applicable to errors that are issued for multiple inputs,
         outputs, Output Transport Streams, etc..
         This is used to indicate the input port, output port, or
         Output Transport to which the error applies.
         Zero indicates that the error does not use this parameter,
         the SEM cannot determine the port or stream number for
         the error, or the SEM is not supporting this parameter for
         the error."
::= { semHwErrorEntry 3 }

semHwErrorDescription OBJECT-TYPE
    SYNTAX DisplayString
    MAX-ACCESS read-only
    STATUS current
    DESCRIPTION
        "Text description of the error."
::= { semHwErrorEntry 4 }

semHwErrorTimeLogged OBJECT-TYPE
    SYNTAX TimeTicks
    MAX-ACCESS read-only
    STATUS current
    DESCRIPTION
        "Time in GPS seconds (semSystemTime) that this event was logged.
        "
::= { semHwErrorEntry 5 }


-- ------------------------------------------------------------------------------
--
-- semInvalidInitDataTable
--

semInvalidInitDataTable OBJECT-TYPE
    SYNTAX SEQUENCE OF SemInvalidInitDataEntry
    MAX-ACCESS not-accessible
    STATUS current
    DESCRIPTION
        "Table of Invalid Initialization Data Errors.
         Maximum of 100 errors will be recorded.
        "
::= { semErrorStatus 2 }

semInvalidInitDataEntry OBJECT-TYPE
    SYNTAX SemInvalidInitDataEntry
    MAX-ACCESS not-accessible
    STATUS current
    DESCRIPTION
        "Invalid Initialization Data Table Entry."
    INDEX { semInvalidInitDataIndex }
::= { semInvalidInitDataTable 1 }

SemInvalidInitDataEntry ::= SEQUENCE
    {
     semInvalidInitDataIndex          Integer32,
     semInvalidInitDataMibName        DisplayString,
     semInvalidInitDataItemNum        Integer32,
     semInvalidInitDataIndex1         Integer32,
     semInvalidInitDataIndex2         Integer32
    }

semInvalidInitDataIndex OBJECT-TYPE
    SYNTAX Integer32
    MAX-ACCESS not-accessible
    STATUS current
    DESCRIPTION
        "Index to Invalid Initialization Data table entry."
::= { semInvalidInitDataEntry 1 }

semInvalidInitDataMibName OBJECT-TYPE
    SYNTAX DisplayString
    MAX-ACCESS read-only
    STATUS current
    DESCRIPTION
        "Text string of the MIB variable name of the data item
         or table."
::= { semInvalidInitDataEntry 2 }

semInvalidInitDataItemNum OBJECT-TYPE
    SYNTAX Integer32
    MAX-ACCESS read-only
    STATUS current
    DESCRIPTION
        "When the data item is part of a table this parameter
         indicates which table leaf the error pertains to."
::= { semInvalidInitDataEntry 3 }

semInvalidInitDataIndex1 OBJECT-TYPE
    SYNTAX Integer32
    MAX-ACCESS read-only
    STATUS current
    DESCRIPTION
        "When the data item is part of a table this parameter
         indicates the index value of the first index."
::= { semInvalidInitDataEntry 4 }

semInvalidInitDataIndex2 OBJECT-TYPE
    SYNTAX Integer32
    MAX-ACCESS read-only
    STATUS current
    DESCRIPTION
        "When the data item is part of a table with two indices
         this parameter indicates the index value of the second index."
::= { semInvalidInitDataEntry 5 }


-- ------------------------------------------------------------------------------
--
-- semCommandErrorTable
--

semCommandErrorTable OBJECT-TYPE
    SYNTAX SEQUENCE OF SemCommandErrorEntry
    MAX-ACCESS not-accessible
    STATUS current
    DESCRIPTION
        "Table of Command Processing Errors that have occurred.
         Maximum of 2000 errors will be recorded."
::= { semErrorStatus 3 }

semCommandErrorEntry OBJECT-TYPE
    SYNTAX SemCommandErrorEntry
    MAX-ACCESS not-accessible
    STATUS current
    DESCRIPTION
        "Command Processing Error Table Entry."
    INDEX { semCommandErrorIndex }
::= { semCommandErrorTable 1 }

SemCommandErrorEntry ::= SEQUENCE
    {
     semCommandErrorIndex          Integer32,
     semCommandErrorTimeLogged     Integer32,
     semCommandErrorCommandSeqNum  Integer32,
     semCommandErrorCode           Integer32,
     semCommandErrorCommandId      Integer32
    }

semCommandErrorIndex OBJECT-TYPE
    SYNTAX Integer32
    MAX-ACCESS not-accessible
    STATUS current
    DESCRIPTION
        "Index to Command Processing Error table entry."
::= { semCommandErrorEntry 1 }

semCommandErrorTimeLogged OBJECT-TYPE
    SYNTAX Integer32
    MAX-ACCESS read-only
    STATUS current
    DESCRIPTION
        "Time in GPS seconds (semSystemTime) that this error occurred."
::= { semCommandErrorEntry 2 }

semCommandErrorCommandSeqNum OBJECT-TYPE
    SYNTAX Integer32
    MAX-ACCESS read-only
    STATUS current
    DESCRIPTION
        "Load SEM Command sequence number of erring command."
::= { semCommandErrorEntry 3 }

semCommandErrorCode OBJECT-TYPE
    SYNTAX Integer32
    MAX-ACCESS read-only
    STATUS current
    DESCRIPTION
        "Error Code of Command Processing Error.  This code can be
         used by Motorola personnel to diagnose issues."
::= { semCommandErrorEntry 4 }

semCommandErrorCommandId OBJECT-TYPE
    SYNTAX Integer32
    MAX-ACCESS read-only
    STATUS current
    DESCRIPTION
        "Load SEM Command ID of erring command."
::= { semCommandErrorEntry 5 }


-- ------------------------------------------------------------------------------
--
-- semOutputStreamErrorTable
--

semOutputStreamErrorTable OBJECT-TYPE
    SYNTAX SEQUENCE OF SemOutputStreamErrorEntry
    MAX-ACCESS not-accessible
    STATUS current
    DESCRIPTION
        "Table of Output Stream Error events that have occurred.
         These include errors occurring and clearing.
         Maximum of 200 events will be recorded.
        "
::= { semErrorStatus 4 }

semOutputStreamErrorEntry OBJECT-TYPE
    SYNTAX SemOutputStreamErrorEntry
    MAX-ACCESS not-accessible
    STATUS current
    DESCRIPTION
        "Output Stream Error Table Entry."
    INDEX { semOutputStreamErrorIndex }
::= { semOutputStreamErrorTable 1 }

SemOutputStreamErrorEntry ::= SEQUENCE
    {
     semOutputStreamErrorIndex          Integer32,
     semOutputStreamErrorTimeLogged     Integer32,
     semOutputStreamErrorAlarmCode      Integer32,
     semOutputStreamErrorAlarmSeverity  INTEGER,
     semOutputStreamErrorOtsNum         Integer32,
     semOutputStreamErrorPhysOutType    INTEGER,
     semOutputStreamErrorPhysOutPort    Integer32,
     semOutputStreamErrorCurRate        Integer32,
     semOutputStreamErrorAvgRate        Integer32,
     semOutputStreamErrorMinRate        Integer32,
     semOutputStreamErrorPeakRate       Integer32,
     semOutputStreamErrorDescription    DisplayString
    }

semOutputStreamErrorIndex OBJECT-TYPE
    SYNTAX Integer32
    MAX-ACCESS not-accessible
    STATUS current
    DESCRIPTION
        "Index to Output Stream Error table.
        "
::= { semOutputStreamErrorEntry 1 }

semOutputStreamErrorTimeLogged OBJECT-TYPE
    SYNTAX Integer32
    MAX-ACCESS read-only
    STATUS current
    DESCRIPTION
        "Time in GPS seconds (semSystemTime) that this event was logged.
        "
::= { semOutputStreamErrorEntry 2 }

semOutputStreamErrorAlarmCode OBJECT-TYPE
    SYNTAX Integer32
    MAX-ACCESS read-only
    STATUS current
    DESCRIPTION
        "Last number of alarm OID.  Can be one of the following:
            8013 semAlarmOtsUtilizationFault
            8016 semAlarmQamFault
            8017 semAlarmUpconverterFault
            8018 semAlarmOtsHostIpOverflow
            8019 semAlarmOtsOverflow

         More details about the error can be found in semOutputStreamErrorDescription.
        "
::= { semOutputStreamErrorEntry 3 }

semOutputStreamErrorAlarmSeverity OBJECT-TYPE
    SYNTAX INTEGER
        {
         ok(1),
         indeterminate(2),
         warning(3),
         minor(4),
         major(5),
         critical(6)
        }
    MAX-ACCESS read-only
    STATUS current
    DESCRIPTION
        "Alarm severity level of this event.
        "
::= { semOutputStreamErrorEntry 4 }

semOutputStreamErrorOtsNum OBJECT-TYPE
    SYNTAX Integer32 (0..16)
    MAX-ACCESS read-only
    STATUS current
    DESCRIPTION
        "The number of the output transport stream for this event.
        "
::= { semOutputStreamErrorEntry 5 }

semOutputStreamErrorPhysOutType OBJECT-TYPE
    SYNTAX INTEGER
        {
         gbe (1),
         asi (2),
         qam (4)
        }
    MAX-ACCESS read-only
    STATUS current
    DESCRIPTION
        "The physical interface type of this output stream.  It is the
         value of semOutTransStreamPhysOutType for semOutputStreamErrorOtsNum.
        "
::= { semOutputStreamErrorEntry 6 }

semOutputStreamErrorPhysOutPort OBJECT-TYPE
    SYNTAX Integer32
    MAX-ACCESS read-only
    STATUS current
    DESCRIPTION
        "Number of the output, of semOutputStreamErrorPhysOutType.
         It is the value of semOutTransStreamPhysOutPort for
         semOutputStreamErrorOtsNum.
        "
::= { semOutputStreamErrorEntry 7 }

semOutputStreamErrorCurRate OBJECT-TYPE
    SYNTAX Integer32
    MAX-ACCESS read-only
    STATUS current
    DESCRIPTION
        "Value of semOutTransUtilizationRate when event occurred.
        "
::= { semOutputStreamErrorEntry 8 }

semOutputStreamErrorAvgRate OBJECT-TYPE
    SYNTAX Integer32
    MAX-ACCESS read-only
    STATUS current
    DESCRIPTION
        "Value of semOutTransUtilizationAvgRate when event occurred.
        "
::= { semOutputStreamErrorEntry 9 }

semOutputStreamErrorMinRate OBJECT-TYPE
    SYNTAX Integer32
    MAX-ACCESS read-only
    STATUS current
    DESCRIPTION
        "Value of semOutTransUtilizationMinRate when event occurred.
        "
::= { semOutputStreamErrorEntry 10 }

semOutputStreamErrorPeakRate OBJECT-TYPE
    SYNTAX Integer32
    MAX-ACCESS read-only
    STATUS current
    DESCRIPTION
        "Value of semOutTransUtilizationPeakRate when event occurred.
        "
::= { semOutputStreamErrorEntry 11 }

semOutputStreamErrorDescription OBJECT-TYPE
    SYNTAX DisplayString
    MAX-ACCESS read-only
    STATUS current
    DESCRIPTION
        "Text description of the event.
         Maximum length is 128 characters.
        "
::= { semOutputStreamErrorEntry 12 }


-- ------------------------------------------------------------------------------
--
-- semGbeInputUdpErrorTable
--

semGbeInputUdpErrorTable OBJECT-TYPE
    SYNTAX SEQUENCE OF SemGbeInputUdpErrorEntry
    MAX-ACCESS not-accessible
    STATUS current
    DESCRIPTION
        "Table of Gigabit Ethernet Input UDP Port Error events that have occurred.
         These include errors occurring and clearing.
         Maximum of 100 events will be recorded.
        "
::= { semErrorStatus 5 }

semGbeInputUdpErrorEntry OBJECT-TYPE
    SYNTAX SemGbeInputUdpErrorEntry
    MAX-ACCESS not-accessible
    STATUS current
    DESCRIPTION
        "Gigabit Ethernet Input UDP Port Error Table Entry."
    INDEX { semGbeInputUdpErrorIndex }
::= { semGbeInputUdpErrorTable 1 }

SemGbeInputUdpErrorEntry ::= SEQUENCE
    {
     semGbeInputUdpErrorIndex               Integer32,
     semGbeInputUdpErrorTimeLogged          Integer32,
     semGbeInputUdpErrorAlarmCode           Integer32,
     semGbeInputUdpErrorAlarmSeverity       INTEGER,
     semGbeInputUdpErrorUdpIndex            Integer32,
     semGbeInputUdpErrorGbePort             Integer32,
     semGbeInputUdpErrorUdpPort             Integer32,
     semGbeInputUdpErrorUdpPortState        UdpPortStateTYPE,
     semGbeInputUdpErrorRateCompareType     RateComparisonTYPE,
     semGbeInputUdpErrorSamplingPeriod      Integer32,
     semGbeInputUdpErrorCurCount            Counter32,
     semGbeInputUdpErrorAvgCount            Counter32,
     semGbeInputUdpErrorMinCount            Counter32,
     semGbeInputUdpErrorPeakCount           Counter32,
     semGbeInputUdpErrorDescription         DisplayString
    }

semGbeInputUdpErrorIndex OBJECT-TYPE
    SYNTAX Integer32
    MAX-ACCESS not-accessible
    STATUS current
    DESCRIPTION
        "Index to Gigabit Ethernet Input UDP Port Error table.
        "
::= { semGbeInputUdpErrorEntry 1 }

semGbeInputUdpErrorTimeLogged OBJECT-TYPE
    SYNTAX Integer32
    MAX-ACCESS read-only
    STATUS current
    DESCRIPTION
        "Time in GPS seconds (semSystemTime) that this event was logged.
        "
::= { semGbeInputUdpErrorEntry 2 }

semGbeInputUdpErrorAlarmCode OBJECT-TYPE
    SYNTAX Integer32
    MAX-ACCESS read-only
    STATUS current
    DESCRIPTION
        "Last number of alarm OID.  Can be one of the following:
            8025 semAlarmGbeInputStreamLowBitRate
            8026 semAlarmGbeMptsRedundPrimaryThreshold
            8027 semAlarmGbeMptsRedundFailOver
            8028 semAlarmGbeInputStreamHighBitRate

         More details about the error can be found in semGbeInputUdpErrorDescription.
        "
::= { semGbeInputUdpErrorEntry 3 }

semGbeInputUdpErrorAlarmSeverity OBJECT-TYPE
    SYNTAX INTEGER
        {
         ok(1),
         indeterminate(2),
         warning(3),
         minor(4),
         major(5),
         critical(6)
        }
    MAX-ACCESS read-only
    STATUS current
    DESCRIPTION
        "Alarm severity level of this event.
        "
::= { semGbeInputUdpErrorEntry 4 }

semGbeInputUdpErrorUdpIndex OBJECT-TYPE
    SYNTAX Integer32
    MAX-ACCESS read-only
    STATUS current
    DESCRIPTION
        "The index of this UDP port into semGbeInputUdpConfigTable and
         semGbeStatusInputUdpTable at the time of the event.  Note that
         the UDP port may have been deleted from semGbeInputUdpConfigTable
         after this event occurred.
        "
::= { semGbeInputUdpErrorEntry 5 }

semGbeInputUdpErrorGbePort OBJECT-TYPE
    SYNTAX Integer32
    MAX-ACCESS read-only
    STATUS current
    DESCRIPTION
        "Value of semGbeInUdpConfGbePort when event occurred.
        "
::= { semGbeInputUdpErrorEntry 6 }

semGbeInputUdpErrorUdpPort OBJECT-TYPE
    SYNTAX Integer32
    MAX-ACCESS read-only
    STATUS current
    DESCRIPTION
        "Value of semGbeInUdpConfUdpPort when event occurred.
        "
::= { semGbeInputUdpErrorEntry 7 }

semGbeInputUdpErrorUdpPortState OBJECT-TYPE
    SYNTAX UdpPortStateTYPE
    MAX-ACCESS read-only
    STATUS current
    DESCRIPTION
        "Value of semGbeStatInUdpState when event occurred.
        "
::= { semGbeInputUdpErrorEntry 8 }

semGbeInputUdpErrorRateCompareType OBJECT-TYPE
    SYNTAX RateComparisonTYPE
    MAX-ACCESS read-only
    STATUS current
    DESCRIPTION
        "Value of semGbeInUdpConfRateCompareType when event occurred.
        "
::= { semGbeInputUdpErrorEntry 9 }

semGbeInputUdpErrorSamplingPeriod OBJECT-TYPE
    SYNTAX Integer32
    MAX-ACCESS read-only
    STATUS current
    DESCRIPTION
        "Value of semGbeStatInUdpSamplingPeriod when event occurred.
        "
::= { semGbeInputUdpErrorEntry 10 }

semGbeInputUdpErrorCurCount OBJECT-TYPE
    SYNTAX Counter32
    MAX-ACCESS read-only
    STATUS current
    DESCRIPTION
        "Current Packet Count when event occurred.

         Value of semGbeStatInUdpCurDataCount when semGbeInputUdpErrorRateCompareType
         is 'dataRate'.
         Value of semGbeStatInUdpCurTsCount when semGbeInputUdpErrorRateCompareType
         is 'transportStreamRate'.
        "
::= { semGbeInputUdpErrorEntry 11 }

semGbeInputUdpErrorAvgCount OBJECT-TYPE
    SYNTAX Counter32
    MAX-ACCESS read-only
    STATUS current
    DESCRIPTION
        "Average Packet Count when event occurred.

         Value of semGbeStatInUdpAvgDataCount when semGbeInputUdpErrorRateCompareType
         is 'dataRate'.
         Value of semGbeStatInUdpAvgTsCount when semGbeInputUdpErrorRateCompareType
         is 'transportStreamRate'.
        "
::= { semGbeInputUdpErrorEntry 12 }

semGbeInputUdpErrorMinCount OBJECT-TYPE
    SYNTAX Counter32
    MAX-ACCESS read-only
    STATUS current
    DESCRIPTION
        "Minimum Packet Count when event occurred.

         Value of semGbeStatInUdpMinDataCount when semGbeInputUdpErrorRateCompareType
         is 'dataRate'.
         Value of semGbeStatInUdpMinTsCount when semGbeInputUdpErrorRateCompareType
         is 'transportStreamRate'.
        "
::= { semGbeInputUdpErrorEntry 13 }

semGbeInputUdpErrorPeakCount OBJECT-TYPE
    SYNTAX Counter32
    MAX-ACCESS read-only
    STATUS current
    DESCRIPTION
        "Peak Packet Count when event occurred.

         Value of semGbeStatInUdpPeakDataCount when semGbeInputUdpErrorRateCompareType
         is 'dataRate'.
         Value of semGbeStatInUdpPeakTsCount when semGbeInputUdpErrorRateCompareType
         is 'transportStreamRate'.
        "
::= { semGbeInputUdpErrorEntry 14 }

semGbeInputUdpErrorDescription OBJECT-TYPE
    SYNTAX DisplayString
    MAX-ACCESS read-only
    STATUS current
    DESCRIPTION
        "Text description of the event.
         Maximum length is 128 characters.
        "
::= { semGbeInputUdpErrorEntry 15 }


-- ------------------------------------------------------------------------------
--
-- semConfigAlarms
--
-- semConfAlarmEnable
--

semConfAlarmEnableLossOfPhysIn  OBJECT-TYPE
    SYNTAX EnableDisableTYPE
    MAX-ACCESS read-write
    STATUS current
    DESCRIPTION
        "This setting enables or disables semAlarmLossOfPhysicalInput.  When set
         to 'enabled' the alarm will operate as described.  When set to 'disabled'
         the alarm will not be reported or wrapped into unitAlarmStatus, and
         semAlarmLossOfPhysicalInput will remain 'ok'.  If semAlarmLossOfPhysicalInput
         is not 'ok' when semConfAlarmEnableLossOfPhysIn is changed to 'disabled'
         semConfAlarmEnableLossOfPhysIn will be cleared.

         Once written, the change to this parameter will take immediate
         effect.  However, in order for the change to persist through
         subsequent reboots or power cycles, the change must be saved via
         the semSaveConfig parameter.

         @Config(config=yes, reboot=no)
         @Save(semSaveConfig, value=2)
         @File(config.ini, type='ini')
        "
::= { semConfAlarmEnable 1 }

semConfAlarmEnableGbeInHighBitRate OBJECT-TYPE
    SYNTAX EnableDisableTYPE
    MAX-ACCESS read-write
    STATUS current
    DESCRIPTION
        "This setting enables or disables semAlarmGbeInputStreamHighBitRate.  When set
         to 'enabled' the alarm will operate as described.  When set to 'disabled'
         the alarm will not be reported or wrapped into unitAlarmStatus, and
         semAlarmGbeInputStreamHighBitRate will remain 'ok'.  If semAlarmGbeInputStreamHighBitRate
         is not 'ok' when semConfAlarmEnableGbeInHighBitRate is changed to 'disabled'
         semAlarmGbeInputStreamHighBitRate will be cleared.

         Once written, the change to this parameter will take immediate
         effect.  However, in order for the change to persist through
         subsequent reboots or power cycles, the change must be saved via
         the semSaveConfig parameter.

         @Config(config=yes, reboot=no)
         @Save(semSaveConfig, value=2)
         @File(config.ini, type='ini')
        "
::= { semConfAlarmEnable 2 }


-- ------------------------------------------------------------------------------
--
-- semConfAlarmClear
--

semConfAlarmClearInvalInitData OBJECT-TYPE
    SYNTAX ClearAlarmTYPE
    MAX-ACCESS read-write
    STATUS current
    DESCRIPTION
        "Setting to 'clearAlarm' clears the semAlarmInvalidInitData.
         The SEM will set this parameter back to 'clearAlarmNotInProgress'
         after clearing the alarm.

         Once written, the change to this parameter will take immediate effect.

         @Config(config=no, reboot=no)
        "
::= { semConfAlarmClear 1 }

semConfAlarmClearGbeInStreamLowBitRate OBJECT-TYPE
    SYNTAX ClearAlarmTYPE
    MAX-ACCESS read-write
    STATUS current
    DESCRIPTION
        "Setting to 'clearAlarm' clears the semAlarmGbeInputStreamLowBitRate.
         The SEM will set this parameter back to 'clearAlarmNotInProgress'
         after clearing the alarm.

         This clear will clear all currently active semGbeStatInUdpLowBitRateAlarm.
         After clearing, semAlarmGbeInputStreamLowBitRate will be set for any new
         low bit rate conditions which occur.  The low bit rate conditions that were present
         will not cause semAlarmGbeInputStreamLowBitRate, unless they clear then recur.

         Once written, the change to this parameter will take immediate effect.

         @Config(config=no, reboot=no)
        "
::= { semConfAlarmClear 2 }

semConfAlarmClearGbeMptsRedundThreshold OBJECT-TYPE
    SYNTAX ClearAlarmTYPE
    MAX-ACCESS read-write
    STATUS current
    DESCRIPTION
        "Setting to 'clearAlarm' clears the semAlarmGbeMptsRedundPrimaryThreshold.
         The SEM will set this parameter back to 'clearAlarmNotInProgress'
         after clearing the alarm.

         This clear will clear all currently active semGbeStatInUdpMptsRedundPriAlarm.
         After clearing, semConfAlarmClearGbeMptsRedundThreshold will be set for any new
         Redundancy Threshold conditions which occur.  The Redundancy Threshold conditions
         that were present will not cause semConfAlarmClearGbeMptsRedundThreshold, unless
         they clear then recur.

         Once written, the change to this parameter will take immediate effect.

         @Config(config=no, reboot=no)
        "
::= { semConfAlarmClear 3 }

semConfAlarmClearGbeMptsRedundFailOver OBJECT-TYPE
    SYNTAX ClearAlarmTYPE
    MAX-ACCESS read-write
    STATUS current
    DESCRIPTION
        "Setting to 'clearAlarm' clears the semConfAlarmClearGbeMptsRedundFailOver.
         The SEM will set this parameter back to 'clearAlarmNotInProgress'
         after clearing the alarm.

         This clear will clear all currently active semGbeStatInUdpMptsRedundFailAlarm.
         After clearing, semConfAlarmClearGbeMptsRedundFailOver will be set for any new
         Redundancy Threshold conditions which occur.  The Redundancy Threshold conditions
         that were present will not cause semConfAlarmClearGbeMptsRedundFailOver, unless
         they clear then recur.

         Once written, the change to this parameter will take immediate effect.

         @Config(config=no, reboot=no)
        "
::= { semConfAlarmClear 4 }


-- ------------------------------------------------------------------------------
--
-- semTraps
--

-- ------------------------------------------------------------------------------
--
-- BCS Traps
--
-- Objects are commonly defined but ENTERPRISE is SEM specific.
-- Trap ID starts at 1.  Trap ID 1 and 2 are not issued by the SEM.
--

trapConfigurationChangeInteger NOTIFICATION-TYPE
    OBJECTS
    {
    trapIdentifier,
    trapSequenceId,
    trapNetworkElemModelNumber,
    trapNetworkElemSerialNum,
    trapPerceivedSeverity,
    trapNetworkElemOperState,
    trapNetworkElemAlarmStatus,
    trapNetworkElemAdminState,
    trapNetworkElemAvailStatus,
    trapText,
    trapNETrapLastTrapTimeStamp,
    trapChangedObjectId,
    trapChangedValueInteger
    }
    STATUS current
    DESCRIPTION
        "This trap is issued if configuration of a single variable
         with integer type was changed (via ANY interface).
         TrapChangedValueInteger variable may contain current reading
         of that variable.
         trapPerceivedSeverity - 'indeterminate'"
::= { semTraps 3 }


trapConfigurationChangeDisplayString NOTIFICATION-TYPE
    OBJECTS
    {
    trapIdentifier,
    trapSequenceId,
    trapNetworkElemModelNumber,
    trapNetworkElemSerialNum,
    trapPerceivedSeverity,
    trapNetworkElemOperState,
    trapNetworkElemAlarmStatus,
    trapNetworkElemAdminState,
    trapNetworkElemAvailStatus,
    trapText,
    trapNETrapLastTrapTimeStamp,
    trapChangedObjectId,
    trapChangedValueDisplayString
    }
    STATUS current
    DESCRIPTION
        "This trap is issued if configuration of a single variable
         with DisplayString type was changed (via ANY interface).
         TrapChangedValueDisplayString variable may contain current
         reading of that variable.
         trapPerceivedSeverity - 'indeterminate'"
::= { semTraps 4 }


trapConfigurationChangeOID NOTIFICATION-TYPE
    OBJECTS
    {
    trapIdentifier,
    trapSequenceId,
    trapNetworkElemModelNumber,
    trapNetworkElemSerialNum,
    trapPerceivedSeverity,
    trapNetworkElemOperState,
    trapNetworkElemAlarmStatus,
    trapNetworkElemAdminState,
    trapNetworkElemAvailStatus,
    trapText,
    trapNETrapLastTrapTimeStamp,
    trapChangedObjectId,
    trapChangedValueOID
    }
    STATUS current
    DESCRIPTION
        "This trap is issued if configuration of a single variable
         with OID type was changed (via ANY interface).
         TrapChangedValueOID variable may contain current reading
         of that variable.
         trapPerceivedSeverity - 'indeterminate'"
::= { semTraps 5 }

trapConfigurationChangeIpAddress NOTIFICATION-TYPE
    OBJECTS
    {
    trapIdentifier,
    trapSequenceId,
    trapNetworkElemModelNumber,
    trapNetworkElemSerialNum,
    trapPerceivedSeverity,
    trapNetworkElemOperState,
    trapNetworkElemAlarmStatus,
    trapNetworkElemAdminState,
    trapNetworkElemAvailStatus,
    trapText,
    trapNETrapLastTrapTimeStamp,
    trapChangedObjectId,
    trapChangedValueIpAddress
    }
    STATUS current
    DESCRIPTION
        "This trap is issued if configuration of a single variable
         with IpAddress type was changed (via ANY interface).
         TrapChangedValueIpAddress variable may contain current reading
         of that variable.
         trapPerceivedSeverity - 'indeterminate'"
::= { semTraps 6 }

trapToBeSendQueueOverflow NOTIFICATION-TYPE
    OBJECTS
    {
    trapIdentifier,
    trapSequenceId,
    trapNetworkElemModelNumber,
    trapNetworkElemSerialNum,
    trapPerceivedSeverity,
    trapNetworkElemOperState,
    trapNetworkElemAlarmStatus,
    trapNetworkElemAdminState,
    trapNetworkElemAvailStatus,
    trapText,
    trapNETrapLastTrapTimeStamp
    }
    STATUS current
    DESCRIPTION
        "This trap is issued if SNMP agent's TrapToBeSendQueue is full.
         trapPerceivedSeverity - 'major'
         trapNetworkElemModelNumber - Model # of the Agent
         trapNetworkElemSerialNum - Serial # of the Agent
         trapNetworkElemOperState - from Ident MIB
         trapNetworkElemAlarmStatus - from Ident MIB
         trapNetworkElemAdminState - from Ident MIB
         trapNetworkElemAvailStatus - from Ident MIB"
::= { semTraps 7 }


-- ------------------------------------------------------------------------------
--
-- DNS Traps
--
-- Objects are commonly defined but ENTERPRISE is SEM specific.
-- Trap ID starts at 20.
--

trapConditionNotInList NOTIFICATION-TYPE
    OBJECTS
    {
    trapIdentifier,
    trapSequenceId,
    trapNetworkElemModelNumber,
    trapNetworkElemSerialNum,
    trapPerceivedSeverity,
    trapNetworkElemOperState,
    trapNetworkElemAlarmStatus,
    trapNetworkElemAdminState,
    trapNetworkElemAvailStatus,
    trapText,
    trapNETrapLastTrapTimeStamp,
    trapChangedObjectId,
    trapChangedValueInteger,
    trapAdditionalInfoInteger1,
    trapAdditionalInfoInteger2,
    trapAdditionalInfoInteger3
    }
    STATUS current
    DESCRIPTION
        "This trap is issued if a condition is being cleared and
         it is not in the condition list.
         trapAdditionalInfoInteger1 : Task and Function ID (task
                          and function generates the
                          error condition)
         trapAdditionalInfoInteger2 : Condition number
         trapAdditionalInfoInteger3 : Condition severity"
::= { semTraps 20 }

trapConditionAlreadyInList NOTIFICATION-TYPE
    OBJECTS
    {
    trapIdentifier,
    trapSequenceId,
    trapNetworkElemModelNumber,
    trapNetworkElemSerialNum,
    trapPerceivedSeverity,
    trapNetworkElemOperState,
    trapNetworkElemAlarmStatus,
    trapNetworkElemAdminState,
    trapNetworkElemAvailStatus,
    trapText,
    trapNETrapLastTrapTimeStamp,
    trapChangedObjectId,
    trapChangedValueInteger,
    trapAdditionalInfoInteger1,
    trapAdditionalInfoInteger2,
    trapAdditionalInfoInteger3
    }
    STATUS current
    DESCRIPTION
        "This trap is issued if a condition is being set and
         it is already in the condition list.
         trapAdditionalInfoInteger1 : Task and Function ID (task
                          and function generates the
                          error condition)
         trapAdditionalInfoInteger2 : Condition number
         trapAdditionalInfoInteger3 : Condition severity"
::= { semTraps 21 }

trapConditionListFull NOTIFICATION-TYPE
    OBJECTS
    {
    trapIdentifier,
    trapSequenceId,
    trapNetworkElemModelNumber,
    trapNetworkElemSerialNum,
    trapPerceivedSeverity,
    trapNetworkElemOperState,
    trapNetworkElemAlarmStatus,
    trapNetworkElemAdminState,
    trapNetworkElemAvailStatus,
    trapText,
    trapNETrapLastTrapTimeStamp,
    trapChangedObjectId,
    trapChangedValueInteger,
    trapAdditionalInfoInteger1,
    trapAdditionalInfoInteger2,
    trapAdditionalInfoInteger3
    }
    STATUS current
    DESCRIPTION
        "This trap is issued if a condition is being set and
         the condition list is full.
         trapAdditionalInfoInteger1 : Task and Function ID (task
                          and function generates the
                          error condition)
         trapAdditionalInfoInteger2 : Condition number
         trapAdditionalInfoInteger3 : Condition severity"
::= { semTraps 22 }

trapInvalidCaseInSwitch NOTIFICATION-TYPE
    OBJECTS
    {
    trapIdentifier,
    trapSequenceId,
    trapNetworkElemModelNumber,
    trapNetworkElemSerialNum,
    trapPerceivedSeverity,
    trapNetworkElemOperState,
    trapNetworkElemAlarmStatus,
    trapNetworkElemAdminState,
    trapNetworkElemAvailStatus,
    trapText,
    trapNETrapLastTrapTimeStamp,
    trapChangedObjectId,
    trapChangedValueInteger,
    trapAdditionalInfoInteger1,
    trapAdditionalInfoInteger2,
    trapAdditionalInfoInteger3
    }
    STATUS current
    DESCRIPTION
        "This trap is issued when in a switch statement the
         default case is reached.  The trapAdditionalInfoInteger1
         will contain the task and Function ID.  The
         trapAdditionalInfoInteger2 will contain value of the switch.
         The trapAdditionalInfoInteger3 is not used."
::= { semTraps 23 }

trapCannotCreateSemaphore NOTIFICATION-TYPE
    OBJECTS
    {
    trapIdentifier,
    trapSequenceId,
    trapNetworkElemModelNumber,
    trapNetworkElemSerialNum,
    trapPerceivedSeverity,
    trapNetworkElemOperState,
    trapNetworkElemAlarmStatus,
    trapNetworkElemAdminState,
    trapNetworkElemAvailStatus,
    trapText,
    trapNETrapLastTrapTimeStamp,
    trapChangedObjectId,
    trapChangedValueInteger,
    trapAdditionalInfoInteger1,
    trapAdditionalInfoInteger2,
    trapAdditionalInfoInteger3
    }
    STATUS current
    DESCRIPTION
        "This trap is issued when a semaphore cannot
         be created. The trapAdditionalInfoInteger1 will contain the
         task and Function ID, the trapAdditionalInfoInteger2 and
         trapAdditionalInfoInteger3 will not be used."
::= { semTraps 24 }

trapCannotOpenSocket NOTIFICATION-TYPE
    OBJECTS
    {
    trapIdentifier,
    trapSequenceId,
    trapNetworkElemModelNumber,
    trapNetworkElemSerialNum,
    trapPerceivedSeverity,
    trapNetworkElemOperState,
    trapNetworkElemAlarmStatus,
    trapNetworkElemAdminState,
    trapNetworkElemAvailStatus,
    trapText,
    trapNETrapLastTrapTimeStamp,
    trapChangedObjectId,
    trapChangedValueInteger,
    trapAdditionalInfoInteger1,
    trapAdditionalInfoInteger2,
    trapAdditionalInfoInteger3
    }
    STATUS current
    DESCRIPTION
        "This trap is issued when a socket cannot
         be opened. The trapAdditionalInfoInteger1 will contain the
         task and Function ID. The trapAdditionalInfoInteger2 will
         contain the errno returned by the call to socket(). The
         trapAdditionalInfoInteger3 is not used."
::= { semTraps 25 }

trapUnknownMessageReceived NOTIFICATION-TYPE
    OBJECTS
    {
    trapIdentifier,
    trapSequenceId,
    trapNetworkElemModelNumber,
    trapNetworkElemSerialNum,
    trapPerceivedSeverity,
    trapNetworkElemOperState,
    trapNetworkElemAlarmStatus,
    trapNetworkElemAdminState,
    trapNetworkElemAvailStatus,
    trapText,
    trapNETrapLastTrapTimeStamp,
    trapChangedObjectId,
    trapChangedValueInteger,
    trapAdditionalInfoInteger1,
    trapAdditionalInfoInteger2,
    trapAdditionalInfoInteger3
    }
    STATUS current
    DESCRIPTION
        "This trap is issued when an unknown message
         is received.  The trapAdditionalInfoInteger1 will contain the
         task and Function ID. The trapAdditionalInfoInteger2 will
         contain the message ID and the trapAdditionalInfoInteger3 is
         not used."
::= { semTraps 26 }

trapInvalidMessageReceived NOTIFICATION-TYPE
    OBJECTS
    {
    trapIdentifier,
    trapSequenceId,
    trapNetworkElemModelNumber,
    trapNetworkElemSerialNum,
    trapPerceivedSeverity,
    trapNetworkElemOperState,
    trapNetworkElemAlarmStatus,
    trapNetworkElemAdminState,
    trapNetworkElemAvailStatus,
    trapText,
    trapNETrapLastTrapTimeStamp,
    trapChangedObjectId,
    trapChangedValueInteger,
    trapAdditionalInfoInteger1,
    trapAdditionalInfoInteger2,
    trapAdditionalInfoInteger3
    }
    STATUS current
    DESCRIPTION
        "This trap is issued when an invalid message
         is received.  The trapAdditionalInfoInteger1 will contain the
         task and Function ID. The trapAdditionalInfoInteger2 will
         contain the message ID and the trapAdditionalInfoInteger3 is
         not used."
::= { semTraps 27 }


-- ------------------------------------------------------------------------------
--
-- SEM Alarm Traps
--
-- Trap ID starts at 8000.
--

trapHardwareFault NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm semAlarmHardwareFault.
         Additional Info is not used."
::= { semTraps 8000 }

trapInvalidInitData NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm semAlarmInvalidInitData.
         Additional Info is not used."
::= { semTraps 8001 }

trapZeroSystemTime NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm semAlarmZeroSystemTime.
         Additional Info is not used."
::= { semTraps 8002 }

trapMissingTimeUpdate NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm semAlarmMissingTimeUpdate.
         Additional Info is not used."
::= { semTraps 8003 }

trapCommandTableEmpty NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm semAlarmCommandTableEmpty.
         Additional Info is not used."
::= { semTraps 8004 }

trapCommandTableNearFull NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm semAlarmCommandTableNearFull.
         Additional Info is not used."
::= { semTraps 8005 }

trapServiceInError NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm semAlarmServiceInError.
         Additional Info is not used."
::= { semTraps 8006 }

trapWaitingForExtractedMessage NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm semAlarmWaitingForExtractedMessage.
         Additional Info is not used."
::= { semTraps 8007 }

trapLossOfPhysicalInput NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm semAlarmLossOfPhysicalInput.
         Additional Info is not used."
::= { semTraps 8008 }

trapServiceNotAuthorized NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm semAlarmServiceNotAuthorized.
         Additional Info is not used."
::= { semTraps 8009 }

trapTemperatureFault NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm semAlarmTemperatureFault.
         Additional Info is not used."
::= { semTraps 8010 }

trapFanFault NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm semAlarmFanFault.
         Additional Info is not used."
::= { semTraps 8011 }

trapGigeFailOver NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm semAlarmGigeFailOver.
         Additional Info is not used."
::= { semTraps 8012 }

trapOtsUtilizationFault NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm semAlarmOtsUtilizationFault.
         Additional Info is not used."
::= { semTraps 8013 }

trapGigeRedundantModeThreshold NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm semAlarmGigeRedundantModeThreshold.
         Additional Info is not used."
::= { semTraps 8014 }

trapSimulcryptCommunicationFault NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm semAlarmSimulcryptCommunicationFault.
         Additional Info is not used."
::= { semTraps 8015 }

trapQamFault NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm semAlarmQamFault.
         Additional Info is not used."
::= { semTraps 8016 }

trapUpconverterFault NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm semAlarmUpconverterFault.
         Additional Info is not used."
::= { semTraps 8017 }

trapOtsHostIpOverflow NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm semAlarmOtsHostIpOverflow.
         Additional Info is not used."
::= { semTraps 8018 }

trapOtsOverflow NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm semAlarmOtsOverflow.
         Additional Info is not used."
::= { semTraps 8019 }

trapIceEmmServerCommFailure NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm semAlarmIceEmmServerCommFailure.
         Additional Info is not used."
::= { semTraps 8020 }

trapIceEmmServerInvalidResponse NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm semAlarmIceEmmServerInvalidResponse.
         Additional Info is not used."
::= { semTraps 8021 }

trapIceFullEncryptFailure NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm semAlarmIceFullEncryptFailure.
         Additional Info is not used."
::= { semTraps 8022 }

trapQamPortFault NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm semAlarmQamPortFault.

         This trap is sent on a QAM Port basis.

         Additional Info 1 carries the QAM Port Number.
         Additional Info 2 carries the value of semQamStatusPortError for this QAM Port.
         Additional Info 3 carries the value of semOutTransStatusOverflow for the
         Output Transport Stream associated with this QAM Port."
::= { semTraps 8023 }

trapGbeBufferFullness NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm semAlarmGbeBufferFullness.
         Additional Info is not used."
::= { semTraps 8024 }

trapGbeInputStreamLowBitRate NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm semAlarmGbeInputStreamLowBitRate.

         This trap is sent on a configured UDP Port basis.

         Additional Info 1 carries the semGbeInputUdpConfigTable index.
         Additional Info 2 carries the GBE Interface Port Number.
         Additional Info 3 carries the GBE UDP Port Number.
        "
::= { semTraps 8025 }

trapGbeMptsRedundPrimaryThreshold NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm semAlarmGbeMptsRedundPrimaryThreshold.

         This trap is sent on a configured UDP Port basis.

         Additional Info 1 carries the semGbeInputUdpConfigTable index.
         Additional Info 2 carries the GBE Interface Port Number.
         Additional Info 3 carries the GBE UDP Port Number.
        "
::= { semTraps 8026 }

trapGbeMptsRedundFailOver NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm semAlarmGbeMptsRedundFailOver.

         This trap is sent on a configured UDP Port basis.

         Additional Info 1 carries the semGbeInputUdpConfigTable index.
         Additional Info 2 carries the GBE Interface Port Number.
         Additional Info 3 carries the GBE UDP Port Number.
        "
::= { semTraps 8027 }

trapGbeInputStreamHighBitRate NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm semAlarmGbeInputStreamHighBitRate.

         This trap is sent on a configured UDP Port basis.

         Additional Info 1 carries the semGbeInputUdpConfigTable index.
         Additional Info 2 carries the GBE Interface Port Number.
         Additional Info 3 carries the GBE UDP Port Number.
        "
::= { semTraps 8028 }


-- ------------------------------------------------------------------------------
--
-- SEM Event Traps
--
-- Trap ID starts at 8100.
--

trapHardwareError NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding event semEventHardwareError.
         Additional Info 1 carries the configuration error code."
::= { semTraps 8100 }

trapInvalidInitDataError NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding event semEventInvalidInitDataError.
         Additional Info is not used."
::= { semTraps 8101 }

trapInvalidConfigDataError NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding event semEventInvalidConfigDataError.
         Additional Info is not used."
::= { semTraps 8102 }

trapLoadDeviceError NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding event semEventLoadDeviceError.
         Additional Info 1 carries the error code."
::= { semTraps 8103 }

trapPhysicalInputError NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding event semEventPhysicalInputError.
         Additional Info 1 carries the physical interface type code GBE=1, ASI=2.
         Additional Info 2 carries the physical interface number GBE=1-3, ASI=1-8."
::= { semTraps 8104 }

trapOtsUtilizationError NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding event semEventOtsUtilizationError.
         Additional Info 1 carries the Output Transport Stream Number."
::= { semTraps 8105 }

trapGbeBufferReset NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding event semEventGbeBufferReset.
         Additional Info is not used."
::= { semTraps 8106 }

trapEmUserLoginFailed NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding event semEventEmUserLoginFailed.
         Additional Info is not used."
::= { semTraps 8107 }

trapEmNewControllerObserved NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding event semEventNewControllerObserved.
         Additional Info 1 carries the GPS system time.
         Additional Info 2 carries the IP address in integer rather than
         string format.
         Additional Info 3 carries the IP port."
::= { semTraps 8108 }


-- ------------------------------------------------------------------------------
END
