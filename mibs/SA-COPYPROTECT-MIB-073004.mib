--
-- SA-COPYPROTECT-MIB.mib
-- MIB generated by MG-SOFT Visual MIB Builder Version 4.0 Build 349
-- Tuesday, February 08, 2005 at 09:59:32
--

-- Revision 1 : Initial Public Release
-- Date: Friday, July 30, 2004 at 10:45:57
-- Comment:
-- Initial public release of this module
-- 
	SA-COPYPROTECT-MIB DEFINITIONS ::= BEGIN
 
		IMPORTS
			sa1394DeviceIndex, sa1394DevConnMapIndex			
				FROM SA-1394-MIB			
			saCProtectMib			
				FROM SA-DBDSGEN-MIB			
			saModules			
				FROM SCIATL-COMMON-MIB			
			OBJECT-GROUP			
				FROM SNMPv2-CONF			
			Integer32, Unsigned32, OBJECT-TYPE, MODULE-IDENTITY, OBJECT-IDENTITY			
				FROM SNMPv2-SMI			
			TruthValue, DisplayString, TEXTUAL-CONVENTION			
				FROM SNMPv2-TC;
	
	
		-- 1.3.6.1.4.1.1429.7.1.23
		saCProtectMibModule MODULE-IDENTITY 
			LAST-UPDATED "200407301045Z"		-- July 30, 2004 at 10:45 GMT
			ORGANIZATION 
				"Scientific-Atlanta"
			CONTACT-INFO 
				"DBDS Software Engineering & Architecture
				Scientific-Atlanta
				5030 Sugarloaf Parkway
				Lawrenceville, GA 30044
				"
			DESCRIPTION 
				"Scientific-Atlanta MIB module for Copy Protection.
				
				
				This MIB module Copyright 2003-2005 Scientific-Atlanta"
			REVISION "200502080958Z"		-- February 08, 2005 at 09:58 GMT
			DESCRIPTION 
				"Added Broadcast Flag to CciEventData."
			REVISION "200407301045Z"		-- July 30, 2004 at 10:45 GMT
			DESCRIPTION 
				"Initial public release of this module"
			::= { saModules 23 }

		
	
--
-- Textual conventions
--
	
		CciEventData ::= TEXTUAL-CONVENTION
			STATUS current
			DESCRIPTION 
				"This type describes a CCI Event.
				
				Bit 0 below is the LSBit of the Integer32.
				
				Bit     Definition       Description
				------  ---------------  -----------
				0..1    EMI              00 = Copy Freely
				                         01 = Copy No More
				                         10 = Copy Once
				                         11 = Copy Never
				
				2..3    APS              00 = APS Disabled
				                         01 = APS Split Burst Off
				                         10 = APS 2 Line Split Burst Off
				                         11 = APS 4 Line Split Burst Off
				
				4..4    CIT              1 = Constrained Image Trigger
				
				5..5    EPN              1 = Encryption Plus Non Assertion
				
				6..7    Reserved         Reserved for future expansion
				
				8..8    BroadcastFlag    1 = Redistribution Control Descriptor
				
				9..31   Reserved         Reserved for future expansion"
			SYNTAX Integer32

	
--
-- Node definitions
--
	
		-- 1.3.6.1.4.1.1429.9.1.14.1
		saCProtectConf OBJECT-IDENTITY
			STATUS current
			DESCRIPTION 
				"Conformance"
			::= { saCProtectMib 1 }

		
		-- 1.3.6.1.4.1.1429.9.1.14.1.1
		saCProtectGroups OBJECT-IDENTITY
			STATUS current
			DESCRIPTION 
				"Object Groups of the SA-COPYPROTECT-MIB"
			::= { saCProtectConf 1 }

		
		-- 1.3.6.1.4.1.1429.9.1.14.1.1.1
		saCProtectPolicyHdmiGroup OBJECT-GROUP
			OBJECTS { saCProtectPolicyHdmiPolicy1 }
			STATUS deprecated
			DESCRIPTION 
				"deprecated - The group for HDMI copy protection policy."
			::= { saCProtectGroups 1 }

		
-- The group for Y-Pr-Pb copy protection policy.
		-- 1.3.6.1.4.1.1429.9.1.14.1.1.2
		saCProtectPolicyYPrPbGroup OBJECT-GROUP
			OBJECTS { saCProtectPolicyYPrPbPolicy1 }
			STATUS deprecated
			DESCRIPTION 
				"deprecated - The group for Y-Pr-Pb copy protection policy."
			::= { saCProtectGroups 2 }

		
		-- 1.3.6.1.4.1.1429.9.1.14.1.1.3
		saCProtectPolicy1394Group OBJECT-GROUP
			OBJECTS { saCProtectPolicy1394Policy1 }
			STATUS deprecated
			DESCRIPTION 
				"deprecated - The group for 1394 copy protection policy."
			::= { saCProtectGroups 3 }

		
		-- 1.3.6.1.4.1.1429.9.1.14.1.1.4
		saCProtectPolicyCompositeGroup OBJECT-GROUP
			OBJECTS { saCProtectPolicyCompositePolicy1 }
			STATUS deprecated
			DESCRIPTION 
				"deprecated - The group for Composite copy protection policy."
			::= { saCProtectGroups 4 }

		
		-- 1.3.6.1.4.1.1429.9.1.14.1.1.5
		saCProtectPolicyVodGroup OBJECT-GROUP
			OBJECTS { saCProtectPolicyVodPolicy1 }
			STATUS deprecated
			DESCRIPTION 
				"deprecated - The group for Composite copy protection policy."
			::= { saCProtectGroups 5 }

		
		-- 1.3.6.1.4.1.1429.9.1.14.1.1.6
		saCProtectOutHdmiTableGroup OBJECT-GROUP
			OBJECTS { saCProtectOutHdmiPortEnabled, saCProtectOutHdmiConstrained, saCProtectOutHdmiHdcpEnabled }
			STATUS current
			DESCRIPTION 
				"The group for the saCProtectOutHdmiTable."
			::= { saCProtectGroups 6 }

		
		-- 1.3.6.1.4.1.1429.9.1.14.1.1.7
		saCProtectOutYPrPbTableGroup OBJECT-GROUP
			OBJECTS { saCProtectOutYPrPbPortEnabled, saCProtectOutYPrPbConstrained, saCProtectOutYPrPbMacrovisionEnabled }
			STATUS current
			DESCRIPTION 
				"The group for the saCProtectOutYPrPbTable."
			::= { saCProtectGroups 7 }

		
		-- 1.3.6.1.4.1.1429.9.1.14.1.1.8
		saCProtectOut1394TableGroup OBJECT-GROUP
			OBJECTS { saCProtectOut1394ConnectionEnabled, saCProtectOut1394DtcpEnabled }
			STATUS current
			DESCRIPTION 
				"The group for the saCProtectOut1394Table."
			::= { saCProtectGroups 8 }

		
		-- 1.3.6.1.4.1.1429.9.1.14.1.1.9
		sasCProtectGenCciEvtLogTableGroup OBJECT-GROUP
			OBJECTS { saCProtectGenCciEvtLogSrcPortDescr, saCProtectGenCciEvtLogDstPortDescr, saCProtectGenCciEvtLogCciData }
			STATUS current
			DESCRIPTION 
				"The group for the sasCProtectGenCciEvtLogTable."
			::= { saCProtectGroups 9 }

		
		-- 1.3.6.1.4.1.1429.9.1.14.1.1.10
		saCProtectOutCompositeTableGroup OBJECT-GROUP
			OBJECTS { saCProtectOutCompositeMacrovisionEnabled }
			STATUS current
			DESCRIPTION 
				"The group for the saCProtectOutCompositeTable."
			::= { saCProtectGroups 10 }

		
		-- 1.3.6.1.4.1.1429.9.1.14.1.1.11
		saCProtectPolicyHdmiV2Group OBJECT-GROUP
			OBJECTS { saCProtectPolicyHdmiPolicy1, saCprotectPolicyHdmiFormatVersion }
			STATUS current
			DESCRIPTION 
				"The group for HDMI copy protection policy."
			::= { saCProtectGroups 11 }

		
-- The group for Y-Pr-Pb copy protection policy.
		-- 1.3.6.1.4.1.1429.9.1.14.1.1.12
		saCProtectPolicyYPrPbV2Group OBJECT-GROUP
			OBJECTS { saCProtectPolicyYPrPbPolicy1, saCprotectPolicyYPrPbFormatVersion }
			STATUS current
			DESCRIPTION 
				"The group for Y-Pr-Pb copy protection policy."
			::= { saCProtectGroups 12 }

		
		-- 1.3.6.1.4.1.1429.9.1.14.1.1.13
		saCProtectPolicy1394V2Group OBJECT-GROUP
			OBJECTS { saCProtectPolicy1394Policy1, saCprotectPolicy1394FormatVersion }
			STATUS current
			DESCRIPTION 
				"The group for 1394 copy protection policy."
			::= { saCProtectGroups 13 }

		
		-- 1.3.6.1.4.1.1429.9.1.14.1.1.14
		saCProtectPolicyCompositeV2Group OBJECT-GROUP
			OBJECTS { saCProtectPolicyCompositePolicy1, saCprotectPolicyCompositeFormatVersion }
			STATUS current
			DESCRIPTION 
				"The group for Composite copy protection policy."
			::= { saCProtectGroups 14 }

		
		-- 1.3.6.1.4.1.1429.9.1.14.1.1.15
		saCProtectPolicyVodV2Group OBJECT-GROUP
			OBJECTS { saCProtectPolicyVodPolicy1, saCprotectPolicyVodFormatVersion }
			STATUS current
			DESCRIPTION 
				"The group for VOD copy protection policy."
			::= { saCProtectGroups 15 }

		
		-- 1.3.6.1.4.1.1429.9.1.14.1.1.16
		saCProtectOut1394CitEpnTableGroup OBJECT-GROUP
			OBJECTS { saCProtectOut1394CitEpnCit, saCProtectOut1394CitEpnEpn }
			STATUS current
			DESCRIPTION 
				"The group for saCProtectOut1394CitEpnTable"
			::= { saCProtectGroups 16 }

		
		-- 1.3.6.1.4.1.1429.9.1.14.1.2
		saCProtectCompls OBJECT-IDENTITY
			STATUS current
			DESCRIPTION 
				"Compliances of the SA-COPYPROTECT-MIB"
			::= { saCProtectConf 2 }

		
		-- 1.3.6.1.4.1.1429.9.1.14.2
		saCProtectObjs OBJECT-IDENTITY
			STATUS current
			DESCRIPTION 
				"The MIB Objects defined for the SA-COPYPROTECT-MIB module."
			::= { saCProtectMib 2 }

		
		-- 1.3.6.1.4.1.1429.9.1.14.2.1
		saCProtectPolicy OBJECT-IDENTITY
			STATUS current
			DESCRIPTION 
				"This group provides information regarding the copy protection
				policies in effect on the agent."
			::= { saCProtectObjs 1 }

		
		-- 1.3.6.1.4.1.1429.9.1.14.2.1.1
		saCProtectPolicyHdmi OBJECT-IDENTITY
			STATUS current
			DESCRIPTION 
				"Copy Control policy for HDMI ports:"
			::= { saCProtectPolicy 1 }

		
		-- 1.3.6.1.4.1.1429.9.1.14.2.1.1.1
		saCProtectPolicyHdmiPolicy1 OBJECT-TYPE
			SYNTAX Integer32
			MAX-ACCESS read-only
			STATUS current
			DESCRIPTION
				"Copy Control policy for HDMI ports:
				
				The interpretation of this object depends on the value of saCProtectPolicyHdmiFormatVersion.
				
				:::For format version 1:::
				
				Bit 0 below is the LSBit of the Integer32.
				
				Bits	Meaning
				0	1: Disable (block) HDMI port at all times
				1	1: Output a constrained image to HDMI port when  HDCP authentication fails
				2	1: Block output to HDMI port when HDCP authentication fails
				3-4	00: Use HDCP if EMI is NOT 'copy freely',  or CIT bit is set
					01: Always use HDCP 
					10: Never use HDCP
				5-31	Reserved
				"
			::= { saCProtectPolicyHdmi 1 }

		
		-- 1.3.6.1.4.1.1429.9.1.14.2.1.1.2
		saCprotectPolicyHdmiFormatVersion OBJECT-TYPE
			SYNTAX Integer32
			MAX-ACCESS read-only
			STATUS current
			DESCRIPTION
				"The format version number for HDMI policy.
				This number is the key for interpreting the values reported in 
				the other policy objects within saCProtectPolicyHdmi.
				
				
				Format Version    Applicable Policy Objects
				--------------    -------------------------
				      1           sasCProtectPolicyHdmiPolicy1
				"
			::= { saCProtectPolicyHdmi 2 }

		
		-- 1.3.6.1.4.1.1429.9.1.14.2.1.2
		saCProtectPolicyYPrPb OBJECT-IDENTITY
			STATUS current
			DESCRIPTION 
				"Copy Control policy for Y-Pr-Pb ports:
				"
			::= { saCProtectPolicy 2 }

		
		-- 1.3.6.1.4.1.1429.9.1.14.2.1.2.1
		saCProtectPolicyYPrPbPolicy1 OBJECT-TYPE
			SYNTAX Integer32
			MAX-ACCESS read-only
			STATUS current
			DESCRIPTION
				"Copy Control policy for Y-Pr-Pb ports:
				
				The interpretation of this object depends on the value of saCProtectPolicyYPrPbFormatVersion.
				
				:::For format version 1:::
				
				Bit 0 below is the LSBit of the Integer32.
				
				Bits	Meaning
				0	1: Disable (block) Y-Pr-Pb port at all times
				1	1: Output a constrained image to Y-Pr-Pb port when CIT bit is set
				2	1: Block output to Y-Pr-Pb port when CIT bit is set
				3	1: Enable Macrovision for Y-Pr-Pb port when enabled on composite outputs
				4-31	Reserved
				"
			::= { saCProtectPolicyYPrPb 1 }

		
		-- 1.3.6.1.4.1.1429.9.1.14.2.1.2.2
		saCprotectPolicyYPrPbFormatVersion OBJECT-TYPE
			SYNTAX Integer32
			MAX-ACCESS read-only
			STATUS current
			DESCRIPTION
				"The format version number for YPrPb policy.
				This number is the key for interpreting the values reported in 
				the other policy objects within saCProtectPolicyYPrPb.
				
				
				Format Version    Applicable Policy Objects
				--------------    -------------------------
				      1           sasCProtectPolicyYPrPbPolicy1
				"
			::= { saCProtectPolicyYPrPb 2 }

		
		-- 1.3.6.1.4.1.1429.9.1.14.2.1.3
		saCProtectPolicy1394 OBJECT-IDENTITY
			STATUS current
			DESCRIPTION 
				"Copy Control policy for 1394 ports"
			::= { saCProtectPolicy 3 }

		
		-- 1.3.6.1.4.1.1429.9.1.14.2.1.3.1
		saCProtectPolicy1394Policy1 OBJECT-TYPE
			SYNTAX Integer32
			MAX-ACCESS read-only
			STATUS current
			DESCRIPTION
				"Copy Control policy for 1394 ports:
				
				The interpretation of this object depends on the value of saCProtectPolicy1394FormatVersion.
				
				:::For format version 1:::
				
				Bit 0 below is the LSBit of the Integer32.
				
				
				Bits	Meaning
				0	1: Disable (block) 1394 port at all times
				1-31	Reserved
				"
			::= { saCProtectPolicy1394 1 }

		
		-- 1.3.6.1.4.1.1429.9.1.14.2.1.3.2
		saCprotectPolicy1394FormatVersion OBJECT-TYPE
			SYNTAX Integer32
			MAX-ACCESS read-only
			STATUS current
			DESCRIPTION
				"The format version number for 1394 policy.
				This number is the key for interpreting the values reported in 
				the other policy objects within saCProtectPolicy1394.
				
				
				Format Version    Applicable Policy Objects
				--------------    -------------------------
				      1           sasCProtectPolicy1394Policy1
				"
			::= { saCProtectPolicy1394 2 }

		
		-- 1.3.6.1.4.1.1429.9.1.14.2.1.4
		saCProtectPolicyComposite OBJECT-IDENTITY
			STATUS current
			DESCRIPTION 
				"Copy Control policy for composite outputs"
			::= { saCProtectPolicy 4 }

		
		-- 1.3.6.1.4.1.1429.9.1.14.2.1.4.1
		saCProtectPolicyCompositePolicy1 OBJECT-TYPE
			SYNTAX Integer32
			MAX-ACCESS read-only
			STATUS current
			DESCRIPTION
				"Copy Control policy for composite outputs:
				
				
				The interpretation of this object depends on the value of 
				saCProtectPolicyCompositeFormatVersion.
				
				:::For format version 1:::
				
				Bit 0 below is the LSBit of the Integer32.
				
				Bits	Meaning
				0-31	Reserved
				"
			::= { saCProtectPolicyComposite 1 }

		
		-- 1.3.6.1.4.1.1429.9.1.14.2.1.4.2
		saCprotectPolicyCompositeFormatVersion OBJECT-TYPE
			SYNTAX Integer32
			MAX-ACCESS read-only
			STATUS current
			DESCRIPTION
				"The format version number for Composite policy.
				This number is the key for interpreting the values reported in 
				the other policy objects within saCProtectPolicyComposite.
				
				
				Format Version    Applicable Policy Objects
				--------------    -------------------------
				      1           sasCProtectPolicyCompositePolicy1
				"
			::= { saCProtectPolicyComposite 2 }

		
		-- 1.3.6.1.4.1.1429.9.1.14.2.1.5
		saCProtectPolicyVod OBJECT-IDENTITY
			STATUS current
			DESCRIPTION 
				"Copy Control policy for VOD"
			::= { saCProtectPolicy 5 }

		
		-- 1.3.6.1.4.1.1429.9.1.14.2.1.5.1
		saCProtectPolicyVodPolicy1 OBJECT-TYPE
			SYNTAX TruthValue
			MAX-ACCESS read-only
			STATUS current
			DESCRIPTION
				"Copy Control policy for VOD concerning CCI Override.
				
				If True, then CCI Override.
				If false, then no CCI Override
				"
			::= { saCProtectPolicyVod 1 }

		
		-- 1.3.6.1.4.1.1429.9.1.14.2.1.5.2
		saCprotectPolicyVodFormatVersion OBJECT-TYPE
			SYNTAX Integer32
			MAX-ACCESS read-only
			STATUS current
			DESCRIPTION
				"The format version number for VOD policy.
				This number is the key for interpreting the values reported in 
				the other policy objects within saCProtectPolicyVod.
				
				
				Format Version    Applicable Policy Objects
				--------------    -------------------------
				      1           sasCProtectPolicyVodPolicy1
				"
			::= { saCProtectPolicyVod 2 }

		
		-- 1.3.6.1.4.1.1429.9.1.14.2.2
		saCProtectOut OBJECT-IDENTITY
			STATUS current
			DESCRIPTION 
				"Current Output Port Characteristics related to copy control"
			::= { saCProtectObjs 2 }

		
		-- 1.3.6.1.4.1.1429.9.1.14.2.2.1
		saCProtectOutHdmiTable OBJECT-TYPE
			SYNTAX SEQUENCE OF SaCProtectOutHdmiEntry
			MAX-ACCESS not-accessible
			STATUS current
			DESCRIPTION
				"This table represents the copy control-related characteristics
				of HDMI output ports on the host.
				
				An entry exists for each HDMI output port on the host. If an
				entry in this table corresponds to an entry in hrDeviceTable
				from the HOST-RESOURCES-MIB, then the index value for this table
				must match the corresponding hrDeviceIndex."
			::= { saCProtectOut 1 }

		
		-- 1.3.6.1.4.1.1429.9.1.14.2.2.1.1
		saCProtectOutHdmiEntry OBJECT-TYPE
			SYNTAX SaCProtectOutHdmiEntry
			MAX-ACCESS not-accessible
			STATUS current
			DESCRIPTION
				"An entry in the table.
				
				
				An entry exists for each HDMI output port on the host. If an
				entry in this table corresponds to an entry in hrDeviceTable
				from the HOST-RESOURCES-MIB, then the index value for this table
				must match the corresponding hrDeviceIndex."
			INDEX { saCProtectOutHdmiIndex }
			::= { saCProtectOutHdmiTable 1 }

		
		SaCProtectOutHdmiEntry ::=
			SEQUENCE { 
				saCProtectOutHdmiIndex
					Integer32,
				saCProtectOutHdmiPortEnabled
					TruthValue,
				saCProtectOutHdmiConstrained
					TruthValue,
				saCProtectOutHdmiHdcpEnabled
					TruthValue
			 }

		-- 1.3.6.1.4.1.1429.9.1.14.2.2.1.1.1
		saCProtectOutHdmiIndex OBJECT-TYPE
			SYNTAX Integer32 (1..2147483647)
			MAX-ACCESS not-accessible
			STATUS current
			DESCRIPTION
				"A unique value for this entry.
				
				If an entry in this table corresponds to an entry in hrDeviceTable
				from the HOST-RESOURCES-MIB, then this index value
				must match the corresponding hrDeviceIndex."
			::= { saCProtectOutHdmiEntry 1 }

		
		-- 1.3.6.1.4.1.1429.9.1.14.2.2.1.1.2
		saCProtectOutHdmiPortEnabled OBJECT-TYPE
			SYNTAX TruthValue
			MAX-ACCESS read-only
			STATUS current
			DESCRIPTION
				"Indicates if the port is enabled for output."
			::= { saCProtectOutHdmiEntry 2 }

		
		-- 1.3.6.1.4.1.1429.9.1.14.2.2.1.1.3
		saCProtectOutHdmiConstrained OBJECT-TYPE
			SYNTAX TruthValue
			MAX-ACCESS read-only
			STATUS current
			DESCRIPTION
				"Indicates if the output is constrained."
			::= { saCProtectOutHdmiEntry 3 }

		
		-- 1.3.6.1.4.1.1429.9.1.14.2.2.1.1.4
		saCProtectOutHdmiHdcpEnabled OBJECT-TYPE
			SYNTAX TruthValue
			MAX-ACCESS read-only
			STATUS current
			DESCRIPTION
				"Indicates that HDCP is enabled for the port."
			::= { saCProtectOutHdmiEntry 4 }

		
		-- 1.3.6.1.4.1.1429.9.1.14.2.2.2
		saCProtectOutYPrPbTable OBJECT-TYPE
			SYNTAX SEQUENCE OF SaCProtectOutYPrPbEntry
			MAX-ACCESS not-accessible
			STATUS current
			DESCRIPTION
				"This table represents the copy control-related characteristics
				of Y-Pr-Pb output ports on the host.
				
				An entry exists for each Y-Pr-Pb output port on the host. If an
				entry in this table corresponds to an entry in hrDeviceTable
				from the HOST-RESOURCES-MIB, then the index value for this table
				must match the corresponding hrDeviceIndex."
			::= { saCProtectOut 2 }

		
		-- 1.3.6.1.4.1.1429.9.1.14.2.2.2.1
		saCProtectOutYPrPbEntry OBJECT-TYPE
			SYNTAX SaCProtectOutYPrPbEntry
			MAX-ACCESS not-accessible
			STATUS current
			DESCRIPTION
				"An entry in the table.
				
				
				An entry exists for each Y-Pr-Pb output port on the host. If an
				entry in this table corresponds to an entry in hrDeviceTable
				from the HOST-RESOURCES-MIB, then the index value for this table
				must match the corresponding hrDeviceIndex."
			INDEX { saCProtectOutYPrPbIndex }
			::= { saCProtectOutYPrPbTable 1 }

		
		SaCProtectOutYPrPbEntry ::=
			SEQUENCE { 
				saCProtectOutYPrPbIndex
					Integer32,
				saCProtectOutYPrPbPortEnabled
					TruthValue,
				saCProtectOutYPrPbConstrained
					TruthValue,
				saCProtectOutYPrPbMacrovisionEnabled
					TruthValue
			 }

		-- 1.3.6.1.4.1.1429.9.1.14.2.2.2.1.1
		saCProtectOutYPrPbIndex OBJECT-TYPE
			SYNTAX Integer32 (1..2147483647)
			MAX-ACCESS not-accessible
			STATUS current
			DESCRIPTION
				"A unique value for this entry.
				
				If an entry in this table corresponds to an entry in hrDeviceTable
				from the HOST-RESOURCES-MIB, then this index value
				must match the corresponding hrDeviceIndex."
			::= { saCProtectOutYPrPbEntry 1 }

		
		-- 1.3.6.1.4.1.1429.9.1.14.2.2.2.1.2
		saCProtectOutYPrPbPortEnabled OBJECT-TYPE
			SYNTAX TruthValue
			MAX-ACCESS read-only
			STATUS current
			DESCRIPTION
				"Indicates if the port is enabled for output."
			::= { saCProtectOutYPrPbEntry 2 }

		
		-- 1.3.6.1.4.1.1429.9.1.14.2.2.2.1.3
		saCProtectOutYPrPbConstrained OBJECT-TYPE
			SYNTAX TruthValue
			MAX-ACCESS read-only
			STATUS current
			DESCRIPTION
				"Indicates if the output is constrained."
			::= { saCProtectOutYPrPbEntry 3 }

		
		-- 1.3.6.1.4.1.1429.9.1.14.2.2.2.1.4
		saCProtectOutYPrPbMacrovisionEnabled OBJECT-TYPE
			SYNTAX TruthValue
			MAX-ACCESS read-only
			STATUS current
			DESCRIPTION
				"Indicates that Macrovision is enabled for the port."
			::= { saCProtectOutYPrPbEntry 4 }

		
		-- 1.3.6.1.4.1.1429.9.1.14.2.2.3
		saCProtectOut1394Table OBJECT-TYPE
			SYNTAX SEQUENCE OF SaCProtectOut1394Entry
			MAX-ACCESS not-accessible
			STATUS current
			DESCRIPTION
				"This table represents the copy control-related characteristics
				of 1394 output connections on the host.
				
				An entry exists for each 1394 output connection on the host."
			::= { saCProtectOut 3 }

		
		-- 1.3.6.1.4.1.1429.9.1.14.2.2.3.1
		saCProtectOut1394Entry OBJECT-TYPE
			SYNTAX SaCProtectOut1394Entry
			MAX-ACCESS not-accessible
			STATUS current
			DESCRIPTION
				"An entry in the table.
				
				
				An entry exists for each 1394 output connection on the host. "
			INDEX { sa1394DeviceIndex, sa1394DevConnMapIndex }
			::= { saCProtectOut1394Table 1 }

		
		SaCProtectOut1394Entry ::=
			SEQUENCE { 
				saCProtectOut1394ConnectionEnabled
					TruthValue,
				saCProtectOut1394DtcpEnabled
					TruthValue
			 }

		-- 1.3.6.1.4.1.1429.9.1.14.2.2.3.1.1
		saCProtectOut1394ConnectionEnabled OBJECT-TYPE
			SYNTAX TruthValue
			MAX-ACCESS read-only
			STATUS current
			DESCRIPTION
				"Indicates if the connection is enabled for output."
			::= { saCProtectOut1394Entry 1 }

		
		-- 1.3.6.1.4.1.1429.9.1.14.2.2.3.1.2
		saCProtectOut1394DtcpEnabled OBJECT-TYPE
			SYNTAX TruthValue
			MAX-ACCESS read-only
			STATUS current
			DESCRIPTION
				"Indicates if the DTCP is enabled on the connection."
			::= { saCProtectOut1394Entry 2 }

		
		-- 1.3.6.1.4.1.1429.9.1.14.2.2.4
		saCProtectOutCompositeTable OBJECT-TYPE
			SYNTAX SEQUENCE OF SaCProtectOutCompositeEntry
			MAX-ACCESS not-accessible
			STATUS current
			DESCRIPTION
				"This table represents the copy control-related characteristics
				of Composite output ports on the host.
				
				An entry exists for each Composite output port on the host. If an
				entry in this table corresponds to an entry in hrDeviceTable
				from the HOST-RESOURCES-MIB, then the index value for this table
				must match the corresponding hrDeviceIndex."
			::= { saCProtectOut 4 }

		
		-- 1.3.6.1.4.1.1429.9.1.14.2.2.4.1
		saCProtectOutCompositeEntry OBJECT-TYPE
			SYNTAX SaCProtectOutCompositeEntry
			MAX-ACCESS not-accessible
			STATUS current
			DESCRIPTION
				"An entry in the table.
				
				
				An entry exists for each Y-Pr-Pb output port on the host. If an
				entry in this table corresponds to an entry in hrDeviceTable
				from the HOST-RESOURCES-MIB, then the index value for this table
				must match the corresponding hrDeviceIndex."
			INDEX { saCProtectOutCompositeIndex }
			::= { saCProtectOutCompositeTable 1 }

		
		SaCProtectOutCompositeEntry ::=
			SEQUENCE { 
				saCProtectOutCompositeIndex
					Integer32,
				saCProtectOutCompositeMacrovisionEnabled
					TruthValue
			 }

		-- 1.3.6.1.4.1.1429.9.1.14.2.2.4.1.1
		saCProtectOutCompositeIndex OBJECT-TYPE
			SYNTAX Integer32 (1..2147483647)
			MAX-ACCESS not-accessible
			STATUS current
			DESCRIPTION
				"A unique value for this entry.
				
				If an entry in this table corresponds to an entry in hrDeviceTable
				from the HOST-RESOURCES-MIB, then this index value
				must match the corresponding hrDeviceIndex."
			::= { saCProtectOutCompositeEntry 1 }

		
		-- 1.3.6.1.4.1.1429.9.1.14.2.2.4.1.4
		saCProtectOutCompositeMacrovisionEnabled OBJECT-TYPE
			SYNTAX TruthValue
			MAX-ACCESS read-only
			STATUS current
			DESCRIPTION
				"Indicates that Macrovision is enabled for the port."
			::= { saCProtectOutCompositeEntry 4 }

		
		-- 1.3.6.1.4.1.1429.9.1.14.2.2.5
		saCProtectOut1394CitEpnTable OBJECT-TYPE
			SYNTAX SEQUENCE OF SaCProtectOut1394CitEpnEntry
			MAX-ACCESS not-accessible
			STATUS current
			DESCRIPTION
				"This table represents the CIT and EPN copy control-related characteristics 
				of 1394 output connections on the host. An entry exists for each 1394 output 
				connection on the host.
				"
			::= { saCProtectOut 5 }

		
		-- 1.3.6.1.4.1.1429.9.1.14.2.2.5.1
		saCProtectOut1394CitEpnEntry OBJECT-TYPE
			SYNTAX SaCProtectOut1394CitEpnEntry
			MAX-ACCESS not-accessible
			STATUS current
			DESCRIPTION
				"An entry in the table."
			INDEX { sa1394DeviceIndex, sa1394DevConnMapIndex }
			::= { saCProtectOut1394CitEpnTable 1 }

		
		SaCProtectOut1394CitEpnEntry ::=
			SEQUENCE { 
				saCProtectOut1394CitEpnCit
					TruthValue,
				saCProtectOut1394CitEpnEpn
					TruthValue
			 }

		-- 1.3.6.1.4.1.1429.9.1.14.2.2.5.1.1
		saCProtectOut1394CitEpnCit OBJECT-TYPE
			SYNTAX TruthValue
			MAX-ACCESS read-only
			STATUS current
			DESCRIPTION
				"Constrained Image Trigger"
			::= { saCProtectOut1394CitEpnEntry 1 }

		
		-- 1.3.6.1.4.1.1429.9.1.14.2.2.5.1.2
		saCProtectOut1394CitEpnEpn OBJECT-TYPE
			SYNTAX TruthValue
			MAX-ACCESS read-only
			STATUS current
			DESCRIPTION
				"Encryption Plus Non Assertion"
			::= { saCProtectOut1394CitEpnEntry 2 }

		
		-- 1.3.6.1.4.1.1429.9.1.14.2.3
		saCProtectLog OBJECT-IDENTITY
			STATUS current
			DESCRIPTION 
				"Copy protection logs."
			::= { saCProtectObjs 3 }

		
		-- 1.3.6.1.4.1.1429.9.1.14.2.3.1
		saCProtectGenCciEvtLogTable OBJECT-TYPE
			SYNTAX SEQUENCE OF SaCProtectGenCciEvtLogEntry
			MAX-ACCESS not-accessible
			STATUS current
			DESCRIPTION
				"This table provides a history of CCI Events.
				
				The maximum number of events recorded in this table is 
				implementation-defined. 
				
				Once this number is reached, adding a new event will cause the
				oldest event to be removed from the log. The index number for the 
				new event will be one more than the index number of the most recent
				event before the new event was added. 
				
				If the maximum allowable index number is reached (0xFFFFFFFF), then the next event
				causes the entire log to be cleared and the new event will be placed
				at index 1."
			::= { saCProtectLog 1 }

		
		-- 1.3.6.1.4.1.1429.9.1.14.2.3.1.1
		saCProtectGenCciEvtLogEntry OBJECT-TYPE
			SYNTAX SaCProtectGenCciEvtLogEntry
			MAX-ACCESS not-accessible
			STATUS current
			DESCRIPTION
				"A row in the table."
			INDEX { saCProtectGenCciEvtLogIndex }
			::= { saCProtectGenCciEvtLogTable 1 }

		
		SaCProtectGenCciEvtLogEntry ::=
			SEQUENCE { 
				saCProtectGenCciEvtLogIndex
					Unsigned32,
				saCProtectGenCciEvtLogSrcPortDescr
					DisplayString,
				saCProtectGenCciEvtLogDstPortDescr
					DisplayString,
				saCProtectGenCciEvtLogCciData
					CciEventData
			 }

		-- 1.3.6.1.4.1.1429.9.1.14.2.3.1.1.1
		saCProtectGenCciEvtLogIndex OBJECT-TYPE
			SYNTAX Unsigned32
			MAX-ACCESS not-accessible
			STATUS current
			DESCRIPTION
				"A monotonically increasing number to uniquely identify a 
				row in the table. See the description for saCProtectGenCciEvtLogTable
				for a description of row maintenance and index assignment.
				
				The index value for a given event should never change."
			::= { saCProtectGenCciEvtLogEntry 1 }

		
		-- 1.3.6.1.4.1.1429.9.1.14.2.3.1.1.2
		saCProtectGenCciEvtLogSrcPortDescr OBJECT-TYPE
			SYNTAX DisplayString
			MAX-ACCESS read-only
			STATUS current
			DESCRIPTION
				"A short identification of the source of the stream."
			::= { saCProtectGenCciEvtLogEntry 2 }

		
		-- 1.3.6.1.4.1.1429.9.1.14.2.3.1.1.3
		saCProtectGenCciEvtLogDstPortDescr OBJECT-TYPE
			SYNTAX DisplayString
			MAX-ACCESS read-only
			STATUS current
			DESCRIPTION
				"A short identification of the destination of the stream."
			::= { saCProtectGenCciEvtLogEntry 3 }

		
		-- 1.3.6.1.4.1.1429.9.1.14.2.3.1.1.4
		saCProtectGenCciEvtLogCciData OBJECT-TYPE
			SYNTAX CciEventData
			MAX-ACCESS read-only
			STATUS current
			DESCRIPTION
				"CCI Data associated with the event."
			::= { saCProtectGenCciEvtLogEntry 4 }

		
		-- 1.3.6.1.4.1.1429.9.1.14.3
		saCProtectEvents OBJECT-IDENTITY
			STATUS current
			DESCRIPTION 
				"Events associated with the SA-COPYPROTECT-MIB."
			::= { saCProtectMib 3 }

		
		-- 1.3.6.1.4.1.1429.9.1.14.3.0
		saCProtectEventsV2 OBJECT-IDENTITY
			STATUS current
			DESCRIPTION 
				"Dummy node under which all events must be defined. 
				This is required for SNMP v1/v2 compatability."
			::= { saCProtectEvents 0 }

		
	
	END

--
-- SA-COPYPROTECT-MIB.mib
--
