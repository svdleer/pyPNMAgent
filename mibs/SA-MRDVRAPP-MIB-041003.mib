--
-- SA-MRDVRAPP-MIB.mib
-- MIB generated by MG-SOFT Visual MIB Builder Version 4.0 Build 349
-- Tuesday, July 15, 2003 at 14:23:29
--

	SA-MRDVRAPP-MIB DEFINITIONS ::= BEGIN
 
		IMPORTS
			saMrdvrAppMib			
				FROM SA-DBDSPROD-MIB			
			DhctTimeStampType			
				FROM SA-DHCT-TC			
			saModules			
				FROM SCIATL-COMMON-MIB			
			OBJECT-GROUP, MODULE-COMPLIANCE			
				FROM SNMPv2-CONF			
			Integer32, Unsigned32, Counter32, OBJECT-TYPE, MODULE-IDENTITY, 
			OBJECT-IDENTITY			
				FROM SNMPv2-SMI;
	
	
		-- 1.3.6.1.4.1.1429.7.1.8
		saMrdvrAppMibModule MODULE-IDENTITY 
			LAST-UPDATED "200304101535Z"		-- April 10, 2003 at 15:35 GMT
			ORGANIZATION 
				"Scientific Atlanta"
			CONTACT-INFO 
				"DBDS Software Engineering & Architecture
				Scientific-Atlanta
				5030 Sugarloaf Parkway
				Lawrencville, GA 30044
				"
			DESCRIPTION 
				"MR-DVR Application Information for Client and Server.
				
				This MIB module Copyright 2003 Scientific-Atlanta
				
				
				THIS VERSION IS PRELIMINARY FOR REVIEW PURPOSES ONLY!
				"
			::= { saModules 8 }

		
	
	
--
-- Node definitions
--
	
		-- 1.3.6.1.4.1.1429.5.1.2.1
		saMrdvrAppConf OBJECT-IDENTITY
			STATUS current
			DESCRIPTION 
				"Conformance"
			::= { saMrdvrAppMib 1 }

		
		-- 1.3.6.1.4.1.1429.5.1.2.1.1
		saMrdvrGroups OBJECT-IDENTITY
			STATUS current
			DESCRIPTION 
				"Object groups for the SA-MRDVRAPP-MIB."
			::= { saMrdvrAppConf 1 }

		
		-- 1.3.6.1.4.1.1429.5.1.2.1.1.1
		saMrdvrAppAuthGroup OBJECT-GROUP
			OBJECTS { mrdvrAuthorizations }
			STATUS current
			DESCRIPTION 
				"Provides the MR-DVR-related authorizations loaded onto the station."
			::= { saMrdvrGroups 1 }

		
		-- 1.3.6.1.4.1.1429.5.1.2.1.1.2
		saMrdvrAppCatGroup OBJECT-GROUP
			OBJECTS { catCurrentCount, catCurrentEntryNum, catCurrentServerId, catCurrentVersion, catCurrentSize, 
				catCurrentCreationTimeStamp, catCurrentSendTimeStamp, catCurrentRcvTimeStamp, catCurrentFormatVersion, catHistoryCount, 
				catHistoryEntryNum, catHistoryServerId, catHistoryVersion, catHistorySize, catHistoryCreationTimeStamp, 
				catHistorySendTimeStamp, catHistoryRcvTimeStamp, catHistoryFormatVersion }
			STATUS current
			DESCRIPTION 
				"Objects relating to the MR-DVR Catalog."
			::= { saMrdvrGroups 2 }

		
		-- 1.3.6.1.4.1.1429.5.1.2.1.1.3
		saMrdvrAppProtocolGroup OBJECT-GROUP
			OBJECTS { mrdvrAppProtocolEntityId, mrdvrAppProtocolOutPingRsps, mrdvrAppProtocolInPingRqs, mrdvrAppProtocolInPingRsps, mrdvrAppProtocolOutPingRqs, 
				mrdvrAppProtocolAvSessTimeouts, mrdvrAppProtocolSessSucceeds, mrdvrAppProtocolInUnknownMsgs, mrdvrAppProtocolRetransMsgs, mrdvrAppProtocolOutMsgs, 
				mrdvrAppProtocolInMsgs, mrdvrAppProtocolInitTime, mrdvrAppProtocolVersion }
			STATUS current
			DESCRIPTION 
				"Objects relating to the MR-DVR Application Protocol."
			::= { saMrdvrGroups 3 }

		
		-- 1.3.6.1.4.1.1429.5.1.2.1.1.4
		saMrdvrAppSessGroup OBJECT-GROUP
			OBJECTS { avSessCurrentEntityId, avSessCurrentEntryNum, avSessCurrentId, avSessCurrentRole, avSessCurrentStartTime, 
				avSessCurrentMode, avSessCurrentRecordingState, avSessCurrentPlayScale, avSessCurrentNpt, avSessCurrentEndNpt, 
				avSessCurrentFormat, avSessCurrentProgramNum, avSessCurrentInMsgs, avSessCurrentOutMsgs, avSessCurrentRetransMsgs, 
				avSessCurrentOutStreamCtrlRqs, avSessCurrentInStreamCtrlRsps, avSessCurrentInStreamCtrlRqs, avSessCurrentOutStreamCtrlRsps, avSessCurrentOutStreamDoneEvts, 
				avSessCurrentInStreamDoneRsps, avSessCurrentInStreamDoneEvts, avSessCurrentOutStreamDoneRsps, avSessCurrentOutStreamStatEvts, avSessCurrentInStreamStatEvts, 
				avSessHistoryLimitsEntityId, avSessHistoryLimitsMaxCount, avSessHistoryEntityId, avSessHistoryEntryNum, avSessHistoryId, 
				avSessHistoryRole, avSessHistoryStartTime, avSessHistoryMode, avSessHistoryRecordingState, avSessHistoryPlayScale, 
				avSessHistoryNpt, avSessHistoryEndNpt, avSessHistoryFormat, avSessHistoryProgramNum, avSessHistoryInMsgs, 
				avSessHistoryOutMsgs, avSessHistoryRetransMsgs, avSessHistoryOutStreamCtrlRqs, avSessHistoryInStreamCtrlRsps, avSessHistoryInStreamCtrlRqs, 
				avSessHistoryOutStreamCtrlRsps, avSessHistoryOutStreamDoneEvts, avSessHistoryInStreamDoneRsps, avSessHistoryInStreamDoneEvts, avSessHistoryOutStreamDoneRsps, 
				avSessHistoryOutStreamStatEvts, avSessHistoryInStreamStatEvts, avSessHistoryEndTime, avSessHistoryEndReason }
			STATUS current
			DESCRIPTION 
				"Objects relating to MR-DVR Application Sessions."
			::= { saMrdvrGroups 4 }

		
		-- 1.3.6.1.4.1.1429.5.1.2.1.1.5
		saMrdvrAppDeprecatedGroup OBJECT-GROUP
			OBJECTS { mrdvrAppProtocolCount, avSessCurrentCount, avSessHistoryCount }
			STATUS deprecated
			DESCRIPTION 
				"Objects that are deprecated. Compliance is not required. Furthermore,
				new agent implementations should not include these items and network
				management systems should not use them."
			::= { saMrdvrGroups 5 }

		
		-- 1.3.6.1.4.1.1429.5.1.2.1.3
		saMrdvrCompls OBJECT-IDENTITY
			STATUS current
			DESCRIPTION 
				"Compliances for the SA-MRDVRAPP-MIB module."
			::= { saMrdvrAppConf 3 }

		
		-- 1.3.6.1.4.1.1429.5.1.2.1.3.1
		saMrdvrAppReq MODULE-COMPLIANCE
			STATUS current
			DESCRIPTION 
				"Requirements for conforming agent implementations."
			MODULE -- this module
				MANDATORY-GROUPS { saMrdvrAppAuthGroup }
				GROUP saMrdvrAppCatGroup
					DESCRIPTION 
						"Any agent that publishes or retrieves an
						MR-DVR catalog must conform to this group."
				GROUP saMrdvrAppProtocolGroup
					DESCRIPTION 
						"Any agent that sends or receives MR-DVR
						Application protocol messages must 
						implement this group."
				GROUP saMrdvrAppSessGroup
					DESCRIPTION 
						"Any agent that participates in MR-DVR
						Application Sessions must implement
						this group."
			::= { saMrdvrCompls 1 }

		
		-- 1.3.6.1.4.1.1429.5.1.2.2
		saMrdvrAppObjs OBJECT-IDENTITY
			STATUS current
			DESCRIPTION 
				"SA-MRDVRAPP-MIB objects."
			::= { saMrdvrAppMib 2 }

		
		-- 1.3.6.1.4.1.1429.5.1.2.2.1
		mrdvrAuthorizations OBJECT-TYPE
			SYNTAX BITS
				{
				authAsClient(0),
				authAsServer(1)
				}
			MAX-ACCESS read-only
			STATUS current
			DESCRIPTION
				"Indicates the MR-DVR related authorizations are present on the station.
				
				authAsClient = The station is authorized as a MR-DVR Client
				authAsServer = The station is authorized as a MR-DVR Server"
			::= { saMrdvrAppObjs 1 }

		
		-- 1.3.6.1.4.1.1429.5.1.2.2.2
		mrdvrCatalog OBJECT-IDENTITY
			STATUS current
			DESCRIPTION 
				"Objects pertaining to the MR-DVR Application Catalog"
			::= { saMrdvrAppObjs 2 }

		
		-- 1.3.6.1.4.1.1429.5.1.2.2.2.1
		mrdvrCatCurrent OBJECT-IDENTITY
			STATUS current
			DESCRIPTION 
				"Current catalog information."
			::= { mrdvrCatalog 1 }

		
		-- 1.3.6.1.4.1.1429.5.1.2.2.2.1.1
		catCurrentCount OBJECT-TYPE
			SYNTAX Integer32
			MAX-ACCESS read-only
			STATUS current
			DESCRIPTION
				"The number of entries in the catCurrentTable."
			::= { mrdvrCatCurrent 1 }

		
		-- 1.3.6.1.4.1.1429.5.1.2.2.2.1.2
		catCurrentTable OBJECT-TYPE
			SYNTAX SEQUENCE OF CatCurrentEntry
			MAX-ACCESS not-accessible
			STATUS current
			DESCRIPTION
				"Contains a listing for the current catalog retreived from each MR-DVR Server."
			::= { mrdvrCatCurrent 2 }

		
		-- 1.3.6.1.4.1.1429.5.1.2.2.3.1.2.1
		catCurrentEntry OBJECT-TYPE
			SYNTAX CatCurrentEntry
			MAX-ACCESS not-accessible
			STATUS current
			DESCRIPTION
				"An entry in the table."
			INDEX { catCurrentEntryNum }
			::= { catCurrentTable 1 }

		
		CatCurrentEntry ::=
			SEQUENCE { 
				catCurrentEntryNum
					Integer32,
				catCurrentServerId
					OCTET STRING,
				catCurrentVersion
					OCTET STRING,
				catCurrentSize
					Integer32,
				catCurrentCreationTimeStamp
					DhctTimeStampType,
				catCurrentSendTimeStamp
					DhctTimeStampType,
				catCurrentRcvTimeStamp
					DhctTimeStampType,
				catCurrentFormatVersion
					OCTET STRING
			 }

		-- 1.3.6.1.4.1.1429.5.1.2.2.3.1.2.1.1
		catCurrentEntryNum OBJECT-TYPE
			SYNTAX Integer32 (1..255)
			MAX-ACCESS read-only
			STATUS current
			DESCRIPTION
				"A unique number for this entry."
			::= { catCurrentEntry 1 }

		
		-- 1.3.6.1.4.1.1429.5.1.2.2.3.1.2.1.2
		catCurrentServerId OBJECT-TYPE
			SYNTAX OCTET STRING
			MAX-ACCESS read-only
			STATUS current
			DESCRIPTION
				"The In-Home Network ID for the server from which the catalog
				was published/retreived."
			::= { catCurrentEntry 2 }

		
		-- 1.3.6.1.4.1.1429.5.1.2.2.3.1.2.1.3
		catCurrentVersion OBJECT-TYPE
			SYNTAX OCTET STRING
			MAX-ACCESS read-only
			STATUS current
			DESCRIPTION
				"Version identifier of the catalog.
				This identifier serves to differentiate one catalog from another. 
				For the client, this is the version obtained. 
				For the Server this is the version published."
			::= { catCurrentEntry 3 }

		
		-- 1.3.6.1.4.1.1429.5.1.2.2.3.1.2.1.4
		catCurrentSize OBJECT-TYPE
			SYNTAX Integer32
			UNITS "bytes"
			MAX-ACCESS read-only
			STATUS current
			DESCRIPTION
				"The size of the catalog"
			::= { catCurrentEntry 4 }

		
		-- 1.3.6.1.4.1.1429.5.1.2.2.3.1.2.1.5
		catCurrentCreationTimeStamp OBJECT-TYPE
			SYNTAX DhctTimeStampType
			MAX-ACCESS read-only
			STATUS current
			DESCRIPTION
				"A date/time stamp for the catalog. 
				This is the time the catalog was created.
				
				The epoch for this time value is January 1, 1970, 12:00:00AM GMT."
			::= { catCurrentEntry 5 }

		
		-- 1.3.6.1.4.1.1429.5.1.2.2.3.1.2.1.6
		catCurrentSendTimeStamp OBJECT-TYPE
			SYNTAX DhctTimeStampType
			MAX-ACCESS read-only
			STATUS current
			DESCRIPTION
				"A date/time stamp for the catalog. 
				This is the time the catalog was posted/sent from the server.
				If the client does not have this information, the value is 0.
				
				The epoch for this time value is January 1, 1970, 12:00:00AM GMT."
			::= { catCurrentEntry 6 }

		
		-- 1.3.6.1.4.1.1429.5.1.2.2.3.1.2.1.7
		catCurrentRcvTimeStamp OBJECT-TYPE
			SYNTAX DhctTimeStampType
			MAX-ACCESS read-only
			STATUS current
			DESCRIPTION
				"A date/time stamp for the catalog. 
				This is the time the catalog was received on the client.
				For the server, this value should be 0.
				
				The epoch for this time value is January 1, 1970, 12:00:00AM GMT."
			::= { catCurrentEntry 7 }

		
		-- 1.3.6.1.4.1.1429.5.1.2.2.3.1.2.1.8
		catCurrentFormatVersion OBJECT-TYPE
			SYNTAX OCTET STRING
			MAX-ACCESS read-only
			STATUS current
			DESCRIPTION
				"Identifies the format of the catalog.
				For the client, this is the version obtained. 
				For the Server this is the version published."
			::= { catCurrentEntry 8 }

		
		-- 1.3.6.1.4.1.1429.5.1.2.2.2.2
		mrdvrCatHistory OBJECT-IDENTITY
			STATUS current
			DESCRIPTION 
				"Historical information regarding past catalogs."
			::= { mrdvrCatalog 2 }

		
		-- 1.3.6.1.4.1.1429.5.1.2.2.2.2.1
		catHistoryCount OBJECT-TYPE
			SYNTAX Integer32
			MAX-ACCESS read-only
			STATUS current
			DESCRIPTION
				"The number of entries in cathistoryTable"
			::= { mrdvrCatHistory 1 }

		
		-- 1.3.6.1.4.1.1429.5.1.2.2.2.2.2
		catHistoryTable OBJECT-TYPE
			SYNTAX SEQUENCE OF CatHistoryEntry
			MAX-ACCESS not-accessible
			STATUS current
			DESCRIPTION
				"Historical information regarding past catalogs."
			::= { mrdvrCatHistory 2 }

		
		-- 1.3.6.1.4.1.1429.5.1.2.2.3.2.2.1
		catHistoryEntry OBJECT-TYPE
			SYNTAX CatHistoryEntry
			MAX-ACCESS not-accessible
			STATUS current
			DESCRIPTION
				"An entry in the table."
			INDEX { catHistoryEntryNum }
			::= { catHistoryTable 1 }

		
		CatHistoryEntry ::=
			SEQUENCE { 
				catHistoryEntryNum
					Integer32,
				catHistoryServerId
					OCTET STRING,
				catHistoryVersion
					OCTET STRING,
				catHistorySize
					Integer32,
				catHistoryCreationTimeStamp
					DhctTimeStampType,
				catHistorySendTimeStamp
					DhctTimeStampType,
				catHistoryRcvTimeStamp
					DhctTimeStampType,
				catHistoryFormatVersion
					OCTET STRING
			 }

		-- 1.3.6.1.4.1.1429.5.1.2.2.3.2.2.1.1
		catHistoryEntryNum OBJECT-TYPE
			SYNTAX Integer32 (1..255)
			MAX-ACCESS read-only
			STATUS current
			DESCRIPTION
				"A unique number for this entry."
			::= { catHistoryEntry 1 }

		
		-- 1.3.6.1.4.1.1429.5.1.2.2.3.2.2.1.2
		catHistoryServerId OBJECT-TYPE
			SYNTAX OCTET STRING
			MAX-ACCESS read-only
			STATUS current
			DESCRIPTION
				"The In-Home Network ID for the server from which the catalog
				was retreived."
			::= { catHistoryEntry 2 }

		
		-- 1.3.6.1.4.1.1429.5.1.2.2.3.2.2.1.3
		catHistoryVersion OBJECT-TYPE
			SYNTAX OCTET STRING
			MAX-ACCESS read-only
			STATUS current
			DESCRIPTION
				"Version identifier of the catalog. 
				This identifier serves to differentiate one catalog from another. 
				For the client, this is the version obtained. 
				For the Server this is the version published."
			::= { catHistoryEntry 3 }

		
		-- 1.3.6.1.4.1.1429.5.1.2.2.3.2.2.1.4
		catHistorySize OBJECT-TYPE
			SYNTAX Integer32
			UNITS "bytes"
			MAX-ACCESS read-only
			STATUS current
			DESCRIPTION
				"The size of the catalog"
			::= { catHistoryEntry 4 }

		
		-- 1.3.6.1.4.1.1429.5.1.2.2.3.2.2.1.5
		catHistoryCreationTimeStamp OBJECT-TYPE
			SYNTAX DhctTimeStampType
			MAX-ACCESS read-only
			STATUS current
			DESCRIPTION
				"A date/time stamp for the catalog. 
				This is the time the catalog was created.
				
				The epoch for this time value is January 1, 1970, 12:00:00AM GMT."
			::= { catHistoryEntry 5 }

		
		-- 1.3.6.1.4.1.1429.5.1.2.2.3.2.2.1.6
		catHistorySendTimeStamp OBJECT-TYPE
			SYNTAX DhctTimeStampType
			MAX-ACCESS read-only
			STATUS current
			DESCRIPTION
				"A date/time stamp for the catalog. 
				This is the time the catalog was posted/sent from the server.
				If the client does not have this information, the value is 0.
				
				The epoch for this time value is January 1, 1970, 12:00:00AM GMT."
			::= { catHistoryEntry 6 }

		
		-- 1.3.6.1.4.1.1429.5.1.2.2.3.2.2.1.7
		catHistoryRcvTimeStamp OBJECT-TYPE
			SYNTAX DhctTimeStampType
			MAX-ACCESS read-only
			STATUS current
			DESCRIPTION
				"A date/time stamp for the catalog. 
				This is the time the catalog was received on the client.
				For the server, this value should be 0.
				
				The epoch for this time value is January 1, 1970, 12:00:00AM GMT."
			::= { catHistoryEntry 7 }

		
		-- 1.3.6.1.4.1.1429.5.1.2.2.3.2.2.1.8
		catHistoryFormatVersion OBJECT-TYPE
			SYNTAX OCTET STRING
			MAX-ACCESS read-only
			STATUS current
			DESCRIPTION
				"Identifies the format of the catalog.
				For the client, this is the version obtained. 
				For the Server this is the version published."
			::= { catHistoryEntry 8 }

		
		-- 1.3.6.1.4.1.1429.5.1.2.2.3
		mrdvrAppProtocol OBJECT-IDENTITY
			STATUS current
			DESCRIPTION 
				"Information regarding the MR-DVR Application Protocol."
			::= { saMrdvrAppObjs 3 }

		
		-- 1.3.6.1.4.1.1429.5.1.2.2.3.1
		mrdvrAppProtocolCount OBJECT-TYPE
			SYNTAX Integer32
			MAX-ACCESS read-only
			STATUS deprecated
			DESCRIPTION
				"DEPRICATED! The number of entries in mrdvrAppProtocolTable"
			::= { mrdvrAppProtocol 1 }

		
		-- 1.3.6.1.4.1.1429.5.1.2.2.3.2
		mrdvrAppProtocolTable OBJECT-TYPE
			SYNTAX SEQUENCE OF MrdvrAppProtocolEntry
			MAX-ACCESS not-accessible
			STATUS current
			DESCRIPTION
				"Statistics for each protocol entity on the station."
			::= { mrdvrAppProtocol 2 }

		
		-- 1.3.6.1.4.1.1429.5.1.2.2.3.2.1
		mrdvrAppProtocolEntry OBJECT-TYPE
			SYNTAX MrdvrAppProtocolEntry
			MAX-ACCESS not-accessible
			STATUS current
			DESCRIPTION
				"The statistics for a single protocol entity on the station."
			INDEX { mrdvrAppProtocolEntityId }
			::= { mrdvrAppProtocolTable 1 }

		
		MrdvrAppProtocolEntry ::=
			SEQUENCE { 
				mrdvrAppProtocolEntityId
					Unsigned32,
				mrdvrAppProtocolOutPingRsps
					Counter32,
				mrdvrAppProtocolInPingRqs
					Counter32,
				mrdvrAppProtocolInPingRsps
					Counter32,
				mrdvrAppProtocolOutPingRqs
					Counter32,
				mrdvrAppProtocolAvSessTimeouts
					Counter32,
				mrdvrAppProtocolSessSucceeds
					Counter32,
				mrdvrAppProtocolInUnknownMsgs
					Counter32,
				mrdvrAppProtocolRetransMsgs
					Counter32,
				mrdvrAppProtocolOutMsgs
					Counter32,
				mrdvrAppProtocolInMsgs
					Counter32,
				mrdvrAppProtocolInitTime
					DhctTimeStampType,
				mrdvrAppProtocolVersion
					OCTET STRING
			 }

		-- 1.3.6.1.4.1.1429.5.1.2.2.3.2.1.1
		mrdvrAppProtocolEntityId OBJECT-TYPE
			SYNTAX Unsigned32
			MAX-ACCESS read-only
			STATUS current
			DESCRIPTION
				"The identification number of the MR-DVR Application Protocol entity that uniquely 
				distinguishes this entity from all other MR-DVR Application Protocol entities on 
				this station. This value should correspond to an application or service executing
				on the station."
			::= { mrdvrAppProtocolEntry 1 }

		
		-- 1.3.6.1.4.1.1429.5.1.2.2.3.2.1.2
		mrdvrAppProtocolOutPingRsps OBJECT-TYPE
			SYNTAX Counter32
			MAX-ACCESS read-only
			STATUS current
			DESCRIPTION
				"The number of MR-DVR Application Protocol Ping Response Messages sent since the
				protocol entity was initialized. This number includes all re-transmissions."
			::= { mrdvrAppProtocolEntry 2 }

		
		-- 1.3.6.1.4.1.1429.5.1.2.2.3.2.1.3
		mrdvrAppProtocolInPingRqs OBJECT-TYPE
			SYNTAX Counter32
			MAX-ACCESS read-only
			STATUS current
			DESCRIPTION
				"The number of MR-DVR Application Protocol Ping Request Messages received since the
				protocol entity was initialized. This number includes all re-transmissions."
			::= { mrdvrAppProtocolEntry 3 }

		
		-- 1.3.6.1.4.1.1429.5.1.2.2.3.2.1.4
		mrdvrAppProtocolInPingRsps OBJECT-TYPE
			SYNTAX Counter32
			MAX-ACCESS read-only
			STATUS current
			DESCRIPTION
				"The number of MR-DVR Application Protocol Ping Response Messages received since the
				protocol entity was initialized. This number includes all re-transmissions."
			::= { mrdvrAppProtocolEntry 4 }

		
		-- 1.3.6.1.4.1.1429.5.1.2.2.3.2.1.5
		mrdvrAppProtocolOutPingRqs OBJECT-TYPE
			SYNTAX Counter32
			MAX-ACCESS read-only
			STATUS current
			DESCRIPTION
				"The number of MR-DVR Application Protocol Ping Request Messages sent since the
				protocol entity was initialized. This number includes all re-transmissions."
			::= { mrdvrAppProtocolEntry 5 }

		
		-- 1.3.6.1.4.1.1429.5.1.2.2.3.2.1.6
		mrdvrAppProtocolAvSessTimeouts OBJECT-TYPE
			SYNTAX Counter32
			MAX-ACCESS read-only
			STATUS current
			DESCRIPTION
				"The number of MR-DVR A/V Sessions that have timed out since the
				protocol entity was initialized."
			::= { mrdvrAppProtocolEntry 6 }

		
		-- 1.3.6.1.4.1.1429.5.1.2.2.3.2.1.7
		mrdvrAppProtocolSessSucceeds OBJECT-TYPE
			SYNTAX Counter32
			MAX-ACCESS read-only
			STATUS current
			DESCRIPTION
				"The number of times an attempt to establish an MR-DVR A/V Session succeeded since the
				protocol entity was initialized."
			::= { mrdvrAppProtocolEntry 7 }

		
		-- 1.3.6.1.4.1.1429.5.1.2.2.3.2.1.8
		mrdvrAppProtocolInUnknownMsgs OBJECT-TYPE
			SYNTAX Counter32
			MAX-ACCESS read-only
			STATUS current
			DESCRIPTION
				"The number of MR-DVR Application Protocol Messages received since the
				protocol entity was initialized that were not recognized as any known type."
			::= { mrdvrAppProtocolEntry 8 }

		
		-- 1.3.6.1.4.1.1429.5.1.2.2.3.2.1.9
		mrdvrAppProtocolRetransMsgs OBJECT-TYPE
			SYNTAX Counter32
			MAX-ACCESS read-only
			STATUS current
			DESCRIPTION
				"The number of MR-DVR Application Protocol Messages re-transmitted since the
				protocol entity was initialized."
			::= { mrdvrAppProtocolEntry 9 }

		
		-- 1.3.6.1.4.1.1429.5.1.2.2.3.2.1.10
		mrdvrAppProtocolOutMsgs OBJECT-TYPE
			SYNTAX Counter32
			MAX-ACCESS read-only
			STATUS current
			DESCRIPTION
				"The number of MR-DVR Application Protocol Messages sent since the
				protocol entity was initialized. This number includes all re-transmissions."
			::= { mrdvrAppProtocolEntry 10 }

		
		-- 1.3.6.1.4.1.1429.5.1.2.2.3.2.1.11
		mrdvrAppProtocolInMsgs OBJECT-TYPE
			SYNTAX Counter32
			MAX-ACCESS read-only
			STATUS current
			DESCRIPTION
				"The number of MR-DVR Application Protocol Messages received since the
				protocol entity was initialized."
			::= { mrdvrAppProtocolEntry 11 }

		
		-- 1.3.6.1.4.1.1429.5.1.2.2.3.2.1.12
		mrdvrAppProtocolInitTime OBJECT-TYPE
			SYNTAX DhctTimeStampType
			MAX-ACCESS read-only
			STATUS current
			DESCRIPTION
				"The time the MR-DVR Application Protocol entity was initialized on this station.
				
				The epoch for this time value is January 1, 1970, 12:00:00AM GMT."
			::= { mrdvrAppProtocolEntry 12 }

		
		-- 1.3.6.1.4.1.1429.5.1.2.2.3.2.1.13
		mrdvrAppProtocolVersion OBJECT-TYPE
			SYNTAX OCTET STRING
			MAX-ACCESS read-only
			STATUS current
			DESCRIPTION
				"Protocol version number supported by this protocol entity."
			::= { mrdvrAppProtocolEntry 13 }

		
		-- 1.3.6.1.4.1.1429.5.1.2.2.4
		mrdvrAvSessions OBJECT-IDENTITY
			STATUS current
			DESCRIPTION 
				"Information about MR-DVR A/V Sessions"
			::= { saMrdvrAppObjs 4 }

		
		-- 1.3.6.1.4.1.1429.5.1.2.2.4.1
		mrdvrAvSessCurrent OBJECT-IDENTITY
			STATUS current
			DESCRIPTION 
				"Sessions that are currently in existence."
			::= { mrdvrAvSessions 1 }

		
		-- 1.3.6.1.4.1.1429.5.1.2.2.4.1.1
		avSessCurrentCount OBJECT-TYPE
			SYNTAX Integer32
			MAX-ACCESS read-only
			STATUS deprecated
			DESCRIPTION
				"DEPRECATED! The number of entries in the avSessCurrentTable"
			::= { mrdvrAvSessCurrent 1 }

		
		-- 1.3.6.1.4.1.1429.5.1.2.2.4.1.2
		avSessCurrentTable OBJECT-TYPE
			SYNTAX SEQUENCE OF AvSessCurrentEntry
			MAX-ACCESS not-accessible
			STATUS current
			DESCRIPTION
				"The table of current MR-DVR A/V Sessions."
			::= { mrdvrAvSessCurrent 2 }

		
		-- 1.3.6.1.4.1.1429.5.1.2.2.5.1.2.1
		avSessCurrentEntry OBJECT-TYPE
			SYNTAX AvSessCurrentEntry
			MAX-ACCESS not-accessible
			STATUS current
			DESCRIPTION
				"A current MR-DVR A/V Session."
			INDEX { avSessCurrentEntityId, avSessCurrentEntryNum }
			::= { avSessCurrentTable 1 }

		
		AvSessCurrentEntry ::=
			SEQUENCE { 
				avSessCurrentEntityId
					Unsigned32,
				avSessCurrentEntryNum
					Integer32,
				avSessCurrentId
					OCTET STRING,
				avSessCurrentRole
					INTEGER,
				avSessCurrentStartTime
					DhctTimeStampType,
				avSessCurrentMode
					INTEGER,
				avSessCurrentRecordingState
					INTEGER,
				avSessCurrentPlayScale
					INTEGER,
				avSessCurrentNpt
					Integer32,
				avSessCurrentEndNpt
					Integer32,
				avSessCurrentFormat
					INTEGER,
				avSessCurrentProgramNum
					Integer32,
				avSessCurrentInMsgs
					Counter32,
				avSessCurrentOutMsgs
					Counter32,
				avSessCurrentRetransMsgs
					Counter32,
				avSessCurrentOutStreamCtrlRqs
					Counter32,
				avSessCurrentInStreamCtrlRsps
					Counter32,
				avSessCurrentInStreamCtrlRqs
					Counter32,
				avSessCurrentOutStreamCtrlRsps
					Counter32,
				avSessCurrentOutStreamDoneEvts
					Counter32,
				avSessCurrentInStreamDoneRsps
					Counter32,
				avSessCurrentInStreamDoneEvts
					Counter32,
				avSessCurrentOutStreamDoneRsps
					Counter32,
				avSessCurrentOutStreamStatEvts
					Counter32,
				avSessCurrentInStreamStatEvts
					Counter32
			 }

		-- 1.3.6.1.4.1.1429.5.1.2.2.5.1.2.1.1
		avSessCurrentEntityId OBJECT-TYPE
			SYNTAX Unsigned32
			MAX-ACCESS read-only
			STATUS current
			DESCRIPTION
				"The indentification number of the entity that reports MR-DVR A/V Session information.
				This uniquely distinguishes this entity from all other such entities on this station.
				This value should correspond to an application or service executingon the station."
			::= { avSessCurrentEntry 1 }

		
		-- 1.3.6.1.4.1.1429.5.1.2.2.5.1.2.1.2
		avSessCurrentEntryNum OBJECT-TYPE
			SYNTAX Integer32 (1..255)
			MAX-ACCESS read-only
			STATUS current
			DESCRIPTION
				"A unique number that distinguishes this session from others within the
				scope of a single avSessCurrentEntityId value."
			::= { avSessCurrentEntry 2 }

		
		-- 1.3.6.1.4.1.1429.5.1.2.2.5.1.2.1.3
		avSessCurrentId OBJECT-TYPE
			SYNTAX OCTET STRING
			MAX-ACCESS read-only
			STATUS current
			DESCRIPTION
				"The In-Home Session ID associated with this MR-DVR A/V Session."
			::= { avSessCurrentEntry 3 }

		
		-- 1.3.6.1.4.1.1429.5.1.2.2.5.1.2.1.4
		avSessCurrentRole OBJECT-TYPE
			SYNTAX INTEGER
				{
				client(1),
				server(2)
				}
			MAX-ACCESS read-only
			STATUS current
			DESCRIPTION
				"For this session, was this station acting as the client or the server"
			::= { avSessCurrentEntry 4 }

		
		-- 1.3.6.1.4.1.1429.5.1.2.2.5.1.2.1.5
		avSessCurrentStartTime OBJECT-TYPE
			SYNTAX DhctTimeStampType
			MAX-ACCESS read-only
			STATUS current
			DESCRIPTION
				"The time the station considered this session established.
				
				The epoch for this time value is January 1, 1970, 12:00:00AM GMT."
			::= { avSessCurrentEntry 5 }

		
		-- 1.3.6.1.4.1.1429.5.1.2.2.5.1.2.1.6
		avSessCurrentMode OBJECT-TYPE
			SYNTAX INTEGER
				{
				play(1),
				stop(2),
				pause(3)
				}
			MAX-ACCESS read-only
			STATUS current
			DESCRIPTION
				"The MR-DVR A/V Session mode."
			::= { avSessCurrentEntry 6 }

		
		-- 1.3.6.1.4.1.1429.5.1.2.2.5.1.2.1.7
		avSessCurrentRecordingState OBJECT-TYPE
			SYNTAX INTEGER
				{
				notRecording(1),
				recording(2)
				}
			MAX-ACCESS read-only
			STATUS current
			DESCRIPTION
				"Indicates if the program is currently being recorded.
				
				notRecording = The program is not currently being recorded by the server
				recording    = The program is currently being recorded by the server
				"
			::= { avSessCurrentEntry 7 }

		
		-- 1.3.6.1.4.1.1429.5.1.2.2.5.1.2.1.8
		avSessCurrentPlayScale OBJECT-TYPE
			SYNTAX INTEGER
				{
				forward(1),
				pause(2),
				stepForward(3),
				stepReverse(4),
				fastForward1(11),
				fastForward2(12),
				fastForward3(13),
				fastReverse1(21),
				fastReverse2(22),
				fastReverse3(23),
				slowForward1(41),
				slowReverse1(81)
				}
			MAX-ACCESS read-only
			STATUS current
			DESCRIPTION
				"The current speed scale of the associated stream."
			::= { avSessCurrentEntry 8 }

		
		-- 1.3.6.1.4.1.1429.5.1.2.2.5.1.2.1.9
		avSessCurrentNpt OBJECT-TYPE
			SYNTAX Integer32
			UNITS "milli-seconds"
			MAX-ACCESS read-only
			STATUS current
			DESCRIPTION
				"The Normal Play Time indicating the current position in the associated stream.
				"
			::= { avSessCurrentEntry 9 }

		
		-- 1.3.6.1.4.1.1429.5.1.2.2.5.1.2.1.10
		avSessCurrentEndNpt OBJECT-TYPE
			SYNTAX Integer32
			UNITS "milli-seconds"
			MAX-ACCESS read-only
			STATUS current
			DESCRIPTION
				"The Normal Play Time indicating the end position in the associated stream."
			::= { avSessCurrentEntry 10 }

		
		-- 1.3.6.1.4.1.1429.5.1.2.2.5.1.2.1.11
		avSessCurrentFormat OBJECT-TYPE
			SYNTAX INTEGER
				{
				sd(1),
				hd(2)
				}
			MAX-ACCESS read-only
			STATUS current
			DESCRIPTION
				"The format of the content in the stream:
				sd = Standard Definition
				hd = High Definition"
			::= { avSessCurrentEntry 11 }

		
		-- 1.3.6.1.4.1.1429.5.1.2.2.5.1.2.1.12
		avSessCurrentProgramNum OBJECT-TYPE
			SYNTAX Integer32
			MAX-ACCESS read-only
			STATUS current
			DESCRIPTION
				"The program number associated with the MR-DVR A/V Session."
			::= { avSessCurrentEntry 12 }

		
		-- 1.3.6.1.4.1.1429.5.1.2.2.5.1.2.1.13
		avSessCurrentInMsgs OBJECT-TYPE
			SYNTAX Counter32
			MAX-ACCESS read-only
			STATUS current
			DESCRIPTION
				"The number of MR-DVR Application Protocol Messages received since the
				session was established."
			::= { avSessCurrentEntry 13 }

		
		-- 1.3.6.1.4.1.1429.5.1.2.2.5.1.2.1.14
		avSessCurrentOutMsgs OBJECT-TYPE
			SYNTAX Counter32
			MAX-ACCESS read-only
			STATUS current
			DESCRIPTION
				"The number of MR-DVR Application Protocol Messages sent since the
				session was established. This number includes all re-transmissions."
			::= { avSessCurrentEntry 14 }

		
		-- 1.3.6.1.4.1.1429.5.1.2.2.5.1.2.1.15
		avSessCurrentRetransMsgs OBJECT-TYPE
			SYNTAX Counter32
			MAX-ACCESS read-only
			STATUS current
			DESCRIPTION
				"The number of MR-DVR Application Protocol Messages re-transmitted since the
				session was established."
			::= { avSessCurrentEntry 15 }

		
		-- 1.3.6.1.4.1.1429.5.1.2.2.5.1.2.1.16
		avSessCurrentOutStreamCtrlRqs OBJECT-TYPE
			SYNTAX Counter32
			MAX-ACCESS read-only
			STATUS current
			DESCRIPTION
				"The number of MR-DVR Application Protocol Stream Control Request Messages sent since the
				session was established. This number includes all re-transmissions."
			::= { avSessCurrentEntry 16 }

		
		-- 1.3.6.1.4.1.1429.5.1.2.2.5.1.2.1.17
		avSessCurrentInStreamCtrlRsps OBJECT-TYPE
			SYNTAX Counter32
			MAX-ACCESS read-only
			STATUS current
			DESCRIPTION
				"The number of MR-DVR Application Protocol Stream Control Response Messages received since the
				session was established. This number includes all re-transmissions."
			::= { avSessCurrentEntry 17 }

		
		-- 1.3.6.1.4.1.1429.5.1.2.2.5.1.2.1.18
		avSessCurrentInStreamCtrlRqs OBJECT-TYPE
			SYNTAX Counter32
			MAX-ACCESS read-only
			STATUS current
			DESCRIPTION
				"The number of MR-DVR Application Protocol Stream Control Request Messages received since the
				session was established. This number includes all re-transmissions."
			::= { avSessCurrentEntry 18 }

		
		-- 1.3.6.1.4.1.1429.5.1.2.2.5.1.2.1.19
		avSessCurrentOutStreamCtrlRsps OBJECT-TYPE
			SYNTAX Counter32
			MAX-ACCESS read-only
			STATUS current
			DESCRIPTION
				"The number of MR-DVR Application Protocol Stream Control Response Messages sent since the
				session was established. This number includes all re-transmissions."
			::= { avSessCurrentEntry 19 }

		
		-- 1.3.6.1.4.1.1429.5.1.2.2.5.1.2.1.20
		avSessCurrentOutStreamDoneEvts OBJECT-TYPE
			SYNTAX Counter32
			MAX-ACCESS read-only
			STATUS current
			DESCRIPTION
				"The number of MR-DVR Application Protocol Stream Done Event Messages sent since the
				session was initialized. This number includes all re-transmissions."
			::= { avSessCurrentEntry 20 }

		
		-- 1.3.6.1.4.1.1429.5.1.2.2.5.1.2.1.21
		avSessCurrentInStreamDoneRsps OBJECT-TYPE
			SYNTAX Counter32
			MAX-ACCESS read-only
			STATUS current
			DESCRIPTION
				"The number of MR-DVR Application Protocol Stream Done Response Messages received since the
				session was established. This number includes all re-transmissions."
			::= { avSessCurrentEntry 21 }

		
		-- 1.3.6.1.4.1.1429.5.1.2.2.5.1.2.1.22
		avSessCurrentInStreamDoneEvts OBJECT-TYPE
			SYNTAX Counter32
			MAX-ACCESS read-only
			STATUS current
			DESCRIPTION
				"The number of MR-DVR Application Protocol Stream Done Event Messages received since the
				session was established. This number includes all re-transmissions."
			::= { avSessCurrentEntry 22 }

		
		-- 1.3.6.1.4.1.1429.5.1.2.2.5.1.2.1.23
		avSessCurrentOutStreamDoneRsps OBJECT-TYPE
			SYNTAX Counter32
			MAX-ACCESS read-only
			STATUS current
			DESCRIPTION
				"The number of MR-DVR Application Protocol Stream Done Response Messages sent since the
				session was established. This number includes all re-transmissions."
			::= { avSessCurrentEntry 23 }

		
		-- 1.3.6.1.4.1.1429.5.1.2.2.5.1.2.1.24
		avSessCurrentOutStreamStatEvts OBJECT-TYPE
			SYNTAX Counter32
			MAX-ACCESS read-only
			STATUS current
			DESCRIPTION
				"The number of MR-DVR Application Protocol Stream Status Event Messages sent since the
				session was established. This number includes all re-transmissions."
			::= { avSessCurrentEntry 24 }

		
		-- 1.3.6.1.4.1.1429.5.1.2.2.5.1.2.1.25
		avSessCurrentInStreamStatEvts OBJECT-TYPE
			SYNTAX Counter32
			MAX-ACCESS read-only
			STATUS current
			DESCRIPTION
				"The number of MR-DVR Application Protocol Stream Status Event Messages received since the
				session was established. This number includes all re-transmissions."
			::= { avSessCurrentEntry 25 }

		
		-- 1.3.6.1.4.1.1429.5.1.2.2.4.2
		mrdvrAvSessHistory OBJECT-IDENTITY
			STATUS current
			DESCRIPTION 
				"A history of past sessions."
			::= { mrdvrAvSessions 2 }

		
		-- 1.3.6.1.4.1.1429.5.1.2.2.4.2.1
		avSessHistoryLimitsTable OBJECT-TYPE
			SYNTAX SEQUENCE OF AvSessHistoryLimitsEntry
			MAX-ACCESS not-accessible
			STATUS current
			DESCRIPTION
				"Entity limits regarding session history."
			::= { mrdvrAvSessHistory 1 }

		
		-- 1.3.6.1.4.1.1429.5.1.2.2.5.2.3.1
		avSessHistoryLimitsEntry OBJECT-TYPE
			SYNTAX AvSessHistoryLimitsEntry
			MAX-ACCESS not-accessible
			STATUS current
			DESCRIPTION
				"An entry in the table."
			INDEX { avSessHistoryLimitsEntityId }
			::= { avSessHistoryLimitsTable 1 }

		
		AvSessHistoryLimitsEntry ::=
			SEQUENCE { 
				avSessHistoryLimitsEntityId
					Unsigned32,
				avSessHistoryLimitsMaxCount
					Integer32
			 }

		-- 1.3.6.1.4.1.1429.5.1.2.2.5.2.3.1.1
		avSessHistoryLimitsEntityId OBJECT-TYPE
			SYNTAX Unsigned32
			MAX-ACCESS read-only
			STATUS current
			DESCRIPTION
				"The indentification number of the entity that reports MR-DVR A/V Session information.
				This uniquely distinguishes this entity from all other such entities on this station.
				This value should correspond to an application or service executing on the station."
			::= { avSessHistoryLimitsEntry 1 }

		
		-- 1.3.6.1.4.1.1429.5.1.2.2.5.2.3.1.2
		avSessHistoryLimitsMaxCount OBJECT-TYPE
			SYNTAX Integer32
			MAX-ACCESS read-only
			STATUS current
			DESCRIPTION
				"The maximum number of entries possible in the entity's contribution
				to the avSessHistoryTable."
			::= { avSessHistoryLimitsEntry 2 }

		
		-- 1.3.6.1.4.1.1429.5.1.2.2.4.2.2
		avSessHistoryCount OBJECT-TYPE
			SYNTAX Integer32
			MAX-ACCESS read-only
			STATUS deprecated
			DESCRIPTION
				"DEPRECATED! The number of entries in the avSessHistoryTable"
			::= { mrdvrAvSessHistory 2 }

		
		-- 1.3.6.1.4.1.1429.5.1.2.2.4.2.3
		avSessHistoryTable OBJECT-TYPE
			SYNTAX SEQUENCE OF AvSessHistoryEntry
			MAX-ACCESS not-accessible
			STATUS current
			DESCRIPTION
				"The table of previous MR-DVR A/V Sessions."
			::= { mrdvrAvSessHistory 3 }

		
		-- 1.3.6.1.4.1.1429.5.1.2.2.5.2.5.1
		avSessHistoryEntry OBJECT-TYPE
			SYNTAX AvSessHistoryEntry
			MAX-ACCESS not-accessible
			STATUS current
			DESCRIPTION
				"A previous MR-DVR A/V Session."
			INDEX { avSessHistoryEntityId, avSessHistoryEntryNum }
			::= { avSessHistoryTable 1 }

		
		AvSessHistoryEntry ::=
			SEQUENCE { 
				avSessHistoryEntityId
					Unsigned32,
				avSessHistoryEntryNum
					Integer32,
				avSessHistoryId
					OCTET STRING,
				avSessHistoryRole
					INTEGER,
				avSessHistoryStartTime
					DhctTimeStampType,
				avSessHistoryMode
					INTEGER,
				avSessHistoryRecordingState
					INTEGER,
				avSessHistoryPlayScale
					INTEGER,
				avSessHistoryNpt
					Integer32,
				avSessHistoryEndNpt
					Integer32,
				avSessHistoryFormat
					INTEGER,
				avSessHistoryProgramNum
					Integer32,
				avSessHistoryInMsgs
					Counter32,
				avSessHistoryOutMsgs
					Counter32,
				avSessHistoryRetransMsgs
					Counter32,
				avSessHistoryOutStreamCtrlRqs
					Counter32,
				avSessHistoryInStreamCtrlRsps
					Counter32,
				avSessHistoryInStreamCtrlRqs
					Counter32,
				avSessHistoryOutStreamCtrlRsps
					Counter32,
				avSessHistoryOutStreamDoneEvts
					Counter32,
				avSessHistoryInStreamDoneRsps
					Counter32,
				avSessHistoryInStreamDoneEvts
					Counter32,
				avSessHistoryOutStreamDoneRsps
					Counter32,
				avSessHistoryOutStreamStatEvts
					Counter32,
				avSessHistoryInStreamStatEvts
					Counter32,
				avSessHistoryEndTime
					DhctTimeStampType,
				avSessHistoryEndReason
					INTEGER
			 }

		-- 1.3.6.1.4.1.1429.5.1.2.2.5.2.5.1.1
		avSessHistoryEntityId OBJECT-TYPE
			SYNTAX Unsigned32
			MAX-ACCESS read-only
			STATUS current
			DESCRIPTION
				"The indentification number of the entity that reports MR-DVR A/V Session information.
				This uniquely distinguishes this entity from all other such entities on this station.
				This value should correspond to an application or service executing on the station."
			::= { avSessHistoryEntry 1 }

		
		-- 1.3.6.1.4.1.1429.5.1.2.2.5.2.5.1.2
		avSessHistoryEntryNum OBJECT-TYPE
			SYNTAX Integer32 (1..255)
			MAX-ACCESS read-only
			STATUS current
			DESCRIPTION
				"A unique number that distinguishes this session from others within the
				scope of a single avSessHistoryEntityId value."
			::= { avSessHistoryEntry 2 }

		
		-- 1.3.6.1.4.1.1429.5.1.2.2.5.2.5.1.3
		avSessHistoryId OBJECT-TYPE
			SYNTAX OCTET STRING
			MAX-ACCESS read-only
			STATUS current
			DESCRIPTION
				"The In-Home Session ID associated with this MR-DVR A/V Session."
			::= { avSessHistoryEntry 3 }

		
		-- 1.3.6.1.4.1.1429.5.1.2.2.5.2.5.1.4
		avSessHistoryRole OBJECT-TYPE
			SYNTAX INTEGER
				{
				client(1),
				server(2)
				}
			MAX-ACCESS read-only
			STATUS current
			DESCRIPTION
				"For this session, was this station acting as the client or the server"
			::= { avSessHistoryEntry 4 }

		
		-- 1.3.6.1.4.1.1429.5.1.2.2.5.2.5.1.5
		avSessHistoryStartTime OBJECT-TYPE
			SYNTAX DhctTimeStampType
			MAX-ACCESS read-only
			STATUS current
			DESCRIPTION
				"The time the station considered this session established.
				
				The epoch for this time value is January 1, 1970, 12:00:00AM GMT."
			::= { avSessHistoryEntry 5 }

		
		-- 1.3.6.1.4.1.1429.5.1.2.2.5.2.5.1.6
		avSessHistoryMode OBJECT-TYPE
			SYNTAX INTEGER
				{
				play(1),
				stop(2),
				pause(3)
				}
			MAX-ACCESS read-only
			STATUS current
			DESCRIPTION
				"The MR-DVR A/V Session mode."
			::= { avSessHistoryEntry 6 }

		
		-- 1.3.6.1.4.1.1429.5.1.2.2.5.2.5.1.7
		avSessHistoryRecordingState OBJECT-TYPE
			SYNTAX INTEGER
				{
				notRecording(1),
				recording(2)
				}
			MAX-ACCESS read-only
			STATUS current
			DESCRIPTION
				"Indicates if the program was being recorded.
				
				notRecording = The program was not being recorded by the server
				recording    = The program was being recorded by the server
				"
			::= { avSessHistoryEntry 7 }

		
		-- 1.3.6.1.4.1.1429.5.1.2.2.5.2.5.1.8
		avSessHistoryPlayScale OBJECT-TYPE
			SYNTAX INTEGER
				{
				forward(1),
				pause(2),
				stepForward(3),
				stepReverse(4),
				fastForward1(11),
				fastForward2(12),
				fastForward3(13),
				fastReverse1(21),
				fastReverse2(22),
				fastReverse3(23),
				slowForward1(41),
				slowReverse1(81)
				}
			MAX-ACCESS read-only
			STATUS current
			DESCRIPTION
				"The speed scale of the associated stream."
			::= { avSessHistoryEntry 8 }

		
		-- 1.3.6.1.4.1.1429.5.1.2.2.5.2.5.1.9
		avSessHistoryNpt OBJECT-TYPE
			SYNTAX Integer32
			UNITS "milli-seconds"
			MAX-ACCESS read-only
			STATUS current
			DESCRIPTION
				"The Normal Play Time indicating the position in the associated stream when the session
				was terminated.
				"
			::= { avSessHistoryEntry 9 }

		
		-- 1.3.6.1.4.1.1429.5.1.2.2.5.2.5.1.10
		avSessHistoryEndNpt OBJECT-TYPE
			SYNTAX Integer32
			UNITS "milli-seconds"
			MAX-ACCESS read-only
			STATUS current
			DESCRIPTION
				"The Normal Play Time indicating the end position in the associated stream."
			::= { avSessHistoryEntry 10 }

		
		-- 1.3.6.1.4.1.1429.5.1.2.2.5.2.5.1.11
		avSessHistoryFormat OBJECT-TYPE
			SYNTAX INTEGER
				{
				sd(1),
				hd(2)
				}
			MAX-ACCESS read-only
			STATUS current
			DESCRIPTION
				"The format of the content in the stream:
				sd = Standard Definition
				hd = High Definition"
			::= { avSessHistoryEntry 11 }

		
		-- 1.3.6.1.4.1.1429.5.1.2.2.5.2.5.1.12
		avSessHistoryProgramNum OBJECT-TYPE
			SYNTAX Integer32
			MAX-ACCESS read-only
			STATUS current
			DESCRIPTION
				"The program number associated with the MR-DVR A/V Session."
			::= { avSessHistoryEntry 12 }

		
		-- 1.3.6.1.4.1.1429.5.1.2.2.5.2.5.1.13
		avSessHistoryInMsgs OBJECT-TYPE
			SYNTAX Counter32
			MAX-ACCESS read-only
			STATUS current
			DESCRIPTION
				"The number of MR-DVR Application Protocol Messages received during the session."
			::= { avSessHistoryEntry 13 }

		
		-- 1.3.6.1.4.1.1429.5.1.2.2.5.2.5.1.14
		avSessHistoryOutMsgs OBJECT-TYPE
			SYNTAX Counter32
			MAX-ACCESS read-only
			STATUS current
			DESCRIPTION
				"The number of MR-DVR Application Protocol Messages sent during the session.
				This number includes all re-transmissions."
			::= { avSessHistoryEntry 14 }

		
		-- 1.3.6.1.4.1.1429.5.1.2.2.5.2.5.1.15
		avSessHistoryRetransMsgs OBJECT-TYPE
			SYNTAX Counter32
			MAX-ACCESS read-only
			STATUS current
			DESCRIPTION
				"The number of MR-DVR Application Protocol Messages re-transmitted during the session."
			::= { avSessHistoryEntry 15 }

		
		-- 1.3.6.1.4.1.1429.5.1.2.2.5.2.5.1.16
		avSessHistoryOutStreamCtrlRqs OBJECT-TYPE
			SYNTAX Counter32
			MAX-ACCESS read-only
			STATUS current
			DESCRIPTION
				"The number of MR-DVR Application Protocol Stream Control Request Messages sent during 
				the session. This number includes all re-transmissions."
			::= { avSessHistoryEntry 16 }

		
		-- 1.3.6.1.4.1.1429.5.1.2.2.5.2.5.1.17
		avSessHistoryInStreamCtrlRsps OBJECT-TYPE
			SYNTAX Counter32
			MAX-ACCESS read-only
			STATUS current
			DESCRIPTION
				"The number of MR-DVR Application Protocol Stream Control Response Messages received 
				during the session. This number includes all re-transmissions."
			::= { avSessHistoryEntry 17 }

		
		-- 1.3.6.1.4.1.1429.5.1.2.2.5.2.5.1.18
		avSessHistoryInStreamCtrlRqs OBJECT-TYPE
			SYNTAX Counter32
			MAX-ACCESS read-only
			STATUS current
			DESCRIPTION
				"The number of MR-DVR Application Protocol Stream Control Request Messages received 
				during the session. This number includes all re-transmissions."
			::= { avSessHistoryEntry 18 }

		
		-- 1.3.6.1.4.1.1429.5.1.2.2.5.2.5.1.19
		avSessHistoryOutStreamCtrlRsps OBJECT-TYPE
			SYNTAX Counter32
			MAX-ACCESS read-only
			STATUS current
			DESCRIPTION
				"The number of MR-DVR Application Protocol Stream Control Response Messages sent 
				during the session. This number includes all re-transmissions."
			::= { avSessHistoryEntry 19 }

		
		-- 1.3.6.1.4.1.1429.5.1.2.2.5.2.5.1.20
		avSessHistoryOutStreamDoneEvts OBJECT-TYPE
			SYNTAX Counter32
			MAX-ACCESS read-only
			STATUS current
			DESCRIPTION
				"The number of MR-DVR Application Protocol Stream Done Event Messages sent 
				during the session. This number includes all re-transmissions."
			::= { avSessHistoryEntry 20 }

		
		-- 1.3.6.1.4.1.1429.5.1.2.2.5.2.5.1.21
		avSessHistoryInStreamDoneRsps OBJECT-TYPE
			SYNTAX Counter32
			MAX-ACCESS read-only
			STATUS current
			DESCRIPTION
				"The number of MR-DVR Application Protocol Stream Done Response Messages received 
				during the session. This number includes all re-transmissions."
			::= { avSessHistoryEntry 21 }

		
		-- 1.3.6.1.4.1.1429.5.1.2.2.5.2.5.1.22
		avSessHistoryInStreamDoneEvts OBJECT-TYPE
			SYNTAX Counter32
			MAX-ACCESS read-only
			STATUS current
			DESCRIPTION
				"The number of MR-DVR Application Protocol Stream Done Event Messages received 
				during the session. This number includes all re-transmissions."
			::= { avSessHistoryEntry 22 }

		
		-- 1.3.6.1.4.1.1429.5.1.2.2.5.2.5.1.23
		avSessHistoryOutStreamDoneRsps OBJECT-TYPE
			SYNTAX Counter32
			MAX-ACCESS read-only
			STATUS current
			DESCRIPTION
				"The number of MR-DVR Application Protocol Stream Done Response Messages sent 
				during the session. This number includes all re-transmissions."
			::= { avSessHistoryEntry 23 }

		
		-- 1.3.6.1.4.1.1429.5.1.2.2.5.2.5.1.24
		avSessHistoryOutStreamStatEvts OBJECT-TYPE
			SYNTAX Counter32
			MAX-ACCESS read-only
			STATUS current
			DESCRIPTION
				"The number of MR-DVR Application Protocol Stream Status Event Messages sent 
				during the session. This number includes all re-transmissions."
			::= { avSessHistoryEntry 24 }

		
		-- 1.3.6.1.4.1.1429.5.1.2.2.5.2.5.1.25
		avSessHistoryInStreamStatEvts OBJECT-TYPE
			SYNTAX Counter32
			MAX-ACCESS read-only
			STATUS current
			DESCRIPTION
				"The number of MR-DVR Application Protocol Stream Status Event Messages received 
				during the session. This number includes all re-transmissions."
			::= { avSessHistoryEntry 25 }

		
		-- 1.3.6.1.4.1.1429.5.1.2.2.5.2.5.1.26
		avSessHistoryEndTime OBJECT-TYPE
			SYNTAX DhctTimeStampType
			MAX-ACCESS read-only
			STATUS current
			DESCRIPTION
				"The time the station considered this session terminated.
				
				The epoch for this time value is January 1, 1970, 12:00:00AM GMT."
			::= { avSessHistoryEntry 26 }

		
		-- 1.3.6.1.4.1.1429.5.1.2.2.5.2.5.1.27
		avSessHistoryEndReason OBJECT-TYPE
			SYNTAX INTEGER
				{
				generalError(128),
				serviceNotAvailable(130),
				noSuchProgram(133),
				resourceConflict(134),
				invalidSession(135),
				clientInitiatedNormalTermination(254)
				}
			MAX-ACCESS read-only
			STATUS current
			DESCRIPTION
				"The reason that this station attributes for session termination."
			::= { avSessHistoryEntry 27 }

		
		-- 1.3.6.1.4.1.1429.5.1.2.3
		saMrdvrAppEvents OBJECT-IDENTITY
			STATUS current
			DESCRIPTION 
				"SA-MRDVRAPP-MIB events."
			::= { saMrdvrAppMib 3 }

		
		-- 1.3.6.1.4.1.1429.5.1.2.3.0
		saMrdvrAppEventsV2 OBJECT-IDENTITY
			STATUS current
			DESCRIPTION 
				"For SNMP V1 Compliance"
			::= { saMrdvrAppEvents 0 }

		
	
	END

--
-- SA-MRDVRAPP-MIB.mib
--
