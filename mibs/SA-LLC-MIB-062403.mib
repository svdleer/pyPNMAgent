--
-- SA-LLC-MIB.my
-- MIB generated by MG-SOFT Visual MIB Builder Version 4.0 Build 349
-- Wednesday, June 15, 2005 at 14:27:17
--

-- Scientific-Atlanta Proprietary Information
-- 
-- 
-- Copyright 2005 Scientific-Atlanta, Inc.
-- 
-- All rights reserved.
-- 
-- 
-- Unauthorized copying and distribution are 
-- prohibited. No part of this MIB may be reprinted, 
-- reproduced or utilized in any form or by any electronic, 
-- mechanical, or other means, now known or
-- hereafter invented, including photocopying 
-- and recording, or using any information storage
-- and retrieval system, without permission in writing
-- from Scientific-Atlanta, Inc.
-- 
--  SA-LLC-MIB.mib
-- MIB generated by MG-SOFT Visual MIB Builder Version 4.0 Build 349
-- Thursday, October 28, 2004 at 10:39:53
-- 

	SA-LLC-MIB DEFINITIONS ::= BEGIN
 
		IMPORTS
			ifIndex, DisplayString			
				FROM RFC1213-MIB			
			saLlcMib			
				FROM SA-DBDSGEN-MIB			
			saModules			
				FROM SCIATL-COMMON-MIB			
			TimeTicks, Integer32, Counter32, BITS, OBJECT-TYPE, 
			MODULE-IDENTITY, OBJECT-IDENTITY			
				FROM SNMPv2-SMI;
	
	
--  1.3.6.1.4.1.1429.7.1.10
-- June 24, 2003 at 09:58 GMT
-- October 28, 2004 at 10:38 GMT
-- October 05, 2004 at 16:13 GMT
		-- 1.3.6.1.4.1.1429.7.1.10
		saLlcMibModule MODULE-IDENTITY 
			LAST-UPDATED "200306240958Z"		-- June 24, 2003 at 09:58 GMT
			ORGANIZATION 
				"Scientific-Atlanta"
			CONTACT-INFO 
				"DBDS Software Engineering & Architecture
				Scientific-Atlanta
				5030 Sugarloaf Parkway
				Lawrencville, GA 30044
				"
			DESCRIPTION 
				"The Scientific-Atlanta MIB module for IEEE 802.2 LLC.
				
				This module Copyright 2003-2004 Scientific Atlanta.
				
				
				"
			REVISION "200410051613Z"		-- October 05, 2004 at 16:13 GMT
			DESCRIPTION 
				"Corrected numbering of 
				saLlcConnAggEstablishedConnectSuccess
				from (.2 to .1)"
			REVISION "200410281038Z"		-- October 28, 2004 at 10:38 GMT
			DESCRIPTION 
				"Removed size restriction on saLlcStationName"
			::= { saModules 10 }

		
	
--
-- Type definitions
--
	
--  Type definitions
-- 
		SaLLCServices ::= BITS
			{
			type1(0),
			type2(1),
			type3Initiate(2),
			type3ReceiveData(3),
			type3ReturnData(4)
			}

	
--
-- Node definitions
--
	
--  Node definitions
-- 
-- 1.3.6.1.4.1.1429.9.1.3.1
		-- 1.3.6.1.4.1.1429.9.1.3.1
		saLlcConf OBJECT-IDENTITY
			STATUS current
			DESCRIPTION 
				"Conformance"
			::= { saLlcMib 1 }

		
--  1.3.6.1.4.1.1429.9.1.3.1.1
		-- 1.3.6.1.4.1.1429.9.1.3.1.1
		saLlcGroups OBJECT-IDENTITY
			STATUS current
			DESCRIPTION 
				"Object groups for the SA-LLC-MIB"
			::= { saLlcConf 1 }

		
--  1.3.6.1.4.1.1429.9.1.3.1.2
		-- 1.3.6.1.4.1.1429.9.1.3.1.2
		saLlcCompls OBJECT-IDENTITY
			STATUS current
			DESCRIPTION 
				"Compliance descriptions for the SA-LLC-MIB"
			::= { saLlcConf 2 }

		
--  1.3.6.1.4.1.1429.9.1.3.2
		-- 1.3.6.1.4.1.1429.9.1.3.2
		saLlcObjs OBJECT-IDENTITY
			STATUS current
			DESCRIPTION 
				"The objects of the SA-LLC-MIB module."
			::= { saLlcMib 2 }

		
--  1.3.6.1.4.1.1429.9.1.3.2.1
		-- 1.3.6.1.4.1.1429.9.1.3.2.1
		saLlcStation OBJECT-IDENTITY
			STATUS current
			DESCRIPTION 
				"Contains the definition of all attributes that are common to 
				the LLC station as a whole, regardless of which LLC operations are supported."
			::= { saLlcObjs 1 }

		
--  1.3.6.1.4.1.1429.9.1.3.2.1.1
		-- 1.3.6.1.4.1.1429.9.1.3.2.1.1
		saLlcStationTable OBJECT-TYPE
			SYNTAX SEQUENCE OF SaLlcStationEntry
			MAX-ACCESS not-accessible
			STATUS current
			DESCRIPTION
				"Contains the definition of all attributes that are common to 
				the LLC station as a whole, regardless of which LLC operations are supported."
			::= { saLlcStation 1 }

		
--  1.3.6.1.4.1.1429.9.1.3.2.1.1.1
		-- 1.3.6.1.4.1.1429.9.1.3.2.1.1.1
		saLlcStationEntry OBJECT-TYPE
			SYNTAX SaLlcStationEntry
			MAX-ACCESS not-accessible
			STATUS current
			DESCRIPTION
				"An entry in the table."
			INDEX { ifIndex, saLlcStationSubIndex }
			::= { saLlcStationTable 1 }

		
		SaLlcStationEntry ::=
			SEQUENCE { 
				saLlcStationSubIndex
					Integer32,
				saLlcStationName
					DisplayString,
				saLlcStationMaximumLsapsConfigured
					Integer32,
				saLlcStationNumberOfActiveLsaps
					Integer32,
				saLlcStationSupportedServicesTypes
					SaLLCServices,
				saLlcStationStatus
					INTEGER
			 }

--  1.3.6.1.4.1.1429.9.1.3.2.1.1.1.1
		-- 1.3.6.1.4.1.1429.9.1.3.2.1.1.1.1
		saLlcStationSubIndex OBJECT-TYPE
			SYNTAX Integer32 (1..65535)
			MAX-ACCESS read-only
			STATUS current
			DESCRIPTION
				"If the LLC supports multiple stations per ifIndex,
				then this value serves to differentiate between each
				entry within the domain of a single ifIndex value.
				
				If this feature is not supported, then this value is 0. "
			::= { saLlcStationEntry 1 }

		
--  1.3.6.1.4.1.1429.9.1.3.2.1.1.1.2
		-- 1.3.6.1.4.1.1429.9.1.3.2.1.1.1.2
		saLlcStationName OBJECT-TYPE
			SYNTAX DisplayString
			MAX-ACCESS read-only
			STATUS current
			DESCRIPTION
				"A descriptive name for the station."
			::= { saLlcStationEntry 2 }

		
--  1.3.6.1.4.1.1429.9.1.3.2.1.1.1.3
		-- 1.3.6.1.4.1.1429.9.1.3.2.1.1.1.3
		saLlcStationMaximumLsapsConfigured OBJECT-TYPE
			SYNTAX Integer32
			MAX-ACCESS read-only
			STATUS current
			DESCRIPTION
				"The maximum number of LSAPs that can be supported at
				any moment in time by the port."
			::= { saLlcStationEntry 3 }

		
--  1.3.6.1.4.1.1429.9.1.3.2.1.1.1.4
		-- 1.3.6.1.4.1.1429.9.1.3.2.1.1.1.4
		saLlcStationNumberOfActiveLsaps OBJECT-TYPE
			SYNTAX Integer32
			MAX-ACCESS read-only
			STATUS current
			DESCRIPTION
				"The number of active LSAPs on the port."
			::= { saLlcStationEntry 4 }

		
--  1.3.6.1.4.1.1429.9.1.3.2.1.1.1.5
		-- 1.3.6.1.4.1.1429.9.1.3.2.1.1.1.5
		saLlcStationSupportedServicesTypes OBJECT-TYPE
			SYNTAX SaLLCServices
			MAX-ACCESS read-only
			STATUS current
			DESCRIPTION
				"The type or types of service supported (i.e., Type 1, Type 2, Type 3.)"
			::= { saLlcStationEntry 5 }

		
--  1.3.6.1.4.1.1429.9.1.3.2.1.1.1.6
		-- 1.3.6.1.4.1.1429.9.1.3.2.1.1.1.6
		saLlcStationStatus OBJECT-TYPE
			SYNTAX INTEGER
				{
				up(1),
				down(2),
				other(3)
				}
			MAX-ACCESS read-only
			STATUS current
			DESCRIPTION
				"This attribute allows a manager to determine what state (UP, DOWN, etc.)
				the lLCStation entity is in."
			::= { saLlcStationEntry 6 }

		
--  1.3.6.1.4.1.1429.9.1.3.2.1.2
		-- 1.3.6.1.4.1.1429.9.1.3.2.1.2
		saLlcDupAddressTable OBJECT-TYPE
			SYNTAX SEQUENCE OF SaLlcDupAddressEntry
			MAX-ACCESS not-accessible
			STATUS current
			DESCRIPTION
				"Duplicate station address detection"
			REFERENCE
				"see 6.9.2.1"
			::= { saLlcStation 2 }

		
--  1.3.6.1.4.1.1429.9.1.3.2.1.2.1
		-- 1.3.6.1.4.1.1429.9.1.3.2.1.2.1
		saLlcDupAddressEntry OBJECT-TYPE
			SYNTAX SaLlcDupAddressEntry
			MAX-ACCESS not-accessible
			STATUS current
			DESCRIPTION
				"An entry in the table."
			INDEX { ifIndex, saLlcStationSubIndex }
			::= { saLlcDupAddressTable 1 }

		
		SaLlcDupAddressEntry ::=
			SEQUENCE { 
				saLlcDupAddressType1MaximumRetryCount
					Integer32,
				saLlcDupAddressType1AcknowledgementTimeoutValue
					Integer32
			 }

--  1.3.6.1.4.1.1429.9.1.3.2.1.2.1.1
		-- 1.3.6.1.4.1.1429.9.1.3.2.1.2.1.1
		saLlcDupAddressType1MaximumRetryCount OBJECT-TYPE
			SYNTAX Integer32
			MAX-ACCESS read-only
			STATUS current
			DESCRIPTION
				"The maximum number of retries during duplicate address checking
				"
			REFERENCE
				"(see 6.9.2.2 and 6.9.2.3)"
			::= { saLlcDupAddressEntry 1 }

		
--  1.3.6.1.4.1.1429.9.1.3.2.1.2.1.2
		-- 1.3.6.1.4.1.1429.9.1.3.2.1.2.1.2
		saLlcDupAddressType1AcknowledgementTimeoutValue OBJECT-TYPE
			SYNTAX Integer32
			MAX-ACCESS read-only
			STATUS current
			DESCRIPTION
				"The timeout value of the Ack timer, which is measured in milliseconds.
				"
			REFERENCE
				"(6.9.2.2 and 6.9.2.3)"
			::= { saLlcDupAddressEntry 2 }

		
--  1.3.6.1.4.1.1429.9.1.3.2.1.3
		-- 1.3.6.1.4.1.1429.9.1.3.2.1.3
		saLlcPdusDiscardedTable OBJECT-TYPE
			SYNTAX SEQUENCE OF SaLlcPdusDiscardedEntry
			MAX-ACCESS not-accessible
			STATUS current
			DESCRIPTION
				"Counts discarded PDUs."
			::= { saLlcStation 3 }

		
--  1.3.6.1.4.1.1429.9.1.3.2.1.3.1
		-- 1.3.6.1.4.1.1429.9.1.3.2.1.3.1
		saLlcPdusDiscardedEntry OBJECT-TYPE
			SYNTAX SaLlcPdusDiscardedEntry
			MAX-ACCESS not-accessible
			STATUS current
			DESCRIPTION
				"An entry in the table."
			INDEX { ifIndex, saLlcStationSubIndex }
			::= { saLlcPdusDiscardedTable 1 }

		
		SaLlcPdusDiscardedEntry ::=
			SEQUENCE { 
				saLlcPdusDiscardedInactiveLsap
					Counter32,
				saLlcPdusDiscarded
					Counter32
			 }

--  1.3.6.1.4.1.1429.9.1.3.2.1.3.1.1
		-- 1.3.6.1.4.1.1429.9.1.3.2.1.3.1.1
		saLlcPdusDiscardedInactiveLsap OBJECT-TYPE
			SYNTAX Counter32
			MAX-ACCESS read-only
			STATUS current
			DESCRIPTION
				"This counts the number of PDUs discarded due to the specification
				of an inactive DSAP."
			::= { saLlcPdusDiscardedEntry 1 }

		
--  1.3.6.1.4.1.1429.9.1.3.2.1.3.1.2
		-- 1.3.6.1.4.1.1429.9.1.3.2.1.3.1.2
		saLlcPdusDiscarded OBJECT-TYPE
			SYNTAX Counter32
			MAX-ACCESS read-only
			STATUS current
			DESCRIPTION
				"Provides a total count of invalid PDUs that are discarded. A Discarded
				(invalid) PDU shall be defined as one that meets at least one of
				the following conditions:
				1) It is identified as such by the PHY or the MAC sublayer.
				2) It is not an integral number of octets in length.
				3) It does not contain two properly formatted address fields, one control
				field, and optionally an information field in their proper order.
				4) Its length is less than 3 octets (one-octet control field) or 4 octets
				(two-octet control field)."
			::= { saLlcPdusDiscardedEntry 2 }

		
--  1.3.6.1.4.1.1429.9.1.3.2.4
		-- 1.3.6.1.4.1.1429.9.1.3.2.4
		saLlcSap OBJECT-IDENTITY
			STATUS current
			DESCRIPTION 
				"Contains the definition of all attributes associated with an LLC SAP 
				that are independent of the LLC types of operation that are supported."
			::= { saLlcObjs 4 }

		
--  1.3.6.1.4.1.1429.9.1.3.2.4.1
		-- 1.3.6.1.4.1.1429.9.1.3.2.4.1
		saLlcSapTable OBJECT-TYPE
			SYNTAX SEQUENCE OF SaLlcSapEntry
			MAX-ACCESS not-accessible
			STATUS current
			DESCRIPTION
				"Contains the definition of all attributes associated with an LLC SAP 
				that are independent of the LLC types of operation that are supported."
			::= { saLlcSap 1 }

		
--  1.3.6.1.4.1.1429.9.1.3.2.4.1.1
		-- 1.3.6.1.4.1.1429.9.1.3.2.4.1.1
		saLlcSapEntry OBJECT-TYPE
			SYNTAX SaLlcSapEntry
			MAX-ACCESS not-accessible
			STATUS current
			DESCRIPTION
				"An entry in the table."
			INDEX { ifIndex, saLlcStationSubIndex, saLlcSapSapAddress }
			::= { saLlcSapTable 1 }

		
		SaLlcSapEntry ::=
			SEQUENCE { 
				saLlcSapSapAddress
					OCTET STRING,
				saLlcSapRde
					INTEGER
			 }

--  1.3.6.1.4.1.1429.9.1.3.2.4.1.1.1
		-- 1.3.6.1.4.1.1429.9.1.3.2.4.1.1.1
		saLlcSapSapAddress OBJECT-TYPE
			SYNTAX OCTET STRING
			MAX-ACCESS read-only
			STATUS current
			DESCRIPTION
				"The individual LLC address identifying this LSAP. 
				This is the SAP number and does not include the MAC Address."
			::= { saLlcSapEntry 1 }

		
--  1.3.6.1.4.1.1429.9.1.3.2.4.1.1.2
		-- 1.3.6.1.4.1.1429.9.1.3.2.4.1.1.2
		saLlcSapRde OBJECT-TYPE
			SYNTAX INTEGER
				{
				rdeNotSupported(1),
				rdeSupported(2)
				}
			MAX-ACCESS read-only
			STATUS current
			DESCRIPTION
				"Indicates if RDE is supported by this SAP."
			::= { saLlcSapEntry 2 }

		
--  1.3.6.1.4.1.1429.9.1.3.2.5
		-- 1.3.6.1.4.1.1429.9.1.3.2.5
		saLlcConnless OBJECT-IDENTITY
			STATUS current
			DESCRIPTION 
				"Attributes that are associated with the LLC connectionless service."
			::= { saLlcObjs 5 }

		
--  1.3.6.1.4.1.1429.9.1.3.2.5.1
		-- 1.3.6.1.4.1.1429.9.1.3.2.5.1
		saLlcConnlessTable OBJECT-TYPE
			SYNTAX SEQUENCE OF SaLlcConnlessEntry
			MAX-ACCESS not-accessible
			STATUS current
			DESCRIPTION
				"Attributes that are associated with the LLC connectionless service."
			::= { saLlcConnless 1 }

		
--  1.3.6.1.4.1.1429.9.1.3.2.5.1.1
		-- 1.3.6.1.4.1.1429.9.1.3.2.5.1.1
		saLlcConnlessEntry OBJECT-TYPE
			SYNTAX SaLlcConnlessEntry
			MAX-ACCESS not-accessible
			STATUS current
			DESCRIPTION
				"An entry in the table."
			AUGMENTS { saLlcSapEntry }
			::= { saLlcConnlessTable 1 }

		
		SaLlcConnlessEntry ::=
			SEQUENCE { 
				saLlcConnlessMaxLlcInformationFieldSize
					Integer32,
				saLlcConnlessTestReceivedAbbResponse
					Counter32,
				saLlcConnlessTestReceivedCommand
					Counter32,
				saLlcConnlessTestReceivedResponse
					Counter32,
				saLlcConnlessTestSentAbbResponse
					Counter32,
				saLlcConnlessTestSentCommand
					Counter32,
				saLlcConnlessTestSentResponse
					Counter32,
				saLlcConnlessUiReceived
					Counter32,
				saLlcConnlessUiSent
					Counter32,
				saLlcConnlessXidReceivedCommand
					Counter32,
				saLlcConnlessXidReceivedResponse
					Counter32,
				saLlcConnlessXidSentCommand
					Counter32,
				saLlcConnlessXidSentResponse
					Counter32
			 }

--  1.3.6.1.4.1.1429.9.1.3.2.5.1.1.1
		-- 1.3.6.1.4.1.1429.9.1.3.2.5.1.1.1
		saLlcConnlessMaxLlcInformationFieldSize OBJECT-TYPE
			SYNTAX Integer32
			MAX-ACCESS read-only
			STATUS current
			DESCRIPTION
				"The maximum length LSDU that the LSAP will accommodate."
			::= { saLlcConnlessEntry 1 }

		
--  1.3.6.1.4.1.1429.9.1.3.2.5.1.1.2
		-- 1.3.6.1.4.1.1429.9.1.3.2.5.1.1.2
		saLlcConnlessTestReceivedAbbResponse OBJECT-TYPE
			SYNTAX Counter32
			MAX-ACCESS read-only
			STATUS current
			DESCRIPTION
				"Provides a count of TEST responses received by this LSAP
				without the LSDU due to limited resources at the remote station."
			::= { saLlcConnlessEntry 2 }

		
--  1.3.6.1.4.1.1429.9.1.3.2.5.1.1.3
		-- 1.3.6.1.4.1.1429.9.1.3.2.5.1.1.3
		saLlcConnlessTestReceivedCommand OBJECT-TYPE
			SYNTAX Counter32
			MAX-ACCESS read-only
			STATUS current
			DESCRIPTION
				"Provides a count of TEST commands received from the MAC sublayer by
				this LSAP. This includes commands received with any group address
				recognized by this LSAP."
			::= { saLlcConnlessEntry 3 }

		
--  1.3.6.1.4.1.1429.9.1.3.2.5.1.1.4
		-- 1.3.6.1.4.1.1429.9.1.3.2.5.1.1.4
		saLlcConnlessTestReceivedResponse OBJECT-TYPE
			SYNTAX Counter32
			MAX-ACCESS read-only
			STATUS current
			DESCRIPTION
				"Provides a count of TEST responses received from the MAC sublayer by
				this LSAP."
			::= { saLlcConnlessEntry 4 }

		
--  1.3.6.1.4.1.1429.9.1.3.2.5.1.1.5
		-- 1.3.6.1.4.1.1429.9.1.3.2.5.1.1.5
		saLlcConnlessTestSentAbbResponse OBJECT-TYPE
			SYNTAX Counter32
			MAX-ACCESS read-only
			STATUS current
			DESCRIPTION
				"Provides a count of TEST responses that were delivered to the
				MAC without the LSDU data due to limited resources."
			::= { saLlcConnlessEntry 5 }

		
--  1.3.6.1.4.1.1429.9.1.3.2.5.1.1.6
		-- 1.3.6.1.4.1.1429.9.1.3.2.5.1.1.6
		saLlcConnlessTestSentCommand OBJECT-TYPE
			SYNTAX Counter32
			MAX-ACCESS read-only
			STATUS current
			DESCRIPTION
				"Provides a count of TEST commands sent to the MAC sublayer by this
				LSAP."
			::= { saLlcConnlessEntry 6 }

		
--  1.3.6.1.4.1.1429.9.1.3.2.5.1.1.7
		-- 1.3.6.1.4.1.1429.9.1.3.2.5.1.1.7
		saLlcConnlessTestSentResponse OBJECT-TYPE
			SYNTAX Counter32
			MAX-ACCESS read-only
			STATUS current
			DESCRIPTION
				"Provides a count of TEST responses sent to the MAC sublayer by
				this LSAP."
			::= { saLlcConnlessEntry 7 }

		
--  1.3.6.1.4.1.1429.9.1.3.2.5.1.1.8
		-- 1.3.6.1.4.1.1429.9.1.3.2.5.1.1.8
		saLlcConnlessUiReceived OBJECT-TYPE
			SYNTAX Counter32
			MAX-ACCESS read-only
			STATUS current
			DESCRIPTION
				"Provides a count of user data PDUs that were received by the LSAP from
				the MAC sublayer and passed to the user layer. This includes commands
				received with group addresses of which this LSAP is a member."
			::= { saLlcConnlessEntry 8 }

		
--  1.3.6.1.4.1.1429.9.1.3.2.5.1.1.9
		-- 1.3.6.1.4.1.1429.9.1.3.2.5.1.1.9
		saLlcConnlessUiSent OBJECT-TYPE
			SYNTAX Counter32
			MAX-ACCESS read-only
			STATUS current
			DESCRIPTION
				"Provides a count of user data PDUs that were accepted by the LSAP from
				the user layer and delivered to the MAC sublayer."
			::= { saLlcConnlessEntry 9 }

		
--  1.3.6.1.4.1.1429.9.1.3.2.5.1.1.10
		-- 1.3.6.1.4.1.1429.9.1.3.2.5.1.1.10
		saLlcConnlessXidReceivedCommand OBJECT-TYPE
			SYNTAX Counter32
			MAX-ACCESS read-only
			STATUS current
			DESCRIPTION
				"Provides a count of XID commands received from the MAC sublayer by this
				LSAP. This includes commands received with any group address recognized
				by this LSAP."
			::= { saLlcConnlessEntry 10 }

		
--  1.3.6.1.4.1.1429.9.1.3.2.5.1.1.11
		-- 1.3.6.1.4.1.1429.9.1.3.2.5.1.1.11
		saLlcConnlessXidReceivedResponse OBJECT-TYPE
			SYNTAX Counter32
			MAX-ACCESS read-only
			STATUS current
			DESCRIPTION
				"!Provides a count of XID responses received from the MAC sublayer by this
				LSAP."
			::= { saLlcConnlessEntry 11 }

		
--  1.3.6.1.4.1.1429.9.1.3.2.5.1.1.12
		-- 1.3.6.1.4.1.1429.9.1.3.2.5.1.1.12
		saLlcConnlessXidSentCommand OBJECT-TYPE
			SYNTAX Counter32
			MAX-ACCESS read-only
			STATUS current
			DESCRIPTION
				"Provides a count of XID commands sent to the MAC sublayer by
				this LSAP."
			::= { saLlcConnlessEntry 12 }

		
--  1.3.6.1.4.1.1429.9.1.3.2.5.1.1.13
		-- 1.3.6.1.4.1.1429.9.1.3.2.5.1.1.13
		saLlcConnlessXidSentResponse OBJECT-TYPE
			SYNTAX Counter32
			MAX-ACCESS read-only
			STATUS current
			DESCRIPTION
				"Provides a count of XID responses sent to the MAC sublayer by this
				LSAP."
			::= { saLlcConnlessEntry 13 }

		
--  1.3.6.1.4.1.1429.9.1.3.2.6
		-- 1.3.6.1.4.1.1429.9.1.3.2.6
		saLlcConnection OBJECT-IDENTITY
			STATUS current
			DESCRIPTION 
				"Attributes for type 2 connections."
			::= { saLlcObjs 6 }

		
--  1.3.6.1.4.1.1429.9.1.3.2.6.1
		-- 1.3.6.1.4.1.1429.9.1.3.2.6.1
		saLlcConnTable OBJECT-TYPE
			SYNTAX SEQUENCE OF SaLlcConnEntry
			MAX-ACCESS not-accessible
			STATUS current
			DESCRIPTION
				"Attributes each data link connection (for LLC Type 2 connections).
				One entry shall exist for each data link connection supported."
			::= { saLlcConnection 1 }

		
--  1.3.6.1.4.1.1429.9.1.3.2.6.1.1
		-- 1.3.6.1.4.1.1429.9.1.3.2.6.1.1
		saLlcConnEntry OBJECT-TYPE
			SYNTAX SaLlcConnEntry
			MAX-ACCESS not-accessible
			STATUS current
			DESCRIPTION
				"An entry in the table."
			INDEX { ifIndex, saLlcStationSubIndex, saLlcSapSapAddress, saLlcConnRemoteSap, saLlcConnRemoteMac
				 }
			::= { saLlcConnTable 1 }

		
		SaLlcConnEntry ::=
			SEQUENCE { 
				saLlcConnRemoteMac
					OCTET STRING,
				saLlcConnRemoteSap
					Integer32,
				saLlcConnMaximumRetransmissions
					Integer32,
				saLlcConnReceiveWindowSize
					Integer32,
				saLlcConnSendWindowSize
					Integer32,
				saLlcConnType2AcknowlegeTimeoutValue
					Integer32,
				saLlcConnType2BusyStateTimeoutValue
					Integer32,
				saLlcConnType2PbitTimeoutValue
					Integer32,
				saLlcConnType2RejectTimeoutValue
					Integer32
			 }

--  1.3.6.1.4.1.1429.9.1.3.2.6.1.1.1
		-- 1.3.6.1.4.1.1429.9.1.3.2.6.1.1.1
		saLlcConnRemoteMac OBJECT-TYPE
			SYNTAX OCTET STRING
			MAX-ACCESS read-only
			STATUS current
			DESCRIPTION
				"The MAC address of the remote station participating in 
				the connection."
			::= { saLlcConnEntry 1 }

		
--  1.3.6.1.4.1.1429.9.1.3.2.6.1.1.2
		-- 1.3.6.1.4.1.1429.9.1.3.2.6.1.1.2
		saLlcConnRemoteSap OBJECT-TYPE
			SYNTAX Integer32 (1..255)
			MAX-ACCESS read-only
			STATUS current
			DESCRIPTION
				"The number of the remote SAP participating in the connection."
			::= { saLlcConnEntry 2 }

		
--  1.3.6.1.4.1.1429.9.1.3.2.6.1.1.3
		-- 1.3.6.1.4.1.1429.9.1.3.2.6.1.1.3
		saLlcConnMaximumRetransmissions OBJECT-TYPE
			SYNTAX Integer32
			MAX-ACCESS read-write
			STATUS current
			DESCRIPTION
				"The number of times that the LLC Type 2 should attempt to realize a
				successful PDU transfer."
			::= { saLlcConnEntry 3 }

		
--  1.3.6.1.4.1.1429.9.1.3.2.6.1.1.4
		-- 1.3.6.1.4.1.1429.9.1.3.2.6.1.1.4
		saLlcConnReceiveWindowSize OBJECT-TYPE
			SYNTAX Integer32
			MAX-ACCESS read-write
			STATUS current
			DESCRIPTION
				"The value of the receive window."
			::= { saLlcConnEntry 4 }

		
--  1.3.6.1.4.1.1429.9.1.3.2.6.1.1.5
		-- 1.3.6.1.4.1.1429.9.1.3.2.6.1.1.5
		saLlcConnSendWindowSize OBJECT-TYPE
			SYNTAX Integer32
			MAX-ACCESS read-write
			STATUS current
			DESCRIPTION
				"The value of the send window."
			::= { saLlcConnEntry 5 }

		
--  1.3.6.1.4.1.1429.9.1.3.2.6.1.1.6
		-- 1.3.6.1.4.1.1429.9.1.3.2.6.1.1.6
		saLlcConnType2AcknowlegeTimeoutValue OBJECT-TYPE
			SYNTAX Integer32
			MAX-ACCESS read-write
			STATUS current
			DESCRIPTION
				"This attribute defines the time interval during which the LLC shall expect
				to receive an acknowledgment to one or more outstanding I PDUs or an
				expected response PDU to a sent unnumbered command PDU. This value is measured
				in milliseconds."
			REFERENCE
				"see 7.4.1, 7.4.3, 7.4.5, 7.5, 7.5.5, 7.5.9, 7.6,
				7.8.1.1, 7.9.2, 7.9.2.2, and 7.9.2.3"
			::= { saLlcConnEntry 6 }

		
--  1.3.6.1.4.1.1429.9.1.3.2.6.1.1.7
		-- 1.3.6.1.4.1.1429.9.1.3.2.6.1.1.7
		saLlcConnType2BusyStateTimeoutValue OBJECT-TYPE
			SYNTAX Integer32
			MAX-ACCESS read-write
			STATUS current
			DESCRIPTION
				"This attribute defines the time interval during which the LLC shall wait
				for an indication of the clearance of a busy condition at the other LLC.
				This time value is measured in milliseconds."
			REFERENCE
				"see 7.5.7, 7.5.9, 7.8.1.4,
				7.9.2, 7.9.2.2, and 7.9.2.3"
			::= { saLlcConnEntry 7 }

		
--  1.3.6.1.4.1.1429.9.1.3.2.6.1.1.8
		-- 1.3.6.1.4.1.1429.9.1.3.2.6.1.1.8
		saLlcConnType2PbitTimeoutValue OBJECT-TYPE
			SYNTAX Integer32
			MAX-ACCESS read-write
			STATUS current
			DESCRIPTION
				"The P-bit timer defines the time interval during which the LLC shall expect
				to receive a PDU with the F bit set to 1 in response to a sent Type
				2 command with the P bit set to 1. This value is measured in milliseconds."
			REFERENCE
				"see 7.5.9, 7.8.1.2, 7.9.2, 7.9.2.2, and 7.9.2.3"
			::= { saLlcConnEntry 8 }

		
--  1.3.6.1.4.1.1429.9.1.3.2.6.1.1.9
		-- 1.3.6.1.4.1.1429.9.1.3.2.6.1.1.9
		saLlcConnType2RejectTimeoutValue OBJECT-TYPE
			SYNTAX Integer32
			MAX-ACCESS read-write
			STATUS current
			DESCRIPTION
				"The Reject timer defines the time interval during which the LLC shall
				expect to receive a reply to a sent REJ PDU. This value is measured in
				milliseconds."
			REFERENCE
				"see 7.5.4, 7.8.1.3, 7.9.2, 7.9.2.2, and 7.9.2.3"
			::= { saLlcConnEntry 9 }

		
--  1.3.6.1.4.1.1429.9.1.3.2.6.2
		-- 1.3.6.1.4.1.1429.9.1.3.2.6.2
		saLlcConnStateTable OBJECT-TYPE
			SYNTAX SEQUENCE OF SaLlcConnStateEntry
			MAX-ACCESS not-accessible
			STATUS current
			DESCRIPTION
				"State information for the connection component."
			::= { saLlcConnection 2 }

		
--  1.3.6.1.4.1.1429.9.1.3.2.6.2.1
		-- 1.3.6.1.4.1.1429.9.1.3.2.6.2.1
		saLlcConnStateEntry OBJECT-TYPE
			SYNTAX SaLlcConnStateEntry
			MAX-ACCESS not-accessible
			STATUS current
			DESCRIPTION
				"An entry in the table."
			AUGMENTS { saLlcConnEntry }
			::= { saLlcConnStateTable 1 }

		
		SaLlcConnStateEntry ::=
			SEQUENCE { 
				saLlcConnStateState
					INTEGER,
				saLlcConnStateInitTime
					TimeTicks
			 }

--  1.3.6.1.4.1.1429.9.1.3.2.6.2.1.1
		-- 1.3.6.1.4.1.1429.9.1.3.2.6.2.1.1
		saLlcConnStateState OBJECT-TYPE
			SYNTAX INTEGER
				{
				adm(1),
				setup(2),
				normal(3),
				busy(4),
				reject(5),
				await(6),
				awaitBusy(7),
				awaitReject(8),
				dConn(9),
				reset(10),
				error(11),
				conn(12),
				resetCheck(13),
				resetWait(14)
				}
			MAX-ACCESS read-only
			STATUS current
			DESCRIPTION
				"The current state of the connection component as described by
				IEEE 802.2 Connection Component states."
			REFERENCE
				"see 7.9.2.1"
			::= { saLlcConnStateEntry 1 }

		
--  1.3.6.1.4.1.1429.9.1.3.2.6.2.1.2
		-- 1.3.6.1.4.1.1429.9.1.3.2.6.2.1.2
		saLlcConnStateInitTime OBJECT-TYPE
			SYNTAX TimeTicks
			MAX-ACCESS read-only
			STATUS current
			DESCRIPTION
				"The value of sysUpTime when the connection component was created."
			::= { saLlcConnStateEntry 2 }

		
--  1.3.6.1.4.1.1429.9.1.3.2.6.3
		-- 1.3.6.1.4.1.1429.9.1.3.2.6.3
		saLlcConnBusyTable OBJECT-TYPE
			SYNTAX SEQUENCE OF SaLlcConnBusyEntry
			MAX-ACCESS not-accessible
			STATUS current
			DESCRIPTION
				"Contains attributes that count instances of local or remote
				busy connections."
			::= { saLlcConnection 3 }

		
--  1.3.6.1.4.1.1429.9.1.3.2.6.3.1
		-- 1.3.6.1.4.1.1429.9.1.3.2.6.3.1
		saLlcConnBusyEntry OBJECT-TYPE
			SYNTAX SaLlcConnBusyEntry
			MAX-ACCESS not-accessible
			STATUS current
			DESCRIPTION
				"An entry in the table."
			AUGMENTS { saLlcConnEntry }
			::= { saLlcConnBusyTable 1 }

		
		SaLlcConnBusyEntry ::=
			SEQUENCE { 
				saLlcConnBusyLocalBusy
					Counter32,
				saLlcConnBusyRemoteBusy
					Counter32
			 }

--  1.3.6.1.4.1.1429.9.1.3.2.6.3.1.1
		-- 1.3.6.1.4.1.1429.9.1.3.2.6.3.1.1
		saLlcConnBusyLocalBusy OBJECT-TYPE
			SYNTAX Counter32
			MAX-ACCESS read-only
			STATUS current
			DESCRIPTION
				"Counts occurrences of entry into the busy condition."
			::= { saLlcConnBusyEntry 1 }

		
--  1.3.6.1.4.1.1429.9.1.3.2.6.3.1.2
		-- 1.3.6.1.4.1.1429.9.1.3.2.6.3.1.2
		saLlcConnBusyRemoteBusy OBJECT-TYPE
			SYNTAX Counter32
			MAX-ACCESS read-only
			STATUS current
			DESCRIPTION
				"Counts RNR PDUs received when the remote busy condition is not
				already set."
			::= { saLlcConnBusyEntry 2 }

		
--  1.3.6.1.4.1.1429.9.1.3.2.6.4
		-- 1.3.6.1.4.1.1429.9.1.3.2.6.4
		saLlcConnResetTable OBJECT-TYPE
			SYNTAX SEQUENCE OF SaLlcConnResetEntry
			MAX-ACCESS not-accessible
			STATUS current
			DESCRIPTION
				"Contains attributes that count instances of particular types
				of reset."
			::= { saLlcConnection 4 }

		
--  1.3.6.1.4.1.1429.9.1.3.2.6.4.1
		-- 1.3.6.1.4.1.1429.9.1.3.2.6.4.1
		saLlcConnResetEntry OBJECT-TYPE
			SYNTAX SaLlcConnResetEntry
			MAX-ACCESS not-accessible
			STATUS current
			DESCRIPTION
				"An entry in the table."
			AUGMENTS { saLlcConnEntry }
			::= { saLlcConnResetTable 1 }

		
		SaLlcConnResetEntry ::=
			SEQUENCE { 
				saLlcConnResetRemoteReset
					Counter32,
				saLlcConnResetLocalReset
					Counter32,
				saLlcConnResetProviderReset
					Counter32
			 }

--  1.3.6.1.4.1.1429.9.1.3.2.6.4.1.1
		-- 1.3.6.1.4.1.1429.9.1.3.2.6.4.1.1
		saLlcConnResetRemoteReset OBJECT-TYPE
			SYNTAX Counter32
			MAX-ACCESS read-only
			STATUS current
			DESCRIPTION
				"Counts instances of partner-initiated reset (SABME PDU received in a
				connected state)"
			::= { saLlcConnResetEntry 1 }

		
--  1.3.6.1.4.1.1429.9.1.3.2.6.4.1.2
		-- 1.3.6.1.4.1.1429.9.1.3.2.6.4.1.2
		saLlcConnResetLocalReset OBJECT-TYPE
			SYNTAX Counter32
			MAX-ACCESS read-only
			STATUS current
			DESCRIPTION
				"Counts instances of user request for reset while in a connected state."
			::= { saLlcConnResetEntry 2 }

		
--  1.3.6.1.4.1.1429.9.1.3.2.6.4.1.3
		-- 1.3.6.1.4.1.1429.9.1.3.2.6.4.1.3
		saLlcConnResetProviderReset OBJECT-TYPE
			SYNTAX Counter32
			MAX-ACCESS read-only
			STATUS current
			DESCRIPTION
				"Counts instances of provider-initiated reset due to FRMR PDU sent, FRMR
				received, or retry exhaustion."
			::= { saLlcConnResetEntry 3 }

		
--  1.3.6.1.4.1.1429.9.1.3.2.6.5
		-- 1.3.6.1.4.1.1429.9.1.3.2.6.5
		saLlcType2DiscTable OBJECT-TYPE
			SYNTAX SEQUENCE OF SaLlcType2DiscEntry
			MAX-ACCESS not-accessible
			STATUS current
			DESCRIPTION
				"Specifies a count of DISC PDUs either delivered or received from the MAC."
			::= { saLlcConnection 5 }

		
--  1.3.6.1.4.1.1429.9.1.3.2.6.5.1
		-- 1.3.6.1.4.1.1429.9.1.3.2.6.5.1
		saLlcType2DiscEntry OBJECT-TYPE
			SYNTAX SaLlcType2DiscEntry
			MAX-ACCESS not-accessible
			STATUS current
			DESCRIPTION
				"An entry in the table."
			AUGMENTS { saLlcConnEntry }
			::= { saLlcType2DiscTable 1 }

		
		SaLlcType2DiscEntry ::=
			SEQUENCE { 
				saLlcType2DiscReceivedDisc
					Counter32,
				saLlcType2DiscSentDisc
					Counter32
			 }

--  1.3.6.1.4.1.1429.9.1.3.2.6.5.1.1
		-- 1.3.6.1.4.1.1429.9.1.3.2.6.5.1.1
		saLlcType2DiscReceivedDisc OBJECT-TYPE
			SYNTAX Counter32
			MAX-ACCESS read-only
			STATUS current
			DESCRIPTION
				"Specifies a count of DISC PDUs received from the MAC and not
				discarded."
			::= { saLlcType2DiscEntry 1 }

		
--  1.3.6.1.4.1.1429.9.1.3.2.6.5.1.2
		-- 1.3.6.1.4.1.1429.9.1.3.2.6.5.1.2
		saLlcType2DiscSentDisc OBJECT-TYPE
			SYNTAX Counter32
			MAX-ACCESS read-only
			STATUS current
			DESCRIPTION
				"Specifies a count of DISC PDUs delivered to the MAC."
			::= { saLlcType2DiscEntry 2 }

		
--  1.3.6.1.4.1.1429.9.1.3.2.6.6
		-- 1.3.6.1.4.1.1429.9.1.3.2.6.6
		saLlcType2DmTable OBJECT-TYPE
			SYNTAX SEQUENCE OF SaLlcType2DmEntry
			MAX-ACCESS not-accessible
			STATUS current
			DESCRIPTION
				"Specifies a count of DM PDUs either delivered or received from
				the MAC."
			::= { saLlcConnection 6 }

		
--  1.3.6.1.4.1.1429.9.1.3.2.6.6.1
		-- 1.3.6.1.4.1.1429.9.1.3.2.6.6.1
		saLlcType2DmEntry OBJECT-TYPE
			SYNTAX SaLlcType2DmEntry
			MAX-ACCESS not-accessible
			STATUS current
			DESCRIPTION
				"An entry in the table."
			AUGMENTS { saLlcConnEntry }
			::= { saLlcType2DmTable 1 }

		
		SaLlcType2DmEntry ::=
			SEQUENCE { 
				saLlcType2DmReceivedDm
					Counter32,
				saLlcType2DmSentDm
					Counter32
			 }

--  1.3.6.1.4.1.1429.9.1.3.2.6.6.1.1
		-- 1.3.6.1.4.1.1429.9.1.3.2.6.6.1.1
		saLlcType2DmReceivedDm OBJECT-TYPE
			SYNTAX Counter32
			MAX-ACCESS read-only
			STATUS current
			DESCRIPTION
				"Specifies a count of DM PDUs received from the MAC and not
				discarded."
			::= { saLlcType2DmEntry 1 }

		
--  1.3.6.1.4.1.1429.9.1.3.2.6.6.1.2
		-- 1.3.6.1.4.1.1429.9.1.3.2.6.6.1.2
		saLlcType2DmSentDm OBJECT-TYPE
			SYNTAX Counter32
			MAX-ACCESS read-only
			STATUS current
			DESCRIPTION
				"Specifies a count of DM PDUs delivered to the MAC."
			::= { saLlcType2DmEntry 2 }

		
--  1.3.6.1.4.1.1429.9.1.3.2.6.7
		-- 1.3.6.1.4.1.1429.9.1.3.2.6.7
		saLlcType2FrmrTable OBJECT-TYPE
			SYNTAX SEQUENCE OF SaLlcType2FrmrEntry
			MAX-ACCESS not-accessible
			STATUS current
			DESCRIPTION
				"Specifies a count of FRMR PDUs delivered to the MAC and a
				count of FRMR PDUs received from the MAC and not discarded."
			::= { saLlcConnection 7 }

		
--  1.3.6.1.4.1.1429.9.1.3.2.6.7.1
		-- 1.3.6.1.4.1.1429.9.1.3.2.6.7.1
		saLlcType2FrmrEntry OBJECT-TYPE
			SYNTAX SaLlcType2FrmrEntry
			MAX-ACCESS not-accessible
			STATUS current
			DESCRIPTION
				"An entry in the table."
			AUGMENTS { saLlcConnEntry }
			::= { saLlcType2FrmrTable 1 }

		
		SaLlcType2FrmrEntry ::=
			SEQUENCE { 
				saLlcType2FrmrReceivedFrmr
					Counter32,
				saLlcType2FrmrSentFrmr
					Counter32
			 }

--  1.3.6.1.4.1.1429.9.1.3.2.6.7.1.1
		-- 1.3.6.1.4.1.1429.9.1.3.2.6.7.1.1
		saLlcType2FrmrReceivedFrmr OBJECT-TYPE
			SYNTAX Counter32
			MAX-ACCESS read-only
			STATUS current
			DESCRIPTION
				"Specifies a count of FRMR PDUs received from the MAC and not
				discarded."
			::= { saLlcType2FrmrEntry 1 }

		
--  1.3.6.1.4.1.1429.9.1.3.2.6.7.1.2
		-- 1.3.6.1.4.1.1429.9.1.3.2.6.7.1.2
		saLlcType2FrmrSentFrmr OBJECT-TYPE
			SYNTAX Counter32
			MAX-ACCESS read-only
			STATUS current
			DESCRIPTION
				"Specifies a count of FRMR PDUs delivered to the MAC."
			::= { saLlcType2FrmrEntry 2 }

		
--  1.3.6.1.4.1.1429.9.1.3.2.6.8
		-- 1.3.6.1.4.1.1429.9.1.3.2.6.8
		saLlcType2ITable OBJECT-TYPE
			SYNTAX SEQUENCE OF SaLlcType2IEntry
			MAX-ACCESS not-accessible
			STATUS current
			DESCRIPTION
				"Counts the number of I PDUs received
				and sent"
			::= { saLlcConnection 8 }

		
--  1.3.6.1.4.1.1429.9.1.3.2.6.8.1
		-- 1.3.6.1.4.1.1429.9.1.3.2.6.8.1
		saLlcType2IEntry OBJECT-TYPE
			SYNTAX SaLlcType2IEntry
			MAX-ACCESS not-accessible
			STATUS current
			DESCRIPTION
				"An entry in the table."
			AUGMENTS { saLlcConnEntry }
			::= { saLlcType2ITable 1 }

		
		SaLlcType2IEntry ::=
			SEQUENCE { 
				saLlcType2IReceivedI
					Counter32,
				saLlcType2ISentI
					Counter32
			 }

--  1.3.6.1.4.1.1429.9.1.3.2.6.8.1.1
		-- 1.3.6.1.4.1.1429.9.1.3.2.6.8.1.1
		saLlcType2IReceivedI OBJECT-TYPE
			SYNTAX Counter32
			MAX-ACCESS read-only
			STATUS current
			DESCRIPTION
				"Specifies a count of I PDUs received from the MAC and passed to the LLC
				user."
			::= { saLlcType2IEntry 1 }

		
--  1.3.6.1.4.1.1429.9.1.3.2.6.8.1.2
		-- 1.3.6.1.4.1.1429.9.1.3.2.6.8.1.2
		saLlcType2ISentI OBJECT-TYPE
			SYNTAX Counter32
			MAX-ACCESS read-only
			STATUS current
			DESCRIPTION
				"Specifies a count of I PDUs delivered to the MAC."
			::= { saLlcType2IEntry 2 }

		
--  1.3.6.1.4.1.1429.9.1.3.2.6.9
		-- 1.3.6.1.4.1.1429.9.1.3.2.6.9
		saLlcType2AckTable OBJECT-TYPE
			SYNTAX SEQUENCE OF SaLlcType2AckEntry
			MAX-ACCESS not-accessible
			STATUS current
			DESCRIPTION
				"Contains attributes that count acknowledgments sent and received."
			::= { saLlcConnection 9 }

		
--  1.3.6.1.4.1.1429.9.1.3.2.6.9.1
		-- 1.3.6.1.4.1.1429.9.1.3.2.6.9.1
		saLlcType2AckEntry OBJECT-TYPE
			SYNTAX SaLlcType2AckEntry
			MAX-ACCESS not-accessible
			STATUS current
			DESCRIPTION
				"An entry in the table."
			AUGMENTS { saLlcConnEntry }
			::= { saLlcType2AckTable 1 }

		
		SaLlcType2AckEntry ::=
			SEQUENCE { 
				saLlcType2AckReceivedAcks
					Counter32,
				saLlcType2AckSentAcks
					Counter32
			 }

--  1.3.6.1.4.1.1429.9.1.3.2.6.9.1.1
		-- 1.3.6.1.4.1.1429.9.1.3.2.6.9.1.1
		saLlcType2AckReceivedAcks OBJECT-TYPE
			SYNTAX Counter32
			MAX-ACCESS read-only
			STATUS current
			DESCRIPTION
				"Counts I PDUs acknowledged by connection partner"
			::= { saLlcType2AckEntry 1 }

		
--  1.3.6.1.4.1.1429.9.1.3.2.6.9.1.2
		-- 1.3.6.1.4.1.1429.9.1.3.2.6.9.1.2
		saLlcType2AckSentAcks OBJECT-TYPE
			SYNTAX Counter32
			MAX-ACCESS read-only
			STATUS current
			DESCRIPTION
				"Counts acknowledgments sent for received I PDUs."
			::= { saLlcType2AckEntry 2 }

		
--  1.3.6.1.4.1.1429.9.1.3.2.6.10
		-- 1.3.6.1.4.1.1429.9.1.3.2.6.10
		saLlcType2PdusTable OBJECT-TYPE
			SYNTAX SEQUENCE OF SaLlcType2PdusEntry
			MAX-ACCESS not-accessible
			STATUS current
			DESCRIPTION
				"Contains attributes that count a number of different
				types of discarded PDUs."
			::= { saLlcConnection 10 }

		
--  1.3.6.1.4.1.1429.9.1.3.2.6.10.1
		-- 1.3.6.1.4.1.1429.9.1.3.2.6.10.1
		saLlcType2PdusEntry OBJECT-TYPE
			SYNTAX SaLlcType2PdusEntry
			MAX-ACCESS not-accessible
			STATUS current
			DESCRIPTION
				"An entry in the table."
			AUGMENTS { saLlcConnEntry }
			::= { saLlcType2PdusTable 1 }

		
		SaLlcType2PdusEntry ::=
			SEQUENCE { 
				saLlcType2PdusDiscarded1
					Counter32,
				saLlcType2PdusDiscarded2
					Counter32,
				saLlcType2PdusRetransmissions
					Counter32
			 }

--  1.3.6.1.4.1.1429.9.1.3.2.6.10.1.1
		-- 1.3.6.1.4.1.1429.9.1.3.2.6.10.1.1
		saLlcType2PdusDiscarded1 OBJECT-TYPE
			SYNTAX Counter32
			MAX-ACCESS read-only
			STATUS current
			DESCRIPTION
				"Specifies a count of PDUs discarded due to insufficient resources for
				this connection."
			::= { saLlcType2PdusEntry 1 }

		
--  1.3.6.1.4.1.1429.9.1.3.2.6.10.1.2
		-- 1.3.6.1.4.1.1429.9.1.3.2.6.10.1.2
		saLlcType2PdusDiscarded2 OBJECT-TYPE
			SYNTAX Counter32
			MAX-ACCESS read-only
			STATUS current
			DESCRIPTION
				"Specifies a count of I PDUs discarded due to unexpected or invalid sequence
				number for this connection."
			::= { saLlcType2PdusEntry 2 }

		
--  1.3.6.1.4.1.1429.9.1.3.2.6.10.1.3
		-- 1.3.6.1.4.1.1429.9.1.3.2.6.10.1.3
		saLlcType2PdusRetransmissions OBJECT-TYPE
			SYNTAX Counter32
			MAX-ACCESS read-only
			STATUS current
			DESCRIPTION
				"Specifies a count of the number of times the Type 2 LLC service
				retransmitted PDUs for this connection."
			::= { saLlcType2PdusEntry 3 }

		
--  1.3.6.1.4.1.1429.9.1.3.2.6.11
		-- 1.3.6.1.4.1.1429.9.1.3.2.6.11
		saLlcType2RejTable OBJECT-TYPE
			SYNTAX SEQUENCE OF SaLlcType2RejEntry
			MAX-ACCESS not-accessible
			STATUS current
			DESCRIPTION
				"Contains two attributes to count sent and received REJ PDUs."
			REFERENCE
				"see 7.5.9"
			::= { saLlcConnection 11 }

		
--  1.3.6.1.4.1.1429.9.1.3.2.6.11.1
		-- 1.3.6.1.4.1.1429.9.1.3.2.6.11.1
		saLlcType2RejEntry OBJECT-TYPE
			SYNTAX SaLlcType2RejEntry
			MAX-ACCESS not-accessible
			STATUS current
			DESCRIPTION
				"An entry in the table."
			AUGMENTS { saLlcConnEntry }
			::= { saLlcType2RejTable 1 }

		
		SaLlcType2RejEntry ::=
			SEQUENCE { 
				saLlcType2RejReceivedRej
					Counter32,
				saLlcType2RejSentRej
					Counter32
			 }

--  1.3.6.1.4.1.1429.9.1.3.2.6.11.1.1
		-- 1.3.6.1.4.1.1429.9.1.3.2.6.11.1.1
		saLlcType2RejReceivedRej OBJECT-TYPE
			SYNTAX Counter32
			MAX-ACCESS read-only
			STATUS current
			DESCRIPTION
				"Specifies a count of REJ PDUs received from the MAC and not discarded."
			::= { saLlcType2RejEntry 1 }

		
--  1.3.6.1.4.1.1429.9.1.3.2.6.11.1.2
		-- 1.3.6.1.4.1.1429.9.1.3.2.6.11.1.2
		saLlcType2RejSentRej OBJECT-TYPE
			SYNTAX Counter32
			MAX-ACCESS read-only
			STATUS current
			DESCRIPTION
				"Specifies a count of REJ PDUs delivered to the MAC."
			::= { saLlcType2RejEntry 2 }

		
--  1.3.6.1.4.1.1429.9.1.3.2.6.12
		-- 1.3.6.1.4.1.1429.9.1.3.2.6.12
		saLlcType2RnrTable OBJECT-TYPE
			SYNTAX SEQUENCE OF SaLlcType2RnrEntry
			MAX-ACCESS not-accessible
			STATUS current
			DESCRIPTION
				"Contains attributes that specify the count of RNR
				PDUs either delivered or received from the MAC."
			::= { saLlcConnection 12 }

		
--  1.3.6.1.4.1.1429.9.1.3.2.6.12.1
		-- 1.3.6.1.4.1.1429.9.1.3.2.6.12.1
		saLlcType2RnrEntry OBJECT-TYPE
			SYNTAX SaLlcType2RnrEntry
			MAX-ACCESS not-accessible
			STATUS current
			DESCRIPTION
				"An entry in the table."
			AUGMENTS { saLlcConnEntry }
			::= { saLlcType2RnrTable 1 }

		
		SaLlcType2RnrEntry ::=
			SEQUENCE { 
				saLlcType2RnrReceivedRnr
					Counter32,
				saLlcType2RnrSentRnr
					Counter32
			 }

--  1.3.6.1.4.1.1429.9.1.3.2.6.12.1.1
		-- 1.3.6.1.4.1.1429.9.1.3.2.6.12.1.1
		saLlcType2RnrReceivedRnr OBJECT-TYPE
			SYNTAX Counter32
			MAX-ACCESS read-only
			STATUS current
			DESCRIPTION
				"Specifies a count of RNR PDUs received from the MAC and not discarded."
			::= { saLlcType2RnrEntry 1 }

		
--  1.3.6.1.4.1.1429.9.1.3.2.6.12.1.2
		-- 1.3.6.1.4.1.1429.9.1.3.2.6.12.1.2
		saLlcType2RnrSentRnr OBJECT-TYPE
			SYNTAX Counter32
			MAX-ACCESS read-only
			STATUS current
			DESCRIPTION
				"Specifies a count of RNR PDUs delivered to the MAC."
			::= { saLlcType2RnrEntry 2 }

		
--  1.3.6.1.4.1.1429.9.1.3.2.6.13
		-- 1.3.6.1.4.1.1429.9.1.3.2.6.13
		saLlcType2RrTable OBJECT-TYPE
			SYNTAX SEQUENCE OF SaLlcType2RrEntry
			MAX-ACCESS not-accessible
			STATUS current
			DESCRIPTION
				"Contains attributes that specify the count of RR
				PDUs either delivered or received from the MAC."
			::= { saLlcConnection 13 }

		
--  1.3.6.1.4.1.1429.9.1.3.2.6.13.1
		-- 1.3.6.1.4.1.1429.9.1.3.2.6.13.1
		saLlcType2RrEntry OBJECT-TYPE
			SYNTAX SaLlcType2RrEntry
			MAX-ACCESS not-accessible
			STATUS current
			DESCRIPTION
				"An entry in the table."
			AUGMENTS { saLlcConnEntry }
			::= { saLlcType2RrTable 1 }

		
		SaLlcType2RrEntry ::=
			SEQUENCE { 
				saLlcType2RrReceivedRr
					Counter32,
				saLlcType2RrSentRr
					Counter32
			 }

--  1.3.6.1.4.1.1429.9.1.3.2.6.13.1.1
		-- 1.3.6.1.4.1.1429.9.1.3.2.6.13.1.1
		saLlcType2RrReceivedRr OBJECT-TYPE
			SYNTAX Counter32
			MAX-ACCESS read-only
			STATUS current
			DESCRIPTION
				"Specifies a count of RR PDUs received from the MAC and not discarded."
			::= { saLlcType2RrEntry 1 }

		
--  1.3.6.1.4.1.1429.9.1.3.2.6.13.1.2
		-- 1.3.6.1.4.1.1429.9.1.3.2.6.13.1.2
		saLlcType2RrSentRr OBJECT-TYPE
			SYNTAX Counter32
			MAX-ACCESS read-only
			STATUS current
			DESCRIPTION
				"Specifies a count of RR PDUs delivered to the MAC."
			::= { saLlcType2RrEntry 2 }

		
--  1.3.6.1.4.1.1429.9.1.3.2.6.14
		-- 1.3.6.1.4.1.1429.9.1.3.2.6.14
		saLlcType2SabmeTable OBJECT-TYPE
			SYNTAX SEQUENCE OF SaLlcType2SabmeEntry
			MAX-ACCESS not-accessible
			STATUS current
			DESCRIPTION
				"Contains attributes that specify the count of SABME
				PDUs either delivered or received from the MAC."
			::= { saLlcConnection 14 }

		
--  1.3.6.1.4.1.1429.9.1.3.2.6.14.1
		-- 1.3.6.1.4.1.1429.9.1.3.2.6.14.1
		saLlcType2SabmeEntry OBJECT-TYPE
			SYNTAX SaLlcType2SabmeEntry
			MAX-ACCESS not-accessible
			STATUS current
			DESCRIPTION
				"An entry in the table."
			AUGMENTS { saLlcConnEntry }
			::= { saLlcType2SabmeTable 1 }

		
		SaLlcType2SabmeEntry ::=
			SEQUENCE { 
				saLlcType2SabmeReceivedSabme
					Counter32,
				saLlcType2SabmeSentSabme
					Counter32
			 }

--  1.3.6.1.4.1.1429.9.1.3.2.6.14.1.1
		-- 1.3.6.1.4.1.1429.9.1.3.2.6.14.1.1
		saLlcType2SabmeReceivedSabme OBJECT-TYPE
			SYNTAX Counter32
			MAX-ACCESS read-only
			STATUS current
			DESCRIPTION
				"Specifies a count of SABME PDUs received from the MAC and not discarded."
			::= { saLlcType2SabmeEntry 1 }

		
--  1.3.6.1.4.1.1429.9.1.3.2.6.14.1.2
		-- 1.3.6.1.4.1.1429.9.1.3.2.6.14.1.2
		saLlcType2SabmeSentSabme OBJECT-TYPE
			SYNTAX Counter32
			MAX-ACCESS read-only
			STATUS current
			DESCRIPTION
				"Specifies a count of SABME PDUs delivered to the MAC."
			::= { saLlcType2SabmeEntry 2 }

		
--  1.3.6.1.4.1.1429.9.1.3.2.6.15
		-- 1.3.6.1.4.1.1429.9.1.3.2.6.15
		saLlcType2UaTable OBJECT-TYPE
			SYNTAX SEQUENCE OF SaLlcType2UaEntry
			MAX-ACCESS not-accessible
			STATUS current
			DESCRIPTION
				"Contains attributes that specify the count of UA
				PDUs either delivered or received from the MAC."
			::= { saLlcConnection 15 }

		
--  1.3.6.1.4.1.1429.9.1.3.2.6.15.1
		-- 1.3.6.1.4.1.1429.9.1.3.2.6.15.1
		saLlcType2UaEntry OBJECT-TYPE
			SYNTAX SaLlcType2UaEntry
			MAX-ACCESS not-accessible
			STATUS current
			DESCRIPTION
				"An entry in the table."
			AUGMENTS { saLlcConnEntry }
			::= { saLlcType2UaTable 1 }

		
		SaLlcType2UaEntry ::=
			SEQUENCE { 
				saLlcType2UaReceivedUa
					Counter32,
				saLlcType2UaSentUa
					Counter32
			 }

--  1.3.6.1.4.1.1429.9.1.3.2.6.15.1.1
		-- 1.3.6.1.4.1.1429.9.1.3.2.6.15.1.1
		saLlcType2UaReceivedUa OBJECT-TYPE
			SYNTAX Counter32
			MAX-ACCESS read-only
			STATUS current
			DESCRIPTION
				"Specifies a count of UA PDUs received from the MAC and not discarded."
			::= { saLlcType2UaEntry 1 }

		
--  1.3.6.1.4.1.1429.9.1.3.2.6.15.1.2
		-- 1.3.6.1.4.1.1429.9.1.3.2.6.15.1.2
		saLlcType2UaSentUa OBJECT-TYPE
			SYNTAX Counter32
			MAX-ACCESS read-only
			STATUS current
			DESCRIPTION
				"Specifies a count of UA PDUs delivered to the MAC."
			::= { saLlcType2UaEntry 2 }

		
--  1.3.6.1.4.1.1429.9.1.3.2.6.16
		-- 1.3.6.1.4.1.1429.9.1.3.2.6.16
		saLlcType2ViolationTable OBJECT-TYPE
			SYNTAX SEQUENCE OF SaLlcType2ViolationEntry
			MAX-ACCESS not-accessible
			STATUS current
			DESCRIPTION
				"Contains an attribute to count type 2 violations."
			::= { saLlcConnection 16 }

		
--  1.3.6.1.4.1.1429.9.1.3.2.6.16.1
		-- 1.3.6.1.4.1.1429.9.1.3.2.6.16.1
		saLlcType2ViolationEntry OBJECT-TYPE
			SYNTAX SaLlcType2ViolationEntry
			MAX-ACCESS not-accessible
			STATUS current
			DESCRIPTION
				"An entry in the table."
			AUGMENTS { saLlcConnEntry }
			::= { saLlcType2ViolationTable 1 }

		
		SaLlcType2ViolationEntry ::=
			SEQUENCE { 
				saLlcType2Violation
					Counter32
			 }

--  1.3.6.1.4.1.1429.9.1.3.2.6.16.1.1
		-- 1.3.6.1.4.1.1429.9.1.3.2.6.16.1.1
		saLlcType2Violation OBJECT-TYPE
			SYNTAX Counter32
			MAX-ACCESS read-only
			STATUS current
			DESCRIPTION
				"Provides a count of the number of protocol violations detected by this
				connection. Protocol violations include the following:
				1) those that result in the LLC entity sending an FRMR frame
				2) those that result in a data link resetting action to be initiated by
				the receiving LLC entity itself."
			::= { saLlcType2ViolationEntry 1 }

		
--  1.3.6.1.4.1.1429.9.1.3.2.7
		-- 1.3.6.1.4.1.1429.9.1.3.2.7
		saLlcConnAggregate OBJECT-IDENTITY
			STATUS current
			DESCRIPTION 
				"Description."
			::= { saLlcObjs 7 }

		
--  1.3.6.1.4.1.1429.9.1.3.2.7.1
		-- 1.3.6.1.4.1.1429.9.1.3.2.7.1
		saLlcConnAggEstablishmentTable OBJECT-TYPE
			SYNTAX SEQUENCE OF SaLlcConnAggEstablishmentEntry
			MAX-ACCESS not-accessible
			STATUS current
			DESCRIPTION
				"Contains attributes that track connection establishment statistics."
			::= { saLlcConnAggregate 1 }

		
--  1.3.6.1.4.1.1429.9.1.3.2.7.1.1
		-- 1.3.6.1.4.1.1429.9.1.3.2.7.1.1
		saLlcConnAggEstablishmentEntry OBJECT-TYPE
			SYNTAX SaLlcConnAggEstablishmentEntry
			MAX-ACCESS not-accessible
			STATUS current
			DESCRIPTION
				"An entry in the table."
			AUGMENTS { saLlcSapEntry }
			::= { saLlcConnAggEstablishmentTable 1 }

		
		SaLlcConnAggEstablishmentEntry ::=
			SEQUENCE { 
				saLlcConnAggEstablishConnectSuccess
					Counter32,
				saLlcConnAggEstablishConnectFails
					Counter32
			 }

--  1.3.6.1.4.1.1429.9.1.3.2.7.1.1.1
		-- 1.3.6.1.4.1.1429.9.1.3.2.7.1.1.1
		saLlcConnAggEstablishConnectSuccess OBJECT-TYPE
			SYNTAX Counter32
			MAX-ACCESS read-only
			STATUS current
			DESCRIPTION
				"The number of times a connection was successfully established
				for all connection components since the SAP was initialized"
			::= { saLlcConnAggEstablishmentEntry 1 }

		
--  1.3.6.1.4.1.1429.9.1.3.2.7.1.1.2
		-- 1.3.6.1.4.1.1429.9.1.3.2.7.1.1.2
		saLlcConnAggEstablishConnectFails OBJECT-TYPE
			SYNTAX Counter32
			MAX-ACCESS read-only
			STATUS current
			DESCRIPTION
				"The number of times a connection was attempted, but failed
				for all connection components since the SAP was initialized"
			::= { saLlcConnAggEstablishmentEntry 2 }

		
--  1.3.6.1.4.1.1429.9.1.3.2.7.2
		-- 1.3.6.1.4.1.1429.9.1.3.2.7.2
		saLlcConnAggBusyTable OBJECT-TYPE
			SYNTAX SEQUENCE OF SaLlcConnAggBusyEntry
			MAX-ACCESS not-accessible
			STATUS current
			DESCRIPTION
				"Contains attributes that count instances of local or remote
				busy connections for all connection components since the SAP was initialized."
			::= { saLlcConnAggregate 2 }

		
--  1.3.6.1.4.1.1429.9.1.3.2.7.2.1
		-- 1.3.6.1.4.1.1429.9.1.3.2.7.2.1
		saLlcConnAggBusyEntry OBJECT-TYPE
			SYNTAX SaLlcConnAggBusyEntry
			MAX-ACCESS not-accessible
			STATUS current
			DESCRIPTION
				"An entry in the table."
			AUGMENTS { saLlcSapEntry }
			::= { saLlcConnAggBusyTable 1 }

		
		SaLlcConnAggBusyEntry ::=
			SEQUENCE { 
				saLlcConnAggBusyLocalBusy
					Counter32,
				saLlcConnAggBusyRemoteBusy
					Counter32
			 }

--  1.3.6.1.4.1.1429.9.1.3.2.7.2.1.1
		-- 1.3.6.1.4.1.1429.9.1.3.2.7.2.1.1
		saLlcConnAggBusyLocalBusy OBJECT-TYPE
			SYNTAX Counter32
			MAX-ACCESS read-only
			STATUS current
			DESCRIPTION
				"Counts occurrences of entry into the busy condition
				for all connection components since the SAP was initialized."
			::= { saLlcConnAggBusyEntry 1 }

		
--  1.3.6.1.4.1.1429.9.1.3.2.7.2.1.2
		-- 1.3.6.1.4.1.1429.9.1.3.2.7.2.1.2
		saLlcConnAggBusyRemoteBusy OBJECT-TYPE
			SYNTAX Counter32
			MAX-ACCESS read-only
			STATUS current
			DESCRIPTION
				"Counts RNR PDUs received when the remote busy condition is not
				already set for all connection components since the SAP was initialized."
			::= { saLlcConnAggBusyEntry 2 }

		
--  1.3.6.1.4.1.1429.9.1.3.2.7.3
		-- 1.3.6.1.4.1.1429.9.1.3.2.7.3
		saLlcConnAggResetTable OBJECT-TYPE
			SYNTAX SEQUENCE OF SaLlcConnAggResetEntry
			MAX-ACCESS not-accessible
			STATUS current
			DESCRIPTION
				"Contains attributes that count instances of particular types
				of reset for all connection components since the SAP was initialized."
			::= { saLlcConnAggregate 3 }

		
--  1.3.6.1.4.1.1429.9.1.3.2.7.3.1
		-- 1.3.6.1.4.1.1429.9.1.3.2.7.3.1
		saLlcConnAggResetEntry OBJECT-TYPE
			SYNTAX SaLlcConnAggResetEntry
			MAX-ACCESS not-accessible
			STATUS current
			DESCRIPTION
				"An entry in the table."
			AUGMENTS { saLlcSapEntry }
			::= { saLlcConnAggResetTable 1 }

		
		SaLlcConnAggResetEntry ::=
			SEQUENCE { 
				saLlcConnAggResetRemoteReset
					Counter32,
				saLlcConnAggResetLocalReset
					Counter32,
				saLlcConnAggResetProviderReset
					Counter32
			 }

--  1.3.6.1.4.1.1429.9.1.3.2.7.3.1.1
		-- 1.3.6.1.4.1.1429.9.1.3.2.7.3.1.1
		saLlcConnAggResetRemoteReset OBJECT-TYPE
			SYNTAX Counter32
			MAX-ACCESS read-only
			STATUS current
			DESCRIPTION
				"Counts instances of partner-initiated reset (SABME PDU received in a
				connected state) for all connection components since the SAP was initialized"
			::= { saLlcConnAggResetEntry 1 }

		
--  1.3.6.1.4.1.1429.9.1.3.2.7.3.1.2
		-- 1.3.6.1.4.1.1429.9.1.3.2.7.3.1.2
		saLlcConnAggResetLocalReset OBJECT-TYPE
			SYNTAX Counter32
			MAX-ACCESS read-only
			STATUS current
			DESCRIPTION
				"Counts instances of user request for reset while in a connected state
				for all connection components since the SAP was initialized."
			::= { saLlcConnAggResetEntry 2 }

		
--  1.3.6.1.4.1.1429.9.1.3.2.7.3.1.3
		-- 1.3.6.1.4.1.1429.9.1.3.2.7.3.1.3
		saLlcConnAggResetProviderReset OBJECT-TYPE
			SYNTAX Counter32
			MAX-ACCESS read-only
			STATUS current
			DESCRIPTION
				"Counts instances of provider-initiated reset due to FRMR PDU sent, FRMR
				received, or retry exhaustion for all connection components since the SAP was initialized."
			::= { saLlcConnAggResetEntry 3 }

		
--  1.3.6.1.4.1.1429.9.1.3.2.7.4
		-- 1.3.6.1.4.1.1429.9.1.3.2.7.4
		saLlcType2AggDiscTable OBJECT-TYPE
			SYNTAX SEQUENCE OF SaLlcType2AggDiscEntry
			MAX-ACCESS not-accessible
			STATUS current
			DESCRIPTION
				"Specifies a count of DISC PDUs either delivered or received from the MAC
				for all connection components since the SAP was initialized."
			::= { saLlcConnAggregate 4 }

		
--  1.3.6.1.4.1.1429.9.1.3.2.7.4.1
		-- 1.3.6.1.4.1.1429.9.1.3.2.7.4.1
		saLlcType2AggDiscEntry OBJECT-TYPE
			SYNTAX SaLlcType2AggDiscEntry
			MAX-ACCESS not-accessible
			STATUS current
			DESCRIPTION
				"An entry in the table."
			AUGMENTS { saLlcSapEntry }
			::= { saLlcType2AggDiscTable 1 }

		
		SaLlcType2AggDiscEntry ::=
			SEQUENCE { 
				saLlcType2AggDiscReceivedDisc
					Counter32,
				saLlcType2AggDiscSentDisc
					Counter32
			 }

--  1.3.6.1.4.1.1429.9.1.3.2.7.4.1.1
		-- 1.3.6.1.4.1.1429.9.1.3.2.7.4.1.1
		saLlcType2AggDiscReceivedDisc OBJECT-TYPE
			SYNTAX Counter32
			MAX-ACCESS read-only
			STATUS current
			DESCRIPTION
				"Specifies a count of DISC PDUs received from the MAC and not
				discarded for all connection components since the SAP was initialized."
			::= { saLlcType2AggDiscEntry 1 }

		
--  1.3.6.1.4.1.1429.9.1.3.2.7.4.1.2
		-- 1.3.6.1.4.1.1429.9.1.3.2.7.4.1.2
		saLlcType2AggDiscSentDisc OBJECT-TYPE
			SYNTAX Counter32
			MAX-ACCESS read-only
			STATUS current
			DESCRIPTION
				"Specifies a count of DISC PDUs delivered to the MAC
				for all connection components since the SAP was initialized."
			::= { saLlcType2AggDiscEntry 2 }

		
--  1.3.6.1.4.1.1429.9.1.3.2.7.5
		-- 1.3.6.1.4.1.1429.9.1.3.2.7.5
		saLlcType2AggDmTable OBJECT-TYPE
			SYNTAX SEQUENCE OF SaLlcType2AggDmEntry
			MAX-ACCESS not-accessible
			STATUS current
			DESCRIPTION
				"Specifies a count of DM PDUs either delivered or received from
				the MAC for all connection components since the SAP was initialized."
			::= { saLlcConnAggregate 5 }

		
--  1.3.6.1.4.1.1429.9.1.3.2.7.5.1
		-- 1.3.6.1.4.1.1429.9.1.3.2.7.5.1
		saLlcType2AggDmEntry OBJECT-TYPE
			SYNTAX SaLlcType2AggDmEntry
			MAX-ACCESS not-accessible
			STATUS current
			DESCRIPTION
				"An entry in the table."
			AUGMENTS { saLlcSapEntry }
			::= { saLlcType2AggDmTable 1 }

		
		SaLlcType2AggDmEntry ::=
			SEQUENCE { 
				saLlcType2AggDmReceivedDm
					Counter32,
				saLlcType2AggDmSentDm
					Counter32
			 }

--  1.3.6.1.4.1.1429.9.1.3.2.7.5.1.1
		-- 1.3.6.1.4.1.1429.9.1.3.2.7.5.1.1
		saLlcType2AggDmReceivedDm OBJECT-TYPE
			SYNTAX Counter32
			MAX-ACCESS read-only
			STATUS current
			DESCRIPTION
				"Specifies a count of DM PDUs received from the MAC and not
				discarded for all connection components since the SAP was initialized."
			::= { saLlcType2AggDmEntry 1 }

		
--  1.3.6.1.4.1.1429.9.1.3.2.7.5.1.2
		-- 1.3.6.1.4.1.1429.9.1.3.2.7.5.1.2
		saLlcType2AggDmSentDm OBJECT-TYPE
			SYNTAX Counter32
			MAX-ACCESS read-only
			STATUS current
			DESCRIPTION
				"Specifies a count of DM PDUs delivered to the MAC
				for all connection components since the SAP was initialized."
			::= { saLlcType2AggDmEntry 2 }

		
--  1.3.6.1.4.1.1429.9.1.3.2.7.6
		-- 1.3.6.1.4.1.1429.9.1.3.2.7.6
		saLlcType2AggFrmrTable OBJECT-TYPE
			SYNTAX SEQUENCE OF SaLlcType2AggFrmrEntry
			MAX-ACCESS not-accessible
			STATUS current
			DESCRIPTION
				"Specifies a count of FRMR PDUs delivered to the MAC and a
				count of FRMR PDUs received from the MAC and not discarded
				for all connection components since the SAP was initialized."
			::= { saLlcConnAggregate 6 }

		
--  1.3.6.1.4.1.1429.9.1.3.2.7.6.1
		-- 1.3.6.1.4.1.1429.9.1.3.2.7.6.1
		saLlcType2AggFrmrEntry OBJECT-TYPE
			SYNTAX SaLlcType2AggFrmrEntry
			MAX-ACCESS not-accessible
			STATUS current
			DESCRIPTION
				"An entry in the table."
			AUGMENTS { saLlcSapEntry }
			::= { saLlcType2AggFrmrTable 1 }

		
		SaLlcType2AggFrmrEntry ::=
			SEQUENCE { 
				saLlcType2AggFrmrReceivedFrmr
					Counter32,
				saLlcType2AggFrmrSentFrmr
					Counter32
			 }

--  1.3.6.1.4.1.1429.9.1.3.2.7.6.1.1
		-- 1.3.6.1.4.1.1429.9.1.3.2.7.6.1.1
		saLlcType2AggFrmrReceivedFrmr OBJECT-TYPE
			SYNTAX Counter32
			MAX-ACCESS read-only
			STATUS current
			DESCRIPTION
				"Specifies a count of FRMR PDUs received from the MAC and not
				discarded for all connection components since the SAP was initialized."
			::= { saLlcType2AggFrmrEntry 1 }

		
--  1.3.6.1.4.1.1429.9.1.3.2.7.6.1.2
		-- 1.3.6.1.4.1.1429.9.1.3.2.7.6.1.2
		saLlcType2AggFrmrSentFrmr OBJECT-TYPE
			SYNTAX Counter32
			MAX-ACCESS read-only
			STATUS current
			DESCRIPTION
				"Specifies a count of FRMR PDUs delivered to the MAC
				for all connection components since the SAP was initialized."
			::= { saLlcType2AggFrmrEntry 2 }

		
--  1.3.6.1.4.1.1429.9.1.3.2.7.7
		-- 1.3.6.1.4.1.1429.9.1.3.2.7.7
		saLlcType2AggITable OBJECT-TYPE
			SYNTAX SEQUENCE OF SaLlcType2AggIEntry
			MAX-ACCESS not-accessible
			STATUS current
			DESCRIPTION
				"Counts the number of I PDUs received
				and sent for all connection components since the SAP was initialized"
			::= { saLlcConnAggregate 7 }

		
--  1.3.6.1.4.1.1429.9.1.3.2.7.7.1
		-- 1.3.6.1.4.1.1429.9.1.3.2.7.7.1
		saLlcType2AggIEntry OBJECT-TYPE
			SYNTAX SaLlcType2AggIEntry
			MAX-ACCESS not-accessible
			STATUS current
			DESCRIPTION
				"An entry in the table."
			AUGMENTS { saLlcSapEntry }
			::= { saLlcType2AggITable 1 }

		
		SaLlcType2AggIEntry ::=
			SEQUENCE { 
				saLlcType2AggIReceivedI
					Counter32,
				saLlcType2AggISentI
					Counter32
			 }

--  1.3.6.1.4.1.1429.9.1.3.2.7.7.1.1
		-- 1.3.6.1.4.1.1429.9.1.3.2.7.7.1.1
		saLlcType2AggIReceivedI OBJECT-TYPE
			SYNTAX Counter32
			MAX-ACCESS read-only
			STATUS current
			DESCRIPTION
				"Specifies a count of I PDUs received from the MAC and passed to the LLC
				user for all connection components since the SAP was initialized."
			::= { saLlcType2AggIEntry 1 }

		
--  1.3.6.1.4.1.1429.9.1.3.2.7.7.1.2
		-- 1.3.6.1.4.1.1429.9.1.3.2.7.7.1.2
		saLlcType2AggISentI OBJECT-TYPE
			SYNTAX Counter32
			MAX-ACCESS read-only
			STATUS current
			DESCRIPTION
				"Specifies a count of I PDUs delivered to the MAC
				for all connection components since the SAP was initialized."
			::= { saLlcType2AggIEntry 2 }

		
--  1.3.6.1.4.1.1429.9.1.3.2.7.8
		-- 1.3.6.1.4.1.1429.9.1.3.2.7.8
		saLlcType2AggPdusTable OBJECT-TYPE
			SYNTAX SEQUENCE OF SaLlcType2AggPdusEntry
			MAX-ACCESS not-accessible
			STATUS current
			DESCRIPTION
				"Contains attributes that count a number of different
				types of discarded PDUs for all connection components since the SAP was initialized."
			::= { saLlcConnAggregate 8 }

		
--  1.3.6.1.4.1.1429.9.1.3.2.7.8.1
		-- 1.3.6.1.4.1.1429.9.1.3.2.7.8.1
		saLlcType2AggPdusEntry OBJECT-TYPE
			SYNTAX SaLlcType2AggPdusEntry
			MAX-ACCESS not-accessible
			STATUS current
			DESCRIPTION
				"An entry in the table."
			AUGMENTS { saLlcSapEntry }
			::= { saLlcType2AggPdusTable 1 }

		
		SaLlcType2AggPdusEntry ::=
			SEQUENCE { 
				saLlcType2AggPdusDiscarded1
					Counter32,
				saLlcType2AggPdusDiscarded2
					Counter32,
				saLlcType2AggPdusRetransmissions
					Counter32
			 }

--  1.3.6.1.4.1.1429.9.1.3.2.7.8.1.1
		-- 1.3.6.1.4.1.1429.9.1.3.2.7.8.1.1
		saLlcType2AggPdusDiscarded1 OBJECT-TYPE
			SYNTAX Counter32
			MAX-ACCESS read-only
			STATUS current
			DESCRIPTION
				"Specifies a count of PDUs discarded due to insufficient resources for
				a connection for all connection components since the SAP was initialized."
			::= { saLlcType2AggPdusEntry 1 }

		
--  1.3.6.1.4.1.1429.9.1.3.2.7.8.1.2
		-- 1.3.6.1.4.1.1429.9.1.3.2.7.8.1.2
		saLlcType2AggPdusDiscarded2 OBJECT-TYPE
			SYNTAX Counter32
			MAX-ACCESS read-only
			STATUS current
			DESCRIPTION
				"Specifies a count of I PDUs discarded due to unexpected or invalid sequence
				number for a connection for all connection components since the SAP was initialized."
			::= { saLlcType2AggPdusEntry 2 }

		
--  1.3.6.1.4.1.1429.9.1.3.2.7.8.1.3
		-- 1.3.6.1.4.1.1429.9.1.3.2.7.8.1.3
		saLlcType2AggPdusRetransmissions OBJECT-TYPE
			SYNTAX Counter32
			MAX-ACCESS read-only
			STATUS current
			DESCRIPTION
				"Specifies a count of the number of times the Type 2 LLC service
				retransmitted PDUs for a connection for all connection components 
				since the SAP was initialized."
			::= { saLlcType2AggPdusEntry 3 }

		
--  1.3.6.1.4.1.1429.9.1.3.2.7.9
		-- 1.3.6.1.4.1.1429.9.1.3.2.7.9
		saLlcType2AggRejTable OBJECT-TYPE
			SYNTAX SEQUENCE OF SaLlcType2AggRejEntry
			MAX-ACCESS not-accessible
			STATUS current
			DESCRIPTION
				"Contains two attributes to count sent and received REJ PDUs
				for all connection components since the SAP was initialized."
			REFERENCE
				"see 7.5.9"
			::= { saLlcConnAggregate 9 }

		
--  1.3.6.1.4.1.1429.9.1.3.2.7.9.1
		-- 1.3.6.1.4.1.1429.9.1.3.2.7.9.1
		saLlcType2AggRejEntry OBJECT-TYPE
			SYNTAX SaLlcType2AggRejEntry
			MAX-ACCESS not-accessible
			STATUS current
			DESCRIPTION
				"An entry in the table."
			AUGMENTS { saLlcSapEntry }
			::= { saLlcType2AggRejTable 1 }

		
		SaLlcType2AggRejEntry ::=
			SEQUENCE { 
				saLlcType2AggRejReceivedRej
					Counter32,
				saLlcType2AggRejSentRej
					Counter32
			 }

--  1.3.6.1.4.1.1429.9.1.3.2.7.9.1.1
		-- 1.3.6.1.4.1.1429.9.1.3.2.7.9.1.1
		saLlcType2AggRejReceivedRej OBJECT-TYPE
			SYNTAX Counter32
			MAX-ACCESS read-only
			STATUS current
			DESCRIPTION
				"Specifies a count of REJ PDUs received from the MAC and not discarded
				for all connection components since the SAP was initialized."
			::= { saLlcType2AggRejEntry 1 }

		
--  1.3.6.1.4.1.1429.9.1.3.2.7.9.1.2
		-- 1.3.6.1.4.1.1429.9.1.3.2.7.9.1.2
		saLlcType2AggRejSentRej OBJECT-TYPE
			SYNTAX Counter32
			MAX-ACCESS read-only
			STATUS current
			DESCRIPTION
				"Specifies a count of REJ PDUs delivered to the MAC
				for all connection components since the SAP was initialized."
			::= { saLlcType2AggRejEntry 2 }

		
--  1.3.6.1.4.1.1429.9.1.3.2.7.10
		-- 1.3.6.1.4.1.1429.9.1.3.2.7.10
		saLlcType2AggRnrTable OBJECT-TYPE
			SYNTAX SEQUENCE OF SaLlcType2AggRnrEntry
			MAX-ACCESS not-accessible
			STATUS current
			DESCRIPTION
				"Contains attributes that specify the count of RNR
				PDUs either delivered or received from the MAC
				for all connection components since the SAP was initialized."
			::= { saLlcConnAggregate 10 }

		
--  1.3.6.1.4.1.1429.9.1.3.2.7.10.1
		-- 1.3.6.1.4.1.1429.9.1.3.2.7.10.1
		saLlcType2AggRnrEntry OBJECT-TYPE
			SYNTAX SaLlcType2AggRnrEntry
			MAX-ACCESS not-accessible
			STATUS current
			DESCRIPTION
				"An entry in the table."
			AUGMENTS { saLlcSapEntry }
			::= { saLlcType2AggRnrTable 1 }

		
		SaLlcType2AggRnrEntry ::=
			SEQUENCE { 
				saLlcType2AggRnrReceivedRnr
					Counter32,
				saLlcType2AggRnrSentRnr
					Counter32
			 }

--  1.3.6.1.4.1.1429.9.1.3.2.7.10.1.1
		-- 1.3.6.1.4.1.1429.9.1.3.2.7.10.1.1
		saLlcType2AggRnrReceivedRnr OBJECT-TYPE
			SYNTAX Counter32
			MAX-ACCESS read-only
			STATUS current
			DESCRIPTION
				"Specifies a count of RNR PDUs received from the MAC and not discarded
				for all connection components since the SAP was initialized."
			::= { saLlcType2AggRnrEntry 1 }

		
--  1.3.6.1.4.1.1429.9.1.3.2.7.10.1.2
		-- 1.3.6.1.4.1.1429.9.1.3.2.7.10.1.2
		saLlcType2AggRnrSentRnr OBJECT-TYPE
			SYNTAX Counter32
			MAX-ACCESS read-only
			STATUS current
			DESCRIPTION
				"Specifies a count of RNR PDUs delivered to the MAC
				for all connection components since the SAP was initialized."
			::= { saLlcType2AggRnrEntry 2 }

		
--  1.3.6.1.4.1.1429.9.1.3.2.7.11
		-- 1.3.6.1.4.1.1429.9.1.3.2.7.11
		saLlcType2AggRrTable OBJECT-TYPE
			SYNTAX SEQUENCE OF SaLlcType2AggRrEntry
			MAX-ACCESS not-accessible
			STATUS current
			DESCRIPTION
				"Contains attributes that specify the count of RR
				PDUs either delivered or received from the MAC
				for all connection components since the SAP was initialized."
			::= { saLlcConnAggregate 11 }

		
--  1.3.6.1.4.1.1429.9.1.3.2.7.11.1
		-- 1.3.6.1.4.1.1429.9.1.3.2.7.11.1
		saLlcType2AggRrEntry OBJECT-TYPE
			SYNTAX SaLlcType2AggRrEntry
			MAX-ACCESS not-accessible
			STATUS current
			DESCRIPTION
				"An entry in the table."
			AUGMENTS { saLlcSapEntry }
			::= { saLlcType2AggRrTable 1 }

		
		SaLlcType2AggRrEntry ::=
			SEQUENCE { 
				saLlcType2AggRrReceivedRr
					Counter32,
				saLlcType2AggRrSentRr
					Counter32
			 }

--  1.3.6.1.4.1.1429.9.1.3.2.7.11.1.1
		-- 1.3.6.1.4.1.1429.9.1.3.2.7.11.1.1
		saLlcType2AggRrReceivedRr OBJECT-TYPE
			SYNTAX Counter32
			MAX-ACCESS read-only
			STATUS current
			DESCRIPTION
				"Specifies a count of RR PDUs received from the MAC and not discarded
				for all connection components since the SAP was initialized."
			::= { saLlcType2AggRrEntry 1 }

		
--  1.3.6.1.4.1.1429.9.1.3.2.7.11.1.2
		-- 1.3.6.1.4.1.1429.9.1.3.2.7.11.1.2
		saLlcType2AggRrSentRr OBJECT-TYPE
			SYNTAX Counter32
			MAX-ACCESS read-only
			STATUS current
			DESCRIPTION
				"Specifies a count of RR PDUs delivered to the MAC
				for all connection components since the SAP was initialized."
			::= { saLlcType2AggRrEntry 2 }

		
--  1.3.6.1.4.1.1429.9.1.3.2.7.12
		-- 1.3.6.1.4.1.1429.9.1.3.2.7.12
		saLlcType2AggSabmeTable OBJECT-TYPE
			SYNTAX SEQUENCE OF SaLlcType2AggSabmeEntry
			MAX-ACCESS not-accessible
			STATUS current
			DESCRIPTION
				"Contains attributes that specify the count of SABME
				PDUs either delivered or received from the MAC
				for all connection components since the SAP was initialized."
			::= { saLlcConnAggregate 12 }

		
--  1.3.6.1.4.1.1429.9.1.3.2.7.12.1
		-- 1.3.6.1.4.1.1429.9.1.3.2.7.12.1
		saLlcType2AggSabmeEntry OBJECT-TYPE
			SYNTAX SaLlcType2AggSabmeEntry
			MAX-ACCESS not-accessible
			STATUS current
			DESCRIPTION
				"An entry in the table."
			AUGMENTS { saLlcSapEntry }
			::= { saLlcType2AggSabmeTable 1 }

		
		SaLlcType2AggSabmeEntry ::=
			SEQUENCE { 
				saLlcType2AggSabmeReceivedSabme
					Counter32,
				saLlcType2AggSabmeSentSabme
					Counter32
			 }

--  1.3.6.1.4.1.1429.9.1.3.2.7.12.1.1
		-- 1.3.6.1.4.1.1429.9.1.3.2.7.12.1.1
		saLlcType2AggSabmeReceivedSabme OBJECT-TYPE
			SYNTAX Counter32
			MAX-ACCESS read-only
			STATUS current
			DESCRIPTION
				"Specifies a count of SABME PDUs received from the MAC and not discarded
				for all connection components since the SAP was initialized."
			::= { saLlcType2AggSabmeEntry 1 }

		
--  1.3.6.1.4.1.1429.9.1.3.2.7.12.1.2
		-- 1.3.6.1.4.1.1429.9.1.3.2.7.12.1.2
		saLlcType2AggSabmeSentSabme OBJECT-TYPE
			SYNTAX Counter32
			MAX-ACCESS read-only
			STATUS current
			DESCRIPTION
				"Specifies a count of SABME PDUs delivered to the MAC
				for all connection components since the SAP was initialized."
			::= { saLlcType2AggSabmeEntry 2 }

		
--  1.3.6.1.4.1.1429.9.1.3.2.7.13
		-- 1.3.6.1.4.1.1429.9.1.3.2.7.13
		saLlcType2AggUaTable OBJECT-TYPE
			SYNTAX SEQUENCE OF SaLlcType2AggUaEntry
			MAX-ACCESS not-accessible
			STATUS current
			DESCRIPTION
				"Contains attributes that specify the count of UA
				PDUs either delivered or received from the MAC
				for all connection components since the SAP was initialized."
			::= { saLlcConnAggregate 13 }

		
--  1.3.6.1.4.1.1429.9.1.3.2.7.13.1
		-- 1.3.6.1.4.1.1429.9.1.3.2.7.13.1
		saLlcType2AggUaEntry OBJECT-TYPE
			SYNTAX SaLlcType2AggUaEntry
			MAX-ACCESS not-accessible
			STATUS current
			DESCRIPTION
				"An entry in the table."
			AUGMENTS { saLlcSapEntry }
			::= { saLlcType2AggUaTable 1 }

		
		SaLlcType2AggUaEntry ::=
			SEQUENCE { 
				saLlcType2AggUaReceivedUa
					Counter32,
				saLlcType2AggUaSentUa
					Counter32
			 }

--  1.3.6.1.4.1.1429.9.1.3.2.7.13.1.1
		-- 1.3.6.1.4.1.1429.9.1.3.2.7.13.1.1
		saLlcType2AggUaReceivedUa OBJECT-TYPE
			SYNTAX Counter32
			MAX-ACCESS read-only
			STATUS current
			DESCRIPTION
				"Specifies a count of UA PDUs received from the MAC and not discarded
				for all connection components since the SAP was initialized."
			::= { saLlcType2AggUaEntry 1 }

		
--  1.3.6.1.4.1.1429.9.1.3.2.7.13.1.2
		-- 1.3.6.1.4.1.1429.9.1.3.2.7.13.1.2
		saLlcType2AggUaSentUa OBJECT-TYPE
			SYNTAX Counter32
			MAX-ACCESS read-only
			STATUS current
			DESCRIPTION
				"Specifies a count of UA PDUs delivered to the MAC
				for all connection components since the SAP was initialized."
			::= { saLlcType2AggUaEntry 2 }

		
--  1.3.6.1.4.1.1429.9.1.3.2.7.14
		-- 1.3.6.1.4.1.1429.9.1.3.2.7.14
		saLlcType2AggViolationTable OBJECT-TYPE
			SYNTAX SEQUENCE OF SaLlcType2AggViolationEntry
			MAX-ACCESS not-accessible
			STATUS current
			DESCRIPTION
				"Contains an attribute to count type 2 violations
				for all connection components since the SAP was initialized."
			::= { saLlcConnAggregate 14 }

		
--  1.3.6.1.4.1.1429.9.1.3.2.7.14.1
		-- 1.3.6.1.4.1.1429.9.1.3.2.7.14.1
		saLlcType2AggViolationEntry OBJECT-TYPE
			SYNTAX SaLlcType2AggViolationEntry
			MAX-ACCESS not-accessible
			STATUS current
			DESCRIPTION
				"An entry in the table."
			AUGMENTS { saLlcSapEntry }
			::= { saLlcType2AggViolationTable 1 }

		
		SaLlcType2AggViolationEntry ::=
			SEQUENCE { 
				saLlcType2AggViolation
					Counter32
			 }

--  1.3.6.1.4.1.1429.9.1.3.2.7.14.1.1
		-- 1.3.6.1.4.1.1429.9.1.3.2.7.14.1.1
		saLlcType2AggViolation OBJECT-TYPE
			SYNTAX Counter32
			MAX-ACCESS read-only
			STATUS current
			DESCRIPTION
				"Provides a count of the number of protocol violations detected by a
				connection for all connection components since the SAP was initialized. 
				Protocol violations include the following:
				1) those that result in the LLC entity sending an FRMR frame
				2) those that result in a data link resetting action to be initiated by
				the receiving LLC entity itself."
			::= { saLlcType2AggViolationEntry 1 }

		
--  1.3.6.1.4.1.1429.9.1.3.3
		-- 1.3.6.1.4.1.1429.9.1.3.3
		saLlcEvents OBJECT-IDENTITY
			STATUS current
			DESCRIPTION 
				"Events associated with the SA-LLC-MIB module"
			::= { saLlcMib 3 }

		
--  1.3.6.1.4.1.1429.9.1.3.3.1
		-- 1.3.6.1.4.1.1429.9.1.3.3.1
		saLlcEventsV2 OBJECT-IDENTITY
			STATUS current
			DESCRIPTION 
				"Dummy node needed for V1 compatability."
			::= { saLlcEvents 1 }

		
	
	END

--
-- SA-LLC-MIB.my
--
