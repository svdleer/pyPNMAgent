--****************************************************************************
--    Description:
--
--		private MIB for runtime (not factory) eMTA management
--
--****************************************************************************
--    Revision History:
--
--**************************************************************************

UBEE-CM-EMTA-MGMT-MIB DEFINITIONS ::= BEGIN

IMPORTS
    MODULE-IDENTITY,
    OBJECT-TYPE,
    NOTIFICATION-TYPE,
    Unsigned32
        FROM SNMPv2-SMI
    TruthValue
        FROM SNMPv2-TC
    OBJECT-GROUP,
    MODULE-COMPLIANCE,
    NOTIFICATION-GROUP
        FROM SNMPv2-CONF
    cmEmbeddedDevices
        FROM UBEE-CM-MGMT-MIB;

cmEmtaMgmt MODULE-IDENTITY
    LAST-UPDATED "200902240000Z"
    ORGANIZATION "Ubee Interactive Corporation"
    CONTACT-INFO
        "	Ubee Interactive Global Headquarters

        Postal: 6F-9, No.38, Taiyuan St.
        		Jhubei City Hsinchu County 302
        		Taiwan, R.O.C.

           Tel: +886-3-560-0010

        E-mail: asupport@ubeeinteractive.com"
    DESCRIPTION
        "Ubee MIB for runtime management of CM features which are only
         applicable on a device which contains an embedded PacketCable MTA."
::= { cmEmbeddedDevices 1 }

--
-- Placeholder for any future textual conventions 
--

--
-- Placeholder for any future notifications (traps)
-- 
cmEmtaNotification     OBJECT IDENTIFIER ::= { cmEmtaMgmt 0 }

--
-- Management objects
--
cmEmtaMIBObjects       OBJECT IDENTIFIER ::= { cmEmtaMgmt 1 }

--
-- cmEmtaBase - objects for general-purpose CM - eMTA control
--

cmEmtaBase       OBJECT IDENTIFIER ::= { cmEmtaMIBObjects 1 }

cmEmtaBasicFlowDhcpAccept OBJECT-TYPE
    SYNTAX      TruthValue
    MAX-ACCESS  read-write
    STATUS      current
    DESCRIPTION
        "This object may be used to expedite the acceptance of the EMTA DHCP
         offer when option 122.6 of the offer indicates basic or hybrid
         provisioning flow.
         
         If set to true(1), DHCP offer rule (b) from MTA initialization flow
         MTA2 will not be enforced.  This means that the EMTA will not retry 
         the DHCP discover process in search of an offer which specifies the 
         secure flow, thus resulting in the EMTA becoming operational more
         quickly.
         
         It is important to note that in this configuration the CM is in 
         violation of the PacketCable provisioning specification."
    REFERENCE
        "PacketCable 1.5 Specification MTA Device Provisioning
         PKT-SP-PROV1.5-I03-070412, section 7.2.1, initialization flow MTA2"
    DEFVAL { false }
    ::= { cmEmtaBase 1 }
    
cmEmtaNonSecureFlowDefaultReadCommunity OBJECT-TYPE
    SYNTAX       OCTET STRING
    MAX-ACCESS   read-write
    STATUS       current
    DESCRIPTION
        "The default community string which will be used for read-only access 
         in the EMTA non-secure provisioning flow.  When read, this object will 
         always return an empty string."
    DEFVAL { "private" }
    ::= { cmEmtaBase 2 }

cmEmtaNonSecureFlowDefaultWriteCommunity OBJECT-TYPE
    SYNTAX       OCTET STRING
    MAX-ACCESS   read-write
    STATUS       current
    DESCRIPTION
        "The default community string which will be used for read-write access 
         in the EMTA non-secure provisioning flow.  When read, this object will
         always return an empty string."
    DEFVAL { "private" }
    ::= { cmEmtaBase 3 }

cmEmtaRegistrationState OBJECT-TYPE
    SYNTAX      INTEGER {
                cmScanning(1),
                cmRanging(2),
                cmDhcp(3),
                cmTftp(4),
                cmRegistered(5),
                mtaDhcp(6),
                mtaTftp(7),
                mtaProvisioned(8),
                mtaRsip(9),
                mtaOperational(10),
                mtaRejected(11)
    }
    MAX-ACCESS   read-only
    STATUS       current
    DESCRIPTION
        "Indicates the current state of the CM and EMTA provisioning and 
         registration process."
    ::= { cmEmtaBase 4 }
    
cmEmtaSafeReset OBJECT-TYPE
    SYNTAX      TruthValue
    MAX-ACCESS  read-write
    STATUS      current
    DESCRIPTION
        "Setting this object to true(1) will cause the device to reset only 
         when all telephony lines are on-hook.  If one or more lines are 
         off-hook when the reset is invoked then the reset will be queued and 
         will occur once all lines are on-hook.  Reading this object returns 
         false(2) unless a reset is pending, in which case it returns true(1).  
         A pending reset may be cancelled by setting this object to false(2).
         
         Note that the behavior of this object is also affected by the values of
         objects emtaPostCallCompletionResetDelay and emtaMaxResetDelay as 
         described in the the BRCM-EMTA-MGMT-MIB."
    ::= { cmEmtaBase 5 }
    
cmEmtaPingTestInterval OBJECT-TYPE
    SYNTAX      Unsigned32
    UNITS       "minutes"
    MAX-ACCESS  read-write
    STATUS      current
    DESCRIPTION
        "This object identifies the time interval, in minutes, that the eMTA should
         perform a ping test from the eMTA stack to the default gateway.  If set to
         0, this feature will be disabled."
    DEFVAL {0}
    ::= { cmEmtaBase 6 }

cmEmtaPingTestFailEMTAThreshold OBJECT-TYPE
    SYNTAX      Unsigned32 
    MAX-ACCESS  read-write
    STATUS      current
    DESCRIPTION
        "This object identifies the number of consecutive failed ping tests to 
        trigger an eMTA reset.  If set to 0, this feature will be disabled."
    DEFVAL {0}
    ::= { cmEmtaBase 7 }

cmEmtaPingTestFailCMThreshold OBJECT-TYPE
    SYNTAX      Unsigned32 
    MAX-ACCESS  read-write
    STATUS      current
    DESCRIPTION
        "This object identifies the number of consecutive failed ping tests to 
        trigger a CM reset and eMTA reset.  
        If set to 0, this feature will be disabled."
    DEFVAL {0}
    ::= { cmEmtaBase 8 }
    
cmEmtaCmSnmpAuthFallbackEnable OBJECT-TYPE
    SYNTAX      TruthValue
    MAX-ACCESS  read-write
    STATUS      current
    DESCRIPTION
        "Setting this object to true(1) will cause SNMP transactions with the
         EMTA to be authenticated by the CM's authentication settings if 
         authentication by EMTA settings fails.  This allows use of the CM's
         docsDevNmAccessTable, snmpCommunityTable, or SNMPv3 settings to be
         applied for EMTA SNMP authentication if desired."
    DEFVAL { false }
    ::= { cmEmtaBase 9 }

--
-- cmEmtaBfcEvents provides a node under which EMTA-specific event
-- OIDs may be defined for use in the bfcEventLogTable.
--

cmEmtaBfcEvents OBJECT IDENTIFIER ::= { cmEmtaMIBObjects 2 }

-- This event satisfies Comcast requirement [REQ_E-UE-LOG-150]:
-- "The UE MUST log the name of the CM and MTA configuration file applied to 
-- the device, and the timestamp of when the configuration file was applied. 
-- This log MUST support up to 10 entries and be written to persistent memory."
cmEmtaConfigFileEvent OBJECT-IDENTITY
    STATUS     current
    DESCRIPTION
        "An event giving details regarding the EMTA config file.  At a minimum,
         this event will contain the IP address and path from which the config
         file was downloaded."
    ::= { cmEmtaBfcEvents 1 }
    
-- This event satisfies Comcast requirement [REQ_E-UE-LOG-160]:
-- "The UE MUST log the trigger for bringing a line Out of Service (OOS), 
-- regardless if the OOS condition was trigger from an external event (403 SIP 
-- message) or internal event (SW error). This log MUST support up to 5 entries 
-- per port of the device and be written to persistent memory."
cmEmtaLineOutOfServiceEvent OBJECT-IDENTITY
    STATUS     current
    DESCRIPTION
        "An event giving details regarding the EMTA config file.  At a minimum,
         this event will contain the IP address and path from which the config
         file was downloaded."
    ::= { cmEmtaBfcEvents 2 }

-- This event satisfies Comcast requirement [REQ_E-UE-LOG-170]:
-- "The UE MUST log the timestamp of when loop diagnostics are initiated, and 
-- the timestamp of when they complete. This log MUST support up to 10 entries 
-- and be written to persistent memory."
cmEmtaLoopDiagnosticsEvent OBJECT-IDENTITY
    STATUS     current
    DESCRIPTION
        "An event indicating the beginning or end of a loop diagnostics 
         session."
    ::= { cmEmtaBfcEvents 3 }


--
-- Conformance definitions
--
cmEmtaConformance      OBJECT IDENTIFIER ::= { cmEmtaMgmt 2 }

--
-- Compliance Statements
--
cmEmtaCompliances  OBJECT IDENTIFIER ::= { cmEmtaConformance 1 }
cmEmtaGroups       OBJECT IDENTIFIER ::= { cmEmtaConformance 2 }

cmEmtaCompliance  MODULE-COMPLIANCE
    STATUS      current
    DESCRIPTION
        "The compliance statement for cablemodem devices which include an
         embedded PacketCable MTA."
    MODULE
    MANDATORY-GROUPS {
               cmEmtaBaseGroup
    }
    ::= { cmEmtaCompliances 1 }


cmEmtaBaseGroup OBJECT-GROUP
    OBJECTS {
        cmEmtaBasicFlowDhcpAccept,
        cmEmtaNonSecureFlowDefaultReadCommunity,
        cmEmtaNonSecureFlowDefaultWriteCommunity,
        cmEmtaRegistrationState,
        cmEmtaSafeReset
    }
    STATUS      current
    DESCRIPTION
        "A set of objects supported by all agents which implement this MIB."
    ::= { cmEmtaGroups 1 }

END
