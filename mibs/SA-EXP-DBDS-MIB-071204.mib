--
-- SA-EXP-DBDS-MIB.my
-- MIB generated by MG-SOFT Visual MIB Builder Version 4.0 Build 349
-- Monday, July 12, 2004 at 12:23:27
--

--  SA-EXP-DBDS-MIB.my
-- MIB generated by MG-SOFT Visual MIB Builder Version 4.0 Build 349
-- Monday, July 12, 2004 at 12:20:32
-- 
-- -  SA-EXP-DBDS-MIB.my
-- MIB generated by MG-SOFT Visual MIB Builder Version 4.0 Build 349
-- Thursday, April 24, 2003 at 16:35:49
-- 
-- Revision 1 : R. Killick
-- Date: Thursday, April 24, 2003 at 16:35:49
-- Comment:
-- 
-- Revision 2 : Obsoleted 'drivers' node
-- Date: Wednesday, May 07, 2003 at 15:59:12
-- Comment:
-- New 'dhctDrivers' node replaces
-- 'drivers' node under saOrgs.
-- 
-- Revision 3 : International
-- Date: Wednesday, February 25, 2004 at 12:38:33
-- Comment:
-- Added a node for the inernational
-- group: expDbdsMibObjs.saOrgs.international.
-- 
-- Revision 4 : PTV Experimental Node
-- Date: Monday, July 12, 2004 at 12:18:31
-- Comment:
-- Added experimental node for PTV.
--  

	SA-EXP-DBDS-MIB DEFINITIONS ::= BEGIN
 
		IMPORTS
			saExpDbds			
				FROM SCIATL-COMMON-MIB			
			MODULE-IDENTITY, OBJECT-IDENTITY			
				FROM SNMPv2-SMI;
	
	
--    1.3.6.1.4.1.1429.6.1.1
-- February 25, 2004 at 12:38 GMT
-- May 07, 2003 at 15:57 GMT
-- February 18, 2003 at 10:39 GMT
-- 1.3.6.1.4.1.1429.6.1.1
-- July 12, 2004 at 11:54 GMT
-- February 18, 2003 at 10:39 GMT
-- May 07, 2003 at 15:57 GMT
-- February 25, 2004 at 12:38 GMT
-- 1.3.6.1.4.1.1429.6.1.1
-- July 12, 2004 at 12:18 GMT
-- July 12, 2004 at 12:18 GMT
-- February 25, 2004 at 12:38 GMT
-- May 07, 2003 at 15:57 GMT
-- February 18, 2003 at 10:39 GMT
		-- 1.3.6.1.4.1.1429.6.1.1
		expDbdsMibObjs MODULE-IDENTITY 
			LAST-UPDATED "200407121218Z"		-- July 12, 2004 at 12:18 GMT
			ORGANIZATION 
				"Scientific-Atlanta DBDS Systems Engineering and Architecture."
			CONTACT-INFO 
				"Ray Killick."
			DESCRIPTION 
				"This MIB sets the nodes for future 
				experimentation with the different DBDS components."
			REVISION "200302181039Z"		-- February 18, 2003 at 10:39 GMT
			DESCRIPTION 
				"This MIB was part of our first MIB release to CVC."
			REVISION "200305071557Z"		-- May 07, 2003 at 15:57 GMT
			DESCRIPTION 
				"New 'dhctDrivers' node replaces
				'drivers' node under saOrgs."
			REVISION "200402251238Z"		-- February 25, 2004 at 12:38 GMT
			DESCRIPTION 
				"Added a node for the inernational
				group: expDbdsMibObjs.saOrgs.international."
			REVISION "200407121218Z"		-- July 12, 2004 at 12:18 GMT
			DESCRIPTION 
				"Added experimental node for PTV."
			::= { saExpDbds 1 }

		
	
--
-- Node definitions
--
	
--  Node definitions
-- 
-- Node definitions
-- 
-- 1.3.6.1.4.1.1429.6.1.1.1
-- 
-- 1.3.6.1.4.1.1429.6.1.1.1
		-- 1.3.6.1.4.1.1429.6.1.1.1
		expDbdsMibObjsConformance OBJECT-IDENTITY
			STATUS current
			DESCRIPTION 
				"Conformance node."
			::= { expDbdsMibObjs 1 }

		
--  1.3.6.1.4.1.1429.6.1.1.1.2
-- 1.3.6.1.4.1.1429.6.1.1.1.2
		-- 1.3.6.1.4.1.1429.6.1.1.1.2
		expDbdsMibObjsCompliances OBJECT-IDENTITY
			STATUS current
			DESCRIPTION 
				"Compliances node."
			::= { expDbdsMibObjsConformance 2 }

		
--  1.3.6.1.4.1.1429.6.1.1.1.3
-- 1.3.6.1.4.1.1429.6.1.1.1.3
		-- 1.3.6.1.4.1.1429.6.1.1.1.3
		expDbdsMibObjsGroups OBJECT-IDENTITY
			STATUS current
			DESCRIPTION 
				"Object group nodes."
			::= { expDbdsMibObjsConformance 3 }

		
--  1.3.6.1.4.1.1429.6.1.1.2
-- 1.3.6.1.4.1.1429.6.1.1.2
		-- 1.3.6.1.4.1.1429.6.1.1.2
		saDhct OBJECT-IDENTITY
			STATUS current
			DESCRIPTION 
				"DHCT experimental MIBs."
			::= { expDbdsMibObjs 2 }

		
--  1.3.6.1.4.1.1429.6.1.1.3
-- 1.3.6.1.4.1.1429.6.1.1.3
		-- 1.3.6.1.4.1.1429.6.1.1.3
		saQpsk OBJECT-IDENTITY
			STATUS current
			DESCRIPTION 
				"QPSK experimental MIBs."
			::= { expDbdsMibObjs 3 }

		
--  1.3.6.1.4.1.1429.6.1.1.5
-- 1.3.6.1.4.1.1429.6.1.1.5
		-- 1.3.6.1.4.1.1429.6.1.1.5
		saXdc OBJECT-IDENTITY
			STATUS current
			DESCRIPTION 
				"XDC experimental MIBs."
			::= { expDbdsMibObjs 5 }

		
--  1.3.6.1.4.1.1429.6.1.1.6
-- 1.3.6.1.4.1.1429.6.1.1.6
		-- 1.3.6.1.4.1.1429.6.1.1.6
		saQam OBJECT-IDENTITY
			STATUS current
			DESCRIPTION 
				"QAM experimental MIBs."
			::= { expDbdsMibObjs 6 }

		
--  1.3.6.1.4.1.1429.6.1.1.8
-- 1.3.6.1.4.1.1429.6.1.1.8
		-- 1.3.6.1.4.1.1429.6.1.1.8
		saAppServ OBJECT-IDENTITY
			STATUS current
			DESCRIPTION 
				"App Server experimental MIBs."
			::= { expDbdsMibObjs 8 }

		
--  1.3.6.1.4.1.1429.6.1.1.9
-- 1.3.6.1.4.1.1429.6.1.1.9
		-- 1.3.6.1.4.1.1429.6.1.1.9
		saMpeg OBJECT-IDENTITY
			STATUS current
			DESCRIPTION 
				"MPEG experimental MIBs."
			::= { expDbdsMibObjs 9 }

		
--  1.3.6.1.4.1.1429.6.1.1.10
-- 1.3.6.1.4.1.1429.6.1.1.10
		-- 1.3.6.1.4.1.1429.6.1.1.10
		saOrgs OBJECT-IDENTITY
			STATUS current
			DESCRIPTION 
				"OIDs/MIBs under this node are never published
				and are considered experiments that may lead to
				official MIBs."
			::= { expDbdsMibObjs 10 }

		
--  1.3.6.1.4.1.1429.6.1.1.10.1
-- 1.3.6.1.4.1.1429.6.1.1.10.1
		-- 1.3.6.1.4.1.1429.6.1.1.10.1
		drivers OBJECT-IDENTITY
			STATUS obsolete
			DESCRIPTION 
				"This node has been obsoleted because it
				did not explicitly refer to the DHCT drivers
				organization. A new node is created -- dhctDrivers --
				to remedy the situation."
			::= { saOrgs 1 }

		
--  1.3.6.1.4.1.1429.6.1.1.10.2
-- 1.3.6.1.4.1.1429.6.1.1.10.2
		-- 1.3.6.1.4.1.1429.6.1.1.10.2
		dhctDrivers OBJECT-IDENTITY
			STATUS current
			DESCRIPTION 
				"Node for DHCT drivers experimental MIBs."
			::= { saOrgs 2 }

		
--  1.3.6.1.4.1.1429.6.1.1.10.3
-- 1.3.6.1.4.1.1429.6.1.1.10.3
		-- 1.3.6.1.4.1.1429.6.1.1.10.3
		international OBJECT-IDENTITY
			STATUS current
			DESCRIPTION 
				"Node for experimental MIBs by the International
				group. "
			::= { saOrgs 3 }

		
--  1.3.6.1.4.1.1429.6.1.1.10.4
-- 1.3.6.1.4.1.1429.6.1.1.10.4
		-- 1.3.6.1.4.1.1429.6.1.1.10.4
		saOrgPtv OBJECT-IDENTITY
			STATUS current
			DESCRIPTION 
				"Node for experimental MIBs by PTV."
			::= { saOrgs 4 }

		
	
	END

--
-- SA-EXP-DBDS-MIB.my
--
