--****************************************************************************
--    Description:
--
--    MIB for runtime management of the FTP client
--		
--****************************************************************************
--    Revision History:
--
--****************************************************************************


UBEE-FTP-MGMT-MIB DEFINITIONS ::= BEGIN

IMPORTS
    MODULE-IDENTITY,
    OBJECT-TYPE,
    Counter32,
    Integer32,
    Unsigned32
        FROM SNMPv2-SMI
    DisplayString
        FROM SNMPv2-TC
    InetAddressType,
    InetAddress
        FROM INET-ADDRESS-MIB
    cableDataMgmtMIBObjects
        FROM UBEE-CABLEDATA-MGMT-MIB;
                
ftpMgmt MODULE-IDENTITY
    LAST-UPDATED "201103010000Z"
    ORGANIZATION "Ubee Corporation"
    CONTACT-INFO
        "	Ubee Interactive Global Headquarters

        Postal: 6F-9, No.38, Taiyuan St.
        		Jhubei City Hsinchu County 302
        		Taiwan, R.O.C.

           Tel: +886-3-560-0010

        E-mail: asupport@ubeeinteractive.com"
    DESCRIPTION
        "Ubee proprietary MIB for runtime management and configuration
         of objects related to the FTP client."
    REVISION      "201101120000Z"
    DESCRIPTION
        "Added a put option to the ftpCommand. Added the ftpPutFilenamePath
         and ftpPutFileSize objects."
    REVISION      "200908120000Z"
    DESCRIPTION
        "Added a value range for ftpServerPort."
    REVISION      "200903040000Z"
    DESCRIPTION
        "Initial version of this MIB module."
    ::= { cableDataMgmtMIBObjects 17 }
    
ftpIpStackInterface OBJECT-TYPE
    SYNTAX      Integer32 (1..8)
    MAX-ACCESS  read-write
    STATUS      current
    DESCRIPTION
        "Specifies the IP stack which will be used for FTP transfers."
    DEFVAL { 1 }
    ::= { ftpMgmt 1 }

ftpServerAddressType OBJECT-TYPE
    SYNTAX      InetAddressType
    MAX-ACCESS  read-write
    STATUS      current
    DESCRIPTION
        "The type of internet address used for ftpServerAddress."
    ::= { ftpMgmt 2 }
    
ftpServerAddress OBJECT-TYPE
    SYNTAX      InetAddress
    MAX-ACCESS  read-write
    STATUS      current
    DESCRIPTION
        "The internet address of the FTP server used for FTP transfers."
    ::= { ftpMgmt 3 }
    
ftpServerPort OBJECT-TYPE
    SYNTAX      Integer32 (1..65535)
    MAX-ACCESS  read-write
    STATUS      current
    DESCRIPTION
        "The TCP port on the FTP server to which the client will attempt to 
         connect."
    DEFVAL { 20 }
    ::= { ftpMgmt 4 }
    
ftpUserName OBJECT-TYPE
    SYNTAX      DisplayString (SIZE (0..255))
    MAX-ACCESS  read-write
    STATUS      current
    DESCRIPTION
        "The user name to be used when logging in to the FTP server."
    DEFVAL { "" }
    ::= { ftpMgmt 5 }

ftpPassword OBJECT-TYPE
    SYNTAX      DisplayString (SIZE (0..255))
    MAX-ACCESS  read-write
    STATUS      current
    DESCRIPTION
        "The password to be used when logging in to the FTP server."
    DEFVAL { "" }
    ::= { ftpMgmt 6 }
    
ftpFilename OBJECT-TYPE
    SYNTAX      DisplayString (SIZE (0..255))
    MAX-ACCESS  read-write
    STATUS      current
    DESCRIPTION
        "The path to the file to be transferred."
    DEFVAL { "" }
    ::= { ftpMgmt 7 }
    
ftpCommand OBJECT-TYPE
    SYNTAX      INTEGER {
                cancel(0),
                get(1),
                put(2)
    }
    MAX-ACCESS  read-write
    STATUS      current
    DESCRIPTION
        "Used to invoke an FTP command, or cancel a command which is in 
         progress.  When read, indicates the most recent command.  Note that
         the value of this object does not indicate the current transfer 
         status.  Current status should be read from ftpTransferStatus."
    ::= { ftpMgmt 8 }
    
ftpTransferStatus OBJECT-TYPE
    SYNTAX      INTEGER {
                idle(0),
                fileStatusOk(150),
                serviceReady(200),
                sessionReady(221),
                transferComplete(226),
                passwordOk(230),
                userNameOk(331),
                serviceNotAvail(421),
                invalidLogin(530),
                fileNotFound(550),
                socketConnectFailure(600) -- This is a BRCM extension to the FTP status codes
    }
    MAX-ACCESS  read-only
    STATUS      current
    DESCRIPTION
        "Indicates the status of the file transfer which is currently in 
         progress, or which most recently completed.  If no file transfer has
         been initiated, this object returns a value of idle(0)."
    ::= { ftpMgmt 9 }
    
ftpTransferPayloadBytes OBJECT-TYPE
    SYNTAX      Counter32
    MAX-ACCESS  read-only
    STATUS      current
    DESCRIPTION
        "Indicates the number of file data payload bytes transferred during the 
         file transfer which is currently in progress, or which most recently 
         completed.  For transfers which complete successfully, the value of
         this object will be equal to the size of the file transferred."
    ::= { ftpMgmt 10 }

ftpTransferTotalBytes OBJECT-TYPE
    SYNTAX      Counter32
    MAX-ACCESS  read-only
    STATUS      current
    DESCRIPTION
        "Indicates the total number of bytes transferred during the 
         file transfer which is currently in progress, or which most recently 
         completed.  This value includes file data payload as well as FTP 
         framing data and all IP and layer 2 headers.  This value should be 
         used when calculating transfer throughput."
    ::= { ftpMgmt 11 }
    
ftpTransferElapsedTime OBJECT-TYPE
    SYNTAX      Counter32
    UNITS       "milliseconds"
    MAX-ACCESS  read-only
    STATUS      current
    DESCRIPTION
        "Indicates the total elapsed time of the file transfer which is 
         currently in progress, or which most recently completed."
    ::= { ftpMgmt 12 }
    
ftpTransferThroughput OBJECT-TYPE
    SYNTAX      Unsigned32
    UNITS       "bits per second"
    MAX-ACCESS  read-only
    STATUS      current
    DESCRIPTION
        "Indicates the calculated throughput during the file transfer which is
         currently in progress, or which most recently completed.  This value
         is calculated by dividing ftpTransferTotalBytes by 
         ftpTransferElapsedTime."
    ::= { ftpMgmt 13 }  
    
ftpPutFileSize OBJECT-TYPE
    SYNTAX      Unsigned32 (1..50000)
    UNITS       "kBytes"
    MAX-ACCESS  read-write
    STATUS      current
    DESCRIPTION
        "The number of data bytes to send for a FTP PUT (upload) operation.
        The PUT data is internally generated random data of the size specifed by
        this object. The filesize is specified in kilobytes."
    DEFVAL { 10 }
    ::= { ftpMgmt 14 }

ftpPutFilenamePath OBJECT-TYPE
    SYNTAX      DisplayString (SIZE (0..255))
    MAX-ACCESS  read-write
    STATUS      current
    DESCRIPTION
        "The FTP PUT (upload) operation uses a unique (internally generated)
        upload filename. This object specifies the path to be prepended to the 
        upload filename. The location, specified by this path, should have 
        write/delete acccess on the server. If not specifed, no path is prepended 
        to the filename. If specified the path value should end with the appropriate
        separator e.g., \ or /."
    DEFVAL { "" }
    ::= { ftpMgmt 15 }
   
END
