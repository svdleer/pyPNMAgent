--
-- SCIATL-COMMON-MIB.my
-- MIB generated by MG-SOFT Visual MIB Builder Version 4.0 Build 349
-- Friday, May 02, 2003 at 14:14:26
--

-- Revision 1 : R. Killick
-- Date: Thursday, April 24, 2003 at 16:35:28
-- Comment:
-- 
-- Revision 2 : Updated Description
-- Date: Friday, May 02, 2003 at 14:13:14
-- Comment:
-- 
	SCIATL-COMMON-MIB DEFINITIONS ::= BEGIN
 
		IMPORTS
			OBJECT-GROUP, MODULE-COMPLIANCE			
				FROM SNMPv2-CONF			
			enterprises, Integer32, OBJECT-TYPE, MODULE-IDENTITY, OBJECT-IDENTITY			
				FROM SNMPv2-SMI;
	
	
		-- 1.3.6.1.4.1.1429
		scientific-atlanta MODULE-IDENTITY 
			LAST-UPDATED "200305021413Z"		-- May 02, 2003 at 14:13 GMT
			ORGANIZATION 
				"Scientific-Atlanta"
			CONTACT-INFO 
				"Your contact info"
			DESCRIPTION 
				"This is the S-A enterprise node."
			REVISION "200305021413Z"		-- May 02, 2003 at 14:13 GMT
			DESCRIPTION 
				" "
			REVISION "200304241635Z"		-- April 24, 2003 at 16:35 GMT
			DESCRIPTION 
				" "
			REVISION "200210251736Z"		-- October 25, 2002 at 17:36 GMT
			DESCRIPTION 
				"Conversion of SCIATL-COMMON-MIB from V1 to V2"
			REVISION "200210251741Z"		-- October 25, 2002 at 17:41 GMT
			DESCRIPTION 
				"Conversion of SCIATL-COMMON-MIB from V1 to V2"
			REVISION "200304151537Z"		-- April 15, 2003 at 15:37 GMT
			DESCRIPTION 
				"New nodes have been added to the existing
				MIB to allow a more modern approach
				to the organization of information in
				the MIB. For example, nodes have 
				been added for requirements,  products
				and product registration, as well as an
				experimental node to facilitate the
				development of new MIB modules inhouse. "
			REVISION "200304161623Z"		-- April 16, 2003 at 16:23 GMT
			DESCRIPTION 
				"Added generic, capabilities and subnodes
				to registration."
			::= { enterprises 1429 }

		
	
--
-- Type definitions
--
	
		ActivationStatus ::= INTEGER
			{
			on(1),
			off(2)
			}

	
--
-- Node definitions
--
	
		-- 1.3.6.1.4.1.1429.1
		saTerrestrial OBJECT IDENTIFIER ::= { scientific-atlanta 1 }

		
		-- 1.3.6.1.4.1.1429.1.1
		saDigitalServices OBJECT IDENTIFIER ::= { saTerrestrial 1 }

		
		-- 1.3.6.1.4.1.1429.1.1.1
		saDncs OBJECT IDENTIFIER ::= { saDigitalServices 1 }

		
		-- 1.3.6.1.4.1.1429.1.1.2
		saDhe OBJECT IDENTIFIER ::= { saDigitalServices 2 }

		
		-- 1.3.6.1.4.1.1429.1.1.2.1
		saQamMod OBJECT IDENTIFIER ::= { saDhe 1 }

		
		-- 1.3.6.1.4.1.1429.1.1.2.2
		saDavicQpskModem OBJECT IDENTIFIER ::= { saDhe 2 }

		
		-- 1.3.6.1.4.1.1429.1.1.2.3
		saOQpskMod OBJECT IDENTIFIER ::= { saDhe 3 }

		
		-- 1.3.6.1.4.1.1429.1.1.2.4
		saOQpskDemod OBJECT IDENTIFIER ::= { saDhe 4 }

		
		-- 1.3.6.1.4.1.1429.1.1.2.5
		saCaQam OBJECT IDENTIFIER ::= { saDhe 5 }

		
		-- 1.3.6.1.4.1.1429.1.1.2.6
		saTerrHeadendGPIC OBJECT IDENTIFIER ::= { saDhe 6 }

		
		-- 1.3.6.1.4.1.1429.1.1.2.7
		saTerrHeadendSTA OBJECT IDENTIFIER ::= { saDhe 7 }

		
		-- 1.3.6.1.4.1.1429.1.1.2.8
		saTerrHeadendMQAM OBJECT IDENTIFIER ::= { saDhe 8 }

		
		-- 1.3.6.1.4.1.1429.1.1.2.10
		saBig OBJECT IDENTIFIER ::= { saDhe 10 }

		
		-- 1.3.6.1.4.1.1429.1.1.2.11
		saBigCards OBJECT IDENTIFIER ::= { saDhe 11 }

		
		-- 1.3.6.1.4.1.1429.1.1.2.20
		saEncapsulator OBJECT IDENTIFIER ::= { saDhe 20 }

		
		-- 1.3.6.1.4.1.1429.1.1.2.100
		saDheAlarmInfo OBJECT IDENTIFIER ::= { saDhe 100 }

		
		-- 1.3.6.1.4.1.1429.1.1.2.100.1
		saDheAlarmTable OBJECT-TYPE
			SYNTAX SEQUENCE OF SaDheAlarmEntry
			MAX-ACCESS not-accessible
			STATUS current
			DESCRIPTION
				"A table used to describe alarm information."
			::= { saDheAlarmInfo 1 }

		
		-- 1.3.6.1.4.1.1429.1.1.2.100.1.1
		saDheAlarmEntry OBJECT-TYPE
			SYNTAX SaDheAlarmEntry
			MAX-ACCESS not-accessible
			STATUS current
			DESCRIPTION
				"Each row entry describes an alarm that can be raised by this element."
			INDEX { saDheAlarmId }
			::= { saDheAlarmTable 1 }

		
		SaDheAlarmEntry ::=
			SEQUENCE { 
				saDheAlarmId
					INTEGER,
				saDheAlarmNetMgmtId
					Integer32,
				saDheAlarmLevel
					INTEGER,
				saDheAlarmStatus
					INTEGER,
				saDheAlarmThreshold
					Integer32,
				saDheAlarmTime
					Integer32
			 }

		-- 1.3.6.1.4.1.1429.1.1.2.100.1.1.1
		saDheAlarmId OBJECT-TYPE
			SYNTAX INTEGER (0..65535)
			MAX-ACCESS read-only
			STATUS current
			DESCRIPTION
				"Unique number identifying the alarm type."
			::= { saDheAlarmEntry 1 }

		
		-- 1.3.6.1.4.1.1429.1.1.2.100.1.1.2
		saDheAlarmNetMgmtId OBJECT-TYPE
			SYNTAX Integer32
			MAX-ACCESS read-only
			STATUS current
			DESCRIPTION
				"The number used within the network management platform to uniquely
				identify each type of alarm among all supported network element types."
			::= { saDheAlarmEntry 2 }

		
		-- 1.3.6.1.4.1.1429.1.1.2.100.1.1.3
		saDheAlarmLevel OBJECT-TYPE
			SYNTAX INTEGER
				{
				disabled(1),
				critical(2),
				major(3),
				minor(4),
				status(5)
				}
			MAX-ACCESS read-only
			STATUS current
			DESCRIPTION
				"Describes the severity level associated with this alarm."
			::= { saDheAlarmEntry 3 }

		
		-- 1.3.6.1.4.1.1429.1.1.2.100.1.1.4
		saDheAlarmStatus OBJECT-TYPE
			SYNTAX INTEGER
				{
				set(1),
				clear(2)
				}
			MAX-ACCESS read-only
			STATUS current
			DESCRIPTION
				"The current status for this alarm condition."
			::= { saDheAlarmEntry 4 }

		
		-- 1.3.6.1.4.1.1429.1.1.2.100.1.1.5
		saDheAlarmThreshold OBJECT-TYPE
			SYNTAX Integer32
			MAX-ACCESS read-only
			STATUS current
			DESCRIPTION
				"Determines the number of times per time quantum that this alarm
				condition should be detected before reporting an active condition.
				Note that the time quantum is alarm specific.  For alarms that do
				not use a threshold, this value will be 1."
			::= { saDheAlarmEntry 5 }

		
		-- 1.3.6.1.4.1.1429.1.1.2.100.1.1.6
		saDheAlarmTime OBJECT-TYPE
			SYNTAX Integer32
			MAX-ACCESS read-only
			STATUS current
			DESCRIPTION
				"The time when this alarm condition last became active, expressed in
				Unix epoch time."
			::= { saDheAlarmEntry 6 }

		
		-- 1.3.6.1.4.1.1429.1.1.3
		saConsumer OBJECT IDENTIFIER ::= { saDigitalServices 3 }

		
		-- 1.3.6.1.4.1.1429.1.2
		saAnalogServices OBJECT IDENTIFIER ::= { saTerrestrial 2 }

		
		-- 1.3.6.1.4.1.1429.1.3
		saTelephonyServices OBJECT IDENTIFIER ::= { saTerrestrial 3 }

		
		-- 1.3.6.1.4.1.1429.2
		saSatellite OBJECT IDENTIFIER ::= { scientific-atlanta 2 }

		
		-- 1.3.6.1.4.1.1429.3
		saInstrumentation OBJECT IDENTIFIER ::= { scientific-atlanta 3 }

		
		-- 1.3.6.1.4.1.1429.4
		scientific-atlantaConformance OBJECT IDENTIFIER ::= { scientific-atlanta 4 }

		
		-- 1.3.6.1.4.1.1429.4.1
		scientific-atlantaGroups OBJECT IDENTIFIER ::= { scientific-atlantaConformance 1 }

		
		-- 1.3.6.1.4.1.1429.4.1.1
		currentObjectGroup OBJECT-GROUP
			OBJECTS { saDheAlarmId, saDheAlarmNetMgmtId, saDheAlarmLevel, saDheAlarmStatus, saDheAlarmThreshold, 
				saDheAlarmTime }
			STATUS current
			DESCRIPTION 
				"Enter the description of the created OBJECT-GROUP."
			::= { scientific-atlantaGroups 1 }

		
		-- 1.3.6.1.4.1.1429.4.2
		scientific-atlantaCompliances OBJECT IDENTIFIER ::= { scientific-atlantaConformance 2 }

		
		-- 1.3.6.1.4.1.1429.4.2.1
		basicCompliance MODULE-COMPLIANCE
			STATUS current
			DESCRIPTION 
				"Enter the description of the created MODULE-COMPLIANCE."
			MODULE SCIATL-COMMON-MIB
				MANDATORY-GROUPS { currentObjectGroup }
			::= { scientific-atlantaCompliances 1 }

		
		-- 1.3.6.1.4.1.1429.5
		saProducts OBJECT-IDENTITY
			STATUS current
			DESCRIPTION 
				"Contains all S-A networks ans services: DBDS for example."
			::= { scientific-atlanta 5 }

		
		-- 1.3.6.1.4.1.1429.5.1
		saDBDS OBJECT-IDENTITY
			STATUS current
			DESCRIPTION 
				"This tree contains all the DBDS hardware components: DNCS, XDC, DHCT etc."
			::= { saProducts 1 }

		
		-- 1.3.6.1.4.1.1429.6
		saExperimental OBJECT-IDENTITY
			STATUS current
			DESCRIPTION 
				"The tree is reserved for experimental MIB
				designs not yet mature to be officially
				published."
			::= { scientific-atlanta 6 }

		
		-- 1.3.6.1.4.1.1429.6.1
		saExpDbds OBJECT-IDENTITY
			STATUS current
			DESCRIPTION 
				"DBDS experimental modules are registered here."
			::= { saExperimental 1 }

		
		-- 1.3.6.1.4.1.1429.7
		saRegistration OBJECT-IDENTITY
			STATUS current
			DESCRIPTION 
				"This is the registration tree that 
				contains the OIDs for all S-A products.
				"
			::= { scientific-atlanta 7 }

		
		-- 1.3.6.1.4.1.1429.7.1
		saModules OBJECT-IDENTITY
			STATUS current
			DESCRIPTION 
				"All SA MIB modules are registered here."
			::= { saRegistration 1 }

		
		-- 1.3.6.1.4.1.1429.7.2
		saDbdsReg OBJECT-IDENTITY
			STATUS current
			DESCRIPTION 
				"Sub-tree for registration of DBDS products."
			::= { saRegistration 2 }

		
		-- 1.3.6.1.4.1.1429.8
		saRequirements OBJECT-IDENTITY
			STATUS current
			DESCRIPTION 
				"This tree is used to register the OIDs of 
				management application requirement specs. These specs describe the objects and events used by a functional area of a management app."
			::= { scientific-atlanta 8 }

		
		-- 1.3.6.1.4.1.1429.9
		saGeneric OBJECT-IDENTITY
			STATUS current
			DESCRIPTION 
				"This node contains OIDs for modules that
				are used by a broad range of SA products."
			::= { scientific-atlanta 9 }

		
		-- 1.3.6.1.4.1.1429.9.1
		saDbdsGen OBJECT-IDENTITY
			STATUS current
			DESCRIPTION 
				"Modules that apply to several DBDS products
				are registered here."
			::= { saGeneric 1 }

		
		-- 1.3.6.1.4.1.1429.10
		saCapabilities OBJECT-IDENTITY
			STATUS current
			DESCRIPTION 
				"This node registers agent capabilities/profiles."
			::= { scientific-atlanta 10 }

		
		-- 1.3.6.1.4.1.1429.10.1
		saDbdsCap OBJECT-IDENTITY
			STATUS current
			DESCRIPTION 
				"Used for DBDS agent profiles."
			::= { saCapabilities 1 }

		
	
	END

--
-- SCIATL-COMMON-MIB.my
--
