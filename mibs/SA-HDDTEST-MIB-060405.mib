--
-- SA-HDDTEST-MIB.mib
-- MIB generated by MG-SOFT Visual MIB Builder Version 4.0 Build 349
-- Thursday, June 16, 2005 at 14:26:01
--

	SA-HDDTEST-MIB DEFINITIONS ::= BEGIN
 
		IMPORTS
			saHddTestMib			
				FROM SA-DBDSPROD-MIB			
			saSmartStatusDriveIndex			
				FROM SA-SFF8035-MIB			
			saModules			
				FROM SCIATL-COMMON-MIB			
			OBJECT-GROUP			
				FROM SNMPv2-CONF			
			Integer32, Unsigned32, OBJECT-TYPE, MODULE-IDENTITY, OBJECT-IDENTITY			
				FROM SNMPv2-SMI			
			DisplayString			
				FROM SNMPv2-TC;
	
	
-- Scientific-Atlanta Proprietary Information
-- 
-- Copyright 2005 Scientific-Atlanta, Inc.
-- 
-- All rights reserved.
-- 
--  
-- 
-- Unauthorized copying and distribution are prohibited.  
-- 
-- No part of this MIB may be reprinted, reproduced or utilized
-- 
-- in any form or by any electronic, mechanical, or other means, now known or
-- 
-- hereafter invented, including photocopying and recording, or using any
-- 
-- information storage and retrieval system, without permission in writing
-- 
-- from Scientific-Atlanta, Inc.
-- 
		-- 1.3.6.1.4.1.1429.7.1.30
		saHddTestMibModule MODULE-IDENTITY 
			LAST-UPDATED "200506042155Z"		-- June 04, 2005 at 21:55 GMT
			ORGANIZATION 
				"Scientific-Atlanta, Inc."
			CONTACT-INFO 
				"DBDS Software Engineering & Architecture
				Scientific-Atlanta
				5030 Sugarloaf Parkway
				Lawrencville, GA 30044
				"
			DESCRIPTION 
				"The Scientific-Atlanta MIB module for tracking  certain hard drive tests.
				
				PRELIMINARY FOR REVIEW PURPOSES ONLY"
			::= { saModules 30 }

		
	
	
--
-- Node definitions
--
	
		-- 1.3.6.1.4.1.1429.5.1.10.1.1
		saHddTestConf OBJECT-IDENTITY
			STATUS current
			DESCRIPTION 
				"Conformance"
			::= { saHddTestMib 1 }

		
		-- 1.3.6.1.4.1.1429.5.1.10.1.1.1
		saHddTestGroups OBJECT-IDENTITY
			STATUS current
			DESCRIPTION 
				"Object groups for the SA-HDDTEST-MIB"
			::= { saHddTestConf 1 }

		
		-- 1.3.6.1.4.1.1429.5.1.10.1.1.1.1
		saHddTestMainTableGroup OBJECT-GROUP
			OBJECTS { saHddTestMainModelNumber, saHddTestMainSerialNumber, saHddTestMainFirmwareVersion, saHddTestMainSeqNum, saHddTestMainDriveInitStatus, 
				saHddTestMainPerfExecStatus, saHddTestMainPerfCmdErrCode, saHddTestMainIdReadTime, saHddTestMainMdReadTime, saHddTestMainOdReadTime, 
				saHddTestMainIdWriteTime, saHddTestMainMdWriteTime, saHddTestMainOdWriteTime, saHddTestMainItfsReadTime, saHddTestMainAvfsRecoveredSectors
				 }
			STATUS current
			DESCRIPTION 
				"Group for saHddTestMainTable"
			::= { saHddTestGroups 1 }

		
		-- 1.3.6.1.4.1.1429.5.1.10.1.1.2
		saHddTestCompls OBJECT-IDENTITY
			STATUS current
			DESCRIPTION 
				"Compliance descriptions for the SA-HDDTEST-MIB."
			::= { saHddTestConf 2 }

		
		-- 1.3.6.1.4.1.1429.5.1.10.1.2
		saHddTestObjs OBJECT-IDENTITY
			STATUS current
			DESCRIPTION 
				"The objects of the SA-SFF8035-MIB module."
			::= { saHddTestMib 2 }

		
		-- 1.3.6.1.4.1.1429.5.1.10.1.2.1
		saHddTestMainTable OBJECT-TYPE
			SYNTAX SEQUENCE OF SaHddTestMainEntry
			MAX-ACCESS not-accessible
			STATUS current
			DESCRIPTION
				"This table reports the results of SMART and Performance
				tests that may have been performed on hard disk drives. 
				Each entry provides the results of the last such test run 
				on the associated drive."
			::= { saHddTestObjs 1 }

		
		-- 1.3.6.1.4.1.1429.5.1.10.1.2.1.1
		saHddTestMainEntry OBJECT-TYPE
			SYNTAX SaHddTestMainEntry
			MAX-ACCESS not-accessible
			STATUS current
			DESCRIPTION
				"A row in the table."
			INDEX { saSmartStatusDriveIndex }
			::= { saHddTestMainTable 1 }

		
		SaHddTestMainEntry ::=
			SEQUENCE { 
				saHddTestMainModelNumber
					DisplayString,
				saHddTestMainSerialNumber
					DisplayString,
				saHddTestMainFirmwareVersion
					DisplayString,
				saHddTestMainSeqNum
					Integer32,
				saHddTestMainDriveInitStatus
					INTEGER,
				saHddTestMainPerfExecStatus
					INTEGER,
				saHddTestMainPerfCmdErrCode
					OCTET STRING,
				saHddTestMainIdReadTime
					Unsigned32,
				saHddTestMainMdReadTime
					Unsigned32,
				saHddTestMainOdReadTime
					Unsigned32,
				saHddTestMainIdWriteTime
					Unsigned32,
				saHddTestMainMdWriteTime
					Unsigned32,
				saHddTestMainOdWriteTime
					Unsigned32,
				saHddTestMainItfsReadTime
					Unsigned32,
				saHddTestMainAvfsRecoveredSectors
					Unsigned32
			 }

		-- 1.3.6.1.4.1.1429.5.1.10.1.2.1.1.1
		saHddTestMainModelNumber OBJECT-TYPE
			SYNTAX DisplayString
			MAX-ACCESS read-only
			STATUS current
			DESCRIPTION
				"The model number of the drive.
				"
			::= { saHddTestMainEntry 1 }

		
		-- 1.3.6.1.4.1.1429.5.1.10.1.2.1.1.2
		saHddTestMainSerialNumber OBJECT-TYPE
			SYNTAX DisplayString
			MAX-ACCESS read-only
			STATUS current
			DESCRIPTION
				"The serial number of the drive."
			::= { saHddTestMainEntry 2 }

		
		-- 1.3.6.1.4.1.1429.5.1.10.1.2.1.1.3
		saHddTestMainFirmwareVersion OBJECT-TYPE
			SYNTAX DisplayString
			MAX-ACCESS read-only
			STATUS current
			DESCRIPTION
				"The Firmware Version Number of the drive."
			::= { saHddTestMainEntry 3 }

		
		-- 1.3.6.1.4.1.1429.5.1.10.1.2.1.1.4
		saHddTestMainSeqNum OBJECT-TYPE
			SYNTAX Integer32
			MAX-ACCESS read-only
			STATUS current
			DESCRIPTION
				"Sequence number of the currently reported test result set"
			::= { saHddTestMainEntry 4 }

		
		-- 1.3.6.1.4.1.1429.5.1.10.1.2.1.1.5
		saHddTestMainDriveInitStatus OBJECT-TYPE
			SYNTAX INTEGER
				{
				notRun(0),
				completedOk(1),
				completedFail(2),
				incompoleteTimedOut(3),
				testInterrupted(4),
				notStarted(5),
				notQualified(6),
				cancelled(7)
				}
			MAX-ACCESS read-only
			STATUS current
			DESCRIPTION
				"HDD initialization status
				
				notRun        = Drive Initialization not run
				completedOk   = Completed with success
				completedFail = Completed with failure
				incompleteTimedOut = Started but did not finish because it timed out
				testInterrupted = Started but did not finish because of an unexpected interruption
				notStarted = Test not started - opportunity window closed
				notQualified = Test not started - disqualified drive type
				cancelled = Test not started - cancelled by passthru
				"
			::= { saHddTestMainEntry 5 }

		
		-- 1.3.6.1.4.1.1429.5.1.10.1.2.1.1.6
		saHddTestMainPerfExecStatus OBJECT-TYPE
			SYNTAX INTEGER
				{
				notRun(0),
				completedOk(1),
				completedFail(2),
				incompleteTimedOut(3)
				}
			MAX-ACCESS read-only
			STATUS current
			DESCRIPTION
				"Performance test execution status
				
				notRun        = Test not run
				completedOk   = Completed with success
				completedFail = Completed with failure; see saHddTestMainPerfCmdErrCode
				incompleteTimedOut = The test started but did not finish because it timed out"
			::= { saHddTestMainEntry 6 }

		
		-- 1.3.6.1.4.1.1429.5.1.10.1.2.1.1.7
		saHddTestMainPerfCmdErrCode OBJECT-TYPE
			SYNTAX OCTET STRING
			MAX-ACCESS read-only
			STATUS current
			DESCRIPTION
				"If failure reported by saHddTestMainPerfExecStatus, then this reports
				a more detailed failure code reflecting the ATA/ATAPI-5 defined
				error register.
				
				If no error is being reported, this value is zero (0)."
			REFERENCE
				"ATA/ATAPI-5 Specification - Error Register"
			::= { saHddTestMainEntry 7 }

		
		-- 1.3.6.1.4.1.1429.5.1.10.1.2.1.1.8
		saHddTestMainIdReadTime OBJECT-TYPE
			SYNTAX Unsigned32
			UNITS "milli-seconds"
			MAX-ACCESS read-only
			STATUS current
			DESCRIPTION
				"Inside-diameter read time in ms; 
				0 implies no data is available for this item"
			::= { saHddTestMainEntry 8 }

		
		-- 1.3.6.1.4.1.1429.5.1.10.1.2.1.1.9
		saHddTestMainMdReadTime OBJECT-TYPE
			SYNTAX Unsigned32
			UNITS "milli-seconds"
			MAX-ACCESS read-only
			STATUS current
			DESCRIPTION
				"Middle-diameter read time in ms; 
				0 implies no data is available for this item"
			::= { saHddTestMainEntry 9 }

		
		-- 1.3.6.1.4.1.1429.5.1.10.1.2.1.1.10
		saHddTestMainOdReadTime OBJECT-TYPE
			SYNTAX Unsigned32
			UNITS "milli-seconds"
			MAX-ACCESS read-only
			STATUS current
			DESCRIPTION
				"Outer-diameter read time in ms; 
				0 implies no data is available for this item"
			::= { saHddTestMainEntry 10 }

		
		-- 1.3.6.1.4.1.1429.5.1.10.1.2.1.1.11
		saHddTestMainIdWriteTime OBJECT-TYPE
			SYNTAX Unsigned32
			UNITS "milli-seconds"
			MAX-ACCESS read-only
			STATUS current
			DESCRIPTION
				"Inside-diameter write time in ms; 
				0 implies no data is available for this item"
			::= { saHddTestMainEntry 11 }

		
		-- 1.3.6.1.4.1.1429.5.1.10.1.2.1.1.12
		saHddTestMainMdWriteTime OBJECT-TYPE
			SYNTAX Unsigned32
			UNITS "milli-seconds"
			MAX-ACCESS read-only
			STATUS current
			DESCRIPTION
				"Middle-diameter write time in ms; 
				0 implies no data is available for this item"
			::= { saHddTestMainEntry 12 }

		
		-- 1.3.6.1.4.1.1429.5.1.10.1.2.1.1.13
		saHddTestMainOdWriteTime OBJECT-TYPE
			SYNTAX Unsigned32
			UNITS "milli-seconds"
			MAX-ACCESS read-only
			STATUS current
			DESCRIPTION
				"Outer-diameter write time in ms; 
				0 implies no data is available for this item"
			::= { saHddTestMainEntry 13 }

		
		-- 1.3.6.1.4.1.1429.5.1.10.1.2.1.1.14
		saHddTestMainItfsReadTime OBJECT-TYPE
			SYNTAX Unsigned32
			UNITS "milli-seconds"
			MAX-ACCESS read-only
			STATUS current
			DESCRIPTION
				"The time (in ms) taken to read the ITFS; 
				0 implies no data is available for this item"
			::= { saHddTestMainEntry 14 }

		
		-- 1.3.6.1.4.1.1429.5.1.10.1.2.1.1.15
		saHddTestMainAvfsRecoveredSectors OBJECT-TYPE
			SYNTAX Unsigned32
			MAX-ACCESS read-only
			STATUS current
			DESCRIPTION
				"The number of sectors that were zero-written in the AVFS 
				partition during the write performance test."
			::= { saHddTestMainEntry 15 }

		
	
	END

--
-- SA-HDDTEST-MIB.mib
--
