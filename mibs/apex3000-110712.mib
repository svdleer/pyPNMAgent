APEX3000-MIB DEFINITIONS ::= BEGIN


IMPORTS
        MODULE-IDENTITY,
        IpAddress,
        TimeTicks,
        OBJECT-TYPE,
        NOTIFICATION-TYPE,
        Counter32,
        Unsigned32,
        Integer32
                                FROM SNMPv2-SMI

        DisplayString           FROM SNMPv2-TC

        giproducts              FROM BCS-IDENT-MIB

        trapIdentifier,
        trapSequenceId,
        trapNetworkElemModelNumber,
        trapNetworkElemSerialNum,
        trapPerceivedSeverity,
        trapNetworkElemOperState,
        trapNetworkElemAlarmStatus,
        trapNetworkElemAdminState,
        trapNetworkElemAvailStatus,
        trapText,
        trapNETrapLastTrapTimeStamp,
        trapChangedObjectId,
        trapAdditionalInfoInteger1,
        trapAdditionalInfoInteger2,
        trapAdditionalInfoInteger3,
        trapChangedValueDisplayString,
        trapChangedValueOID,
        trapChangedValueIpAddress,
        trapChangedValueInteger
                                FROM BCS-TRAPS-MIB;

-- ------------------------------------------------------------------------------

apex3000    MODULE-IDENTITY
        LAST-UPDATED "201211070000Z"

        ORGANIZATION "Motorola Mobility Holdings, Inc"
        CONTACT-INFO "Motorola Technical Response Center
                      Inside USA     1-888-944-HELP (1-888-944-4357)
                      Outside USA    1-215-323-0044
                      TRC Hours:
                      Monday through Friday 8 am to 7 pm Eastern Standard Time
                      Saturdays            10 am to 5 pm Eastern Standard Time"

        DESCRIPTION  "The MIB module for the APEX3000."
        
        REVISION     "201211070000Z"
        DESCRIPTION
                     "Version 1.10:
                     
                      November 7, 2012
                      - Added apexGbeConfigFailoverMacAddress to Gbe Config table.
                     "

        REVISION     "201210310000Z"
        DESCRIPTION
                     "Version 1.9:
                     
                      October 31, 2012
                      - Added apexRfModuleStatusCodeFileDownload.
                     "

        REVISION     "201209280000Z"
        DESCRIPTION
                     "Version 1.8:
                     
                      September 28, 2012
                      - Added apexRtspConfControllerVendorName.
                      
                      September 27, 2012
                      - Added apexSesContConfReportUdpMappings.
                      - Added apexUdpMapBlade1ConfInputInterface..apexUdpMapBlade8ConfInputInterface.
                      - Added apexSesContStatusReportUdpMapApplyText.
                     "

        REVISION     "201208100000Z"
        DESCRIPTION
                     "Version 1.7:
                      
                      August 10, 2012
                      - Added apexSysStatDtiModuleFpgaVersion and
                        apexHostModuleStatusTable.
                     "
        
        REVISION     "201207170000Z"
        DESCRIPTION
                     "Version 1.6:
                      
                      July 17, 2012
                      - Added apexImportFile.
                      
                      July 12, 2012
                      - Corrections to apply change references in various descriptions.

                      July 6, 2012
                      - Corrections to ini file and apply change references in
                        various descriptions.
                      
                      June 20, 2012
                      - Added apexQamEntitlement.
                      
                      June 14, 2012
                      - Added apexQamBladeReplicatedServicesMapped and
                        apexQamBladeReplicatedPidsMapped.
                      
                      June 13, 2012
                      - Added QAM Entitlement features ULS MIB section.
                      
                      June 12, 2012
                      - Added apexClearDepiControlConnectionFault to manually
                        clear the DEPI control connection fault alarm.
                      
                      June 11, 2012
                      - Added apexOutputTsConfBladeXQamReplicationRfPort for
                        each output stream.
                      
                      Jun 08, 2012
                      - Added apexQamBladeSimScgsProvisioned, number of SCGs
                        provisioned per blade.
                      - Added apexRoutingStatusOtsSimTable, number of SCGs
                        provisioned per OTS.
                      
                      May 29, 2012
                      - Added apexRpcQamStatTotalInUseBandwidth.               
                      
                      May 18, 2012
                      - Updated valid range of apexEcmEmmFirstPid and
                        apexEcmEmmNumberPids.
                      
                      May 18, 2012
                      - apexDepiControl sections integrated in apexDepiConfig
                        and apexDepiStatus.
                      - apexDepiControlPlaneConfig objects moved to
                        apexDepiControlConfigGeneral.
                      - Added apexDepiSessionBladeXStatusInputTsIndex in
                        apexDepiSessionBladeXStatusTable.
 
                      May 17, 2012
                      - Updated apexDepi adding control plane section, some new
                        configuration object and new session status tables.
                      - Added apexOutputTsConfBladeXDepiRemoteId. 

                      May 15, 2012
                      - Changed SYNTAX of all apexRfConfigBladeXChannelModeComboSelectAnnexC.
                      
                      April 23, 2012
                      - Modified values of apexOutputTsConfBladeXSimulcryptMode.
                        Now it can be none, enabledEmms or enabledNoEmms.
                      
                      April 18, 2012
                      - Added apexSysConfigMcEmmInsertion.
                      - Added apexOutputTsConfBladeXSimulcryptMode to 
                        apexOutputTsConfigBladeXEntry.
                      - Modified apexOutputTsConfBladeXOperatingMode description 
                        adding valid operating modes with Simulcrypt.
                      - Modified apexOutputTsConfBladeXEncryptionType description
                        adding valid combinations with Simulcrypt.
                      - Added dvb-csa algorithm to apexEncryptionConfAlgorithm.
                      
                      April 11, 2012
                      - Added apexRfConfigBladeXModesSymbolRateAnnexC entries.
                     "
                      
        REVISION     "201204200000Z"
        DESCRIPTION
                     "Version 1.5:
                      
                      April 20, 2012
                      - Changed length of apexRtspConfControllerStreamingZone
                        to 120 characters.
                      - Added support for new UDP Port Mapping Mode - 10/6.
                      - Changed the OuputTsConf Apply change for each blade to
                        include the PAT TSID.
                      - Added UDP Map status table.
                     "

        REVISION     "201203010000Z"
        DESCRIPTION
                     "Version 1.4:
                     
                      March 1, 2012
                      - Added apexRpcEdgeAnnounceEnable
                      
                      February 29, 2012
                      - Added apexUls.

                      February 17, 2012
                      - Changed descriptions of
                        apexRfConfigBladeXSubBlockChanSpacingAnnexA
                        and apexRfConfigBladeXChannelFrequencyGridSelect.

                      February 15, 2012
                      - Added apexDepi.
                     "
                     
        REVISION     "201202060000Z"
        DESCRIPTION
                     "Version 1.3:

                      February 6, 2012
                      - Added apexRpcReportSessionInfoPmt.

                      February 1, 2012
                      - Added apexQamBladeRedundConfigDefaultRfConfBlade.

                      January 31, 2012
                      - Added apexHostRedundTriggerEnet1LinkLoss and
                        apexHostRedundTriggerEnetTimer.
                      
                      January 30, 2012
                      - Added apexRpcSetupFailureStatCount.
                      - Added apexRtspSetupFailureStatCount.

                      January 27, 2012
                      - Added apexGqdStatNumOutputTs.

                      January 25, 2012
                      - Added apexRpcIncludeGenericQamDevices.
                      - Added apexSesContStatusTableApplyText.

                      January 24, 2012
                      - Added apexGenericQamDeviceTable.
                      - Added apexGenericQamDeviceApplyChange.
                      - Added apexGenericQamDeviceApplyText.
                      - Added apexGqdStatTable.

                      January 23, 2012
                      - Added apexSesContBlade1ConfQamDeviceIndex to Session table.
                      - Added apexSesContBlade1ConfCmdOutputPort to Session table.

                      January 17, 2012
                      - Added apexBladeInactiveServicesMapped.
                      - Added apexBladeMultiplexedServicesMapped.
                      - Added apexAlarmServiceInactiveError.
                      - Added apexEnableServiceInactiveError.
                      - Added apexQamBladeStatusServiceInactiveFault.
                     "

        REVISION     "201112090000Z"
        DESCRIPTION
                     "Version 1.2:

                      December 9, 2011
                      - Added apexRfErrorRfPortSwitchError.
                     "

        REVISION     "201111140000Z"
        DESCRIPTION
                     "Version 1.1:

                      November 14, 2011
                      - Added AutomaticManualTYPE,
                        apexRfConfigBladeXRfPortNprimeMaxMode, and
                        apexRfStatusRfPortNprimeMax.
                      - Updated descriptions of:
                        apexGbeInputTsInUseCount,
                        apexRfConfigBladeXRfPortSpectrumInversion,
                        apexRfConfigBladeXRfPortMute,
                        apexRfConfigBladeXRfPortRfLevel,
                        apexRfConfigBladeXRfPortNprimeMax,
                        apexRfConfigBladeXChannelRfLevelAdjust,
                        apexRfStatusRfPortRfLevelNominal,
                        apexRfStatusChannelActive,
                        apexRfStatusRfCountsChannelsAssigned,
                        and apexAlarmQamBladeRedundMismatch.
                      
                      November 1, 2011
                      - Added apexFanSpeed1FaultCondition
                        and apexFanSpeed2FaultCondition.
                     "

        REVISION     "201111010000Z"
        DESCRIPTION
                     "Version 1.0:

                      November 01, 2011
                      - Initial Revision.
                     "

         ::= {giproducts 39}

-- ------------------------------------------------------------------------------
--
-- REUSABLE TYPE DEFINITIONS
--

EnableDisableTYPE ::=  INTEGER
   {
    notApplicable (0),
    disabled      (1),
    enabled       (2)
   }

ActiveTYPE ::=  INTEGER
   {
    notApplicable (0),
    notActive     (1),
    active        (2)
   }

ApplyDataToDeviceTYPE ::= INTEGER
   {
    applyNotInProgress            (1),
    apply                         (2),
    applyNotInProgressValidData   (3),
    applyNotInProgressInvalidData (4)
   }

ResetStatisticsTYPE ::= INTEGER
   {
    notApplicable      (0),
    resetNotInProgress (1),
    reset              (2)
   }

ClearAlarmTYPE ::= INTEGER
   {
    notApplicable           (0),
    clearAlarmNotInProgress (1),
    clearAlarm              (2)
   }

AutomaticManualTYPE ::= INTEGER
   {
    automatic (0),
    manual    (1)
   }

RateComparisonTYPE ::=  INTEGER
   {
    notApplicable       (0),
    dataRate            (1),
    transportStreamRate (2)
   }

InputTsStateTYPE ::=  INTEGER
   {
    closed              (0),
    openedInUse         (1)
   }

EthernetInterfaceTYPE ::=  INTEGER
   {
    enet1         (1),
    enet2         (2)
   }

ModulePresentTYPE ::=  INTEGER
   {
    unknown (0),
    missing (1),
    present (2)
   }

ModuleLatchedTYPE ::=  INTEGER
   {
    unknown (0),
    unlatched (1),
    latched (2)
   }

ModuleAvailableTYPE ::=  INTEGER
   {
    unknown       (0),
    notAvailable  (1),
    initializing  (2),
    fwLoading     (3),
    available     (4),
    fwFailure     (5),
    shutdown      (6),
    unsupported   (7)
   }

OverflowErrorTYPE ::=  INTEGER
   {
    notApplicable   (0),
    noError         (1),
    overflow        (2)
   }

QamRfTransmissionModeTYPE ::= INTEGER
   {
    notApplicable       (0),
    annexB-ATSC-DCII    (1),
    annexA-DVB          (2),
    annexC-Asia-Pacific (3)
   }

QamRfModulationModeTYPE ::=  INTEGER
   {
    notApplicable (0),
    qam64         (1),
    qam256        (2)
   }

QamRfSpectrumInversionTYPE ::= INTEGER
   {
    notApplicable (0),
    normal        (1),
    invert        (2)
   }

QamRfMuteTYPE ::= INTEGER
   {
    notApplicable (0),
    unmute        (1),
    mute          (2)
   }

QamRfDiagSuppressModeTYPE ::= INTEGER
   {
    none              (0),
    oneChannel        (1),
    allChannelsButOne (2),
    allChannels       (3)
   }

QamChannelTestModeTYPE ::= INTEGER
   {
    noTest     (0),
    suppress   (1),
    cwtest     (2),
    prbs23m    (3),
    prbsUnique (4),
    mpegNull   (5),
    biPhase    (6)
   }

ErrorTYPE ::= INTEGER
   {
    noError (0),
    error   (1)
   }

LowHighErrorTYPE ::= INTEGER
   {
    noError (0),
    low     (1),
    high    (2)
   }

QamRfInterleaverDepthAnnexBTYPE ::= INTEGER
   {
    notApplicable (0),
    i64-j2        (1),
    i32-j4        (2),
    i16-j8        (3),
    i8-j16        (4),
    i128-j1       (5),
    i128-j2       (6),
    i128-j3       (7),
    i128-j4       (8),
    i128-j5       (9),
    i128-j6       (10),
    i128-j7       (11),
    i128-j8       (12)
   }

EnableDisableAllTYPE ::= INTEGER
   {
    notInProgress          (0),
    enableBlade1Routes     (1),
    enableBlade2Routes     (2),
    enableBlade3Routes     (3),
    enableBlade4Routes     (4),
    enableBlade5Routes     (5),
    enableBlade6Routes     (6),
    enableBlade7Routes     (7),
    enableBlade8Routes     (8),
    enableAllBladeRoutes   (9),
    disableBlade1Routes    (10),
    disableBlade2Routes    (11),
    disableBlade3Routes    (12),
    disableBlade4Routes    (13),
    disableBlade5Routes    (14),
    disableBlade6Routes    (15),
    disableBlade7Routes    (16),
    disableBlade8Routes    (17),
    disableAllBladeRoutes  (18)
   }

MasterRfPortTYPE ::= INTEGER
   {
    none  (0),
    port1 (1),
    port2 (2),
    port3 (3)
   }

--
-- APEX MIB STRUCTURE
--
-- The following duplicates the structure and entries in the APEX MIB.
-- Object identifiers for groups are defined here.
--
   apexSys                                                OBJECT IDENTIFIER ::= {apex3000 1}
      apexSysConfig                                       OBJECT IDENTIFIER ::= {apexSys 1}
         apexSysConfigGeneral                             OBJECT IDENTIFIER ::= {apexSysConfig 1}
--          apexSaveConfig                                                      {apexSysConfigGeneral 1}
--          apexProductName                                                     {apexSysConfigGeneral 2}
--          apexBootMethod                                                      {apexSysConfigGeneral 3}
         apexSysConfigMcEmmInsertion                      OBJECT IDENTIFIER ::= {apexSysConfig 2}
--          apexMcEmmInsertionMode                                              {apexSysConfigMcEmmInsertion 1}
--          apexMcEmmInsertionPid1Enable                                        {apexSysConfigMcEmmInsertion 2}
--          apexMcEmmInsertionPid1                                              {apexSysConfigMcEmmInsertion 3}
--          apexMcEmmInsertionPid2Enable                                        {apexSysConfigMcEmmInsertion 4}
--          apexMcEmmInsertionPid2                                              {apexSysConfigMcEmmInsertion 5}
--          apexMcEmmInsertionApplyChange                                       {apexSysConfigMcEmmInsertion 6}
      apexSysStatus                                       OBJECT IDENTIFIER ::= {apexSys 2}
         apexSysStatusGeneral                             OBJECT IDENTIFIER ::= {apexSysStatus 1}
--          apexBootReason                                                      {apexSysStatusGeneral 1}
--          apexMaxServiceMappings                                              {apexSysStatsgGeneral 2}
         apexSysStatusVersions                            OBJECT IDENTIFIER ::= {apexSysStatus 2}
--          apexProductType                                                     {apexSysStatusVersions 1}
         apexSysStatusModules                             OBJECT IDENTIFIER ::= {apexSysStatus 3}
            apexSysStatFrontPanelModule                   OBJECT IDENTIFIER ::= {apexSysStatusModules 1}
--             apexSysStatFrontPanelModulePresent                               {apexSysStatFrontPanelModule 1}
--             apexSysStatFrontPanelModuleType                                  {apexSysStatFrontPanelModule 2}
--             apexSysStatFrontPanelModuleAvailable                             {apexSysStatFrontPanelModule 3}
--             apexSysStatFrontPanelModuleSerialNumber                          {apexSysStatFrontPanelModule 4}
--             apexSysStatFrontPanelModuleHardwareVersion                       {apexSysStatFrontPanelModule 5}
--             apexSysStatFrontPanelModuleMicroCtrlVersion                      {apexSysStatFrontPanelModule 6}
--             apexSysStatFrontPanelModuleGoodStatusPollCounts                  {apexSysStatFrontPanelModule 7}
--             apexSysStatFrontPanelModuleBadStatusPollCounts                   {apexSysStatFrontPanelModule 8}
            apexSysStatDtiModule                          OBJECT IDENTIFIER ::= {apexSysStatusModules 2}
--             apexSysStatDtiModulePresent                                      {apexSysStatDtiModule 1}
--             apexSysStatDtiModuleType                                         {apexSysStatDtiModule 2}
--             apexSysStatDtiModuleAvailable                                    {apexSysStatDtiModule 3}
--             apexSysStatDtiModuleSerialNumber                                 {apexSysStatDtiModule 4}
--             apexSysStatDtiModuleHardwareVersion                              {apexSysStatDtiModule 5}
--             apexSysStatDtiModuleMicroCtrlVersion                             {apexSysStatDtiModule 6}
--             apexSysStatDtiModuleGoodStatusPollCounts                         {apexSysStatDtiModule 7}
--             apexSysStatDtiModuleBadStatusPollCounts                          {apexSysStatDtiModule 8}
--             apexSysStatDtiModuleFpgaVersion                                  {apexSysStatDtiModule 9}
--          apexSysStatHostModuleTable                                          {apexSysStatusModules 3}
--             apexSysStatHostModuleEntry                                       {apexSysStatHostModuleTable 1}
--                apexSysStatHostModuleNum                                      {apexSysStatHostModuleEntry 1}
--                apexSysStatHostModulePresent                                  {apexSysStatHostModuleEntry 2}
--                apexSysStatHostModuleType                                     {apexSysStatHostModuleEntry 3}
--                apexSysStatHostModuleAvailable                                {apexSysStatHostModuleEntry 4}
--                apexSysStatHostModuleSerialNumber                             {apexSysStatHostModuleEntry 5}
--                apexSysStatHostModuleHardwareVersion                          {apexSysStatHostModuleEntry 6}
--                apexSysStatHostModuleMicroCtrlVersion                         {apexSysStatHostModuleEntry 7}
--                apexSysStatHostModuleBootCodeVersion                          {apexSysStatHostModuleEntry 8}
--                apexSysStatHostModuleApplicationDate                          {apexSysStatHostModuleEntry 9}
--                apexSysStatHostModuleGlueFpgaVersion                          {apexSysStatHostModuleEntry 10}
--                apexSysStatHostModuleAppVersion                               {apexSysStatHostModuleEntry 11}
--                apexSysStatHostModuleAmpAppDate                               {apexSysStatHostModuleEntry 12}
--                apexSysStatHostModuleAmpAppVersion                            {apexSysStatHostModuleEntry 13}
--                apexSysStatHostModuleGoodStatusPollCounts                     {apexSysStatHostModuleEntry 14}
--                apexSysStatHostModuleBadStatusPollCounts                      {apexSysStatHostModuleEntry 15}
--          apexSysStat10GbeModuleTable                                         {apexSysStatusModules 4}
--             apexSysStat10GbeModuleEntry                                      {apexSysStat10GbeModuleTable 1}
--                apexSysStat10GbeModuleNum                                     {apexSysStat10GbeModuleEntry 1}
--                apexSysStat10GbeModulePresent                                 {apexSysStat10GbeModuleEntry 2}
--                apexSysStat10GbeModuleType                                    {apexSysStat10GbeModuleEntry 3}
--                apexSysStat10GbeModuleAvailable                               {apexSysStat10GbeModuleEntry 4}
--                apexSysStat10GbeModuleSerialNumber                            {apexSysStat10GbeModuleEntry 5}
--                apexSysStat10GbeModuleHardwareVersion                         {apexSysStat10GbeModuleEntry 6}
--                apexSysStat10GbeModuleMicroCtrlVersion                        {apexSysStat10GbeModuleEntry 7}
--                apexSysStat10GbeModuleGoodStatusPollCounts                    {apexSysStat10GbeModuleEntry 8}
--                apexSysStat10GbeModuleBadStatusPollCounts                     {apexSysStat10GbeModuleEntry 9}
--          apexSysStatQamBladeTable                                            {apexSysStatusModules 5}
--             apexSysStatQamBladeEntry                                         {apexSysStatQamBladeTable 1}
--                apexSysStatQamBladeNum                                        {apexSysStatQamBladeEntry 1}
--                apexSysStatQamBladePresent                                    {apexSysStatQamBladeEntry 2}
--                apexSysStatQamBladeType                                       {apexSysStatQamBladeEntry 3}
--                apexSysStatQamBladeAvailable                                  {apexSysStatQamBladeEntry 4}
--                apexSysStatQamBladeSerialNumber                               {apexSysStatQamBladeEntry 5}
--                apexSysStatQamBladeHardwareVersion                            {apexSysStatQamBladeEntry 6}
--                apexSysStatQamBladeMicroCtrlVersion                           {apexSysStatQamBladeEntry 7}
--                apexSysStatQamBladeNpuBootCodeVersion                         {apexSysStatQamBladeEntry 8}
--                apexSysStatQamBladeNpuApplicationVersion                      {apexSysStatQamBladeEntry 9}
--                apexSysStatQamBladeMuxFpgaVersion                             {apexSysStatQamBladeEntry 10}
--                apexSysStatQamBladeIngressFpgaVersion                         {apexSysStatQamBladeEntry 11}
--                apexSysStatQamBladeLatched                                    {apexSysStatQamBladeEntry 12}
--                apexSysStatQamBladeClockSource                                {apexSysStatQamBladeEntry 13}
--                apexSysStatQamBladeGoodStatusPollCounts                       {apexSysStatQamBladeEntry 14}
--                apexSysStatQamBladeBadStatusPollCounts                        {apexSysStatQamBladeEntry 15}
--          apexSysStatRfModuleTable                                            {apexSysStatusModules 6}
--             apexSysStatRfModuleEntry                                         {apexSysStatRfModuleTable 1}
--                apexSysStatRfModuleNum                                        {apexSysStatRfModuleEntry 1}
--                apexSysStatRfModulePresent                                    {apexSysStatRfModuleEntry 2}
--                apexSysStatRfModuleType                                       {apexSysStatRfModuleEntry 3}
--                apexSysStatRfModuleSerialNumber                               {apexSysStatRfModuleEntry 4}
--                apexSysStatRfModuleHardwareVersion                            {apexSysStatRfModuleEntry 5}
--                apexSysStatRfModuleFwBootCodeVersion                          {apexSysStatRfModuleEntry 6}
--                apexSysStatRfModuleFwApplicationVersion                       {apexSysStatRfModuleEntry 7}
--                apexSysStatRfModuleFwAppBuildNumber                           {apexSysStatRfModuleEntry 8}
--                apexSysStatRfModuleFpgaVersion                                {apexSysStatRfModuleEntry 9}
--                apexSysStatRfModuleCodeFileVersion                            {apexSysStatRfModuleEntry 10}
--                apexSysStatRfModuleCalibrationVersion                         {apexSysStatRfModuleEntry 11}
--                apexSysStatRfModuleTestVersion                                {apexSysStatRfModuleEntry 12}
--          apexSysStatRfSwitchModuleTable                                      {apexSysStatusModules 7}
--             apexSysStatRfSwitchModuleEntry                                   {apexSysStatRfSwitchModuleTable 1}
--                apexSysStatRfSwitchModuleNum                                  {apexSysStatRfSwitchModuleEntry 1}
--                apexSysStatRfSwitchModulePresent                              {apexSysStatRfSwitchModuleEntry 2}
--                apexSysStatRfSwitchModuleType                                 {apexSysStatRfSwitchModuleEntry 3}
--                apexSysStatRfSwitchModuleAvailable                            {apexSysStatRfSwitchModuleEntry 4}
--                apexSysStatRfSwitchModuleSerialNumber                         {apexSysStatRfSwitchModuleEntry 4}
--                apexSysStatRfSwitchModuleHardwareVersion                      {apexSysStatRfSwitchModuleEntry 5}
--                apexSysStatRfSwitchModuleMicroCtrlVersion                     {apexSysStatRfSwitchModuleEntry 6}
--                apexSysStatRfSwitchModuleGoodStatusPollCounts                 {apexSysStatRfSwitchModuleEntry 7}
--                apexSysStatRfSwitchModuleBadStatusPollCounts                  {apexSysStatRfSwitchModuleEntry 8}
--          apexSysStatFanFillerModuleTable                                     {apexSysStatusModules 8}
--             apexSysStatFanFillerModuleEntry                                  {apexSysStatFanFillerModuleTable 1}
--                apexSysStatFanFillerModuleNum                                 {apexSysStatFanFillerModuleEntry 1}
--                apexSysStatFanFillerModulePresent                             {apexSysStatFanFillerModuleEntry 2}
--                apexSysStatFanFillerModuleType                                {apexSysStatFanFillerModuleEntry 3}
--                apexSysStatFanFillerModuleAvailable                           {apexSysStatFanFillerModuleEntry 4}
--                apexSysStatFanFillerModuleSerialNumber                        {apexSysStatFanFillerModuleEntry 5}
--                apexSysStatFanFillerModuleHardwareVersion                     {apexSysStatFanFillerModuleEntry 6}
--                apexSysStatFanFillerModuleMicroCtrlVersion                    {apexSysStatFanFillerModuleEntry 7}
--                apexSysStatFanFillerModuleGoodStatusPollCounts                {apexSysStatFanFillerModuleEntry 8}
--                apexSysStatFanFillerModuleBadStatusPollCounts                 {apexSysStatFanFillerModuleEntry 9}
--          apexSysStatPowerSupplyModuleTable                                   {apexSysStatusModules 9}
--             apexSysStatPowerSupplyModuleEntry                                {apexSysStatPowerSupplyModuleTable 1}
--                apexSysStatPowerSupplyModuleNum                               {apexSysStatPowerSupplyModuleEntry 1}
--                apexSysStatPowerSupplyModulePresent                           {apexSysStatPowerSupplyModuleEntry 2}
--                apexSysStatPowerSupplyModuleType                              {apexSysStatPowerSupplyModuleEntry 3}
--                apexSysStatPowerSupplyModuleAvailable                         {apexSysStatPowerSupplyModuleEntry 4}
--                apexSysStatPowerSupplyModuleSerialNumber                      {apexSysStatPowerSupplyModuleEntry 5}
            apexSysStatPowerTransitionModule              OBJECT IDENTIFIER ::= {apexSysStatusModules 10}
--             apexSysStatPowerTransitionModulePresent                          {apexSysStatPowerTransitionModule 1}
--             apexSysStatPowerTransitionModuleType                             {apexSysStatPowerTransitionModule 2}
--             apexSysStatPowerTransitionModuleAvailable                        {apexSysStatPowerTransitionModule 3}
--             apexSysStatPowerTransitionModuleSerialNumber                     {apexSysStatPowerTransitionModule 4}
--             apexSysStatPowerTransitionModuleHardwareVersion                  {apexSysStatPowerTransitionModule 5}
--          apexSysStatBladeSlotTable                                           {apexSysStatusModules 11}
--             apexSysStatBladeSlotEntry                                        {apexSysStatBladeSlotTable 1}
--                apexSysStatBladeSlotNum                                       {apexSysStatBladeSlotEntry 1}
--                apexSysStatBladeSlotModuleType                                {apexSysStatBladeSlotEntry 2}
   apexTime                                               OBJECT IDENTIFIER ::= {apex3000 2}
      apexTimeConfig                                      OBJECT IDENTIFIER ::= {apexTime 1}
         apexTimeConfigGeneral                            OBJECT IDENTIFIER ::= {apexTimeConfig 1}
--          apexTimeSource                                                      {apexTimeConfigGeneral 1}
--          apexSntpUtcOffset                                                   {apexTimeConfigGeneral 2}
--          apexSntpServerSpecified                                             {apexTimeConfigGeneral 3}
--          apexSntpServerIpAddr                                                {apexTimeConfigGeneral 4}
--          apexUserSuppliedTime                                                {apexTimeConfigGeneral 5}
      apexTimeStatus                                      OBJECT IDENTIFIER ::= {apexTime 2}
         apexTimeStatusGeneral                            OBJECT IDENTIFIER ::= {apexTimeStatus 1}
--          apexSystemTime                                                      {apexTimeStatusGeneral 1}
--          apexOperationalTime                                                 {apexTimeStatusGeneral 2}
   apexTemperature                                        OBJECT IDENTIFIER ::= {apex3000 3}
      apexTemperatureConfig                               OBJECT IDENTIFIER ::= {apexTemperature 1}
         apexTemperatureConfigGeneral                     OBJECT IDENTIFIER ::= {apexTemperatureConfig 1}
      apexTemperatureStatus                               OBJECT IDENTIFIER ::= {apexTemperature 2}
         apexTemperatureStatusGeneral                     OBJECT IDENTIFIER ::= {apexTemperatureStatus 1}
         apexModuleTemperatures                           OBJECT IDENTIFIER ::= {apexTemperatureStatus 2}
            apexTempsFrontPanel                           OBJECT IDENTIFIER ::= {apexModuleTemperatures 1}
--             apexTempsFrontPanelFaultCondition                                {apexTempsFrontPanel 1}
--             apexTempsFrontPanelMicroCtrl                                     {apexTempsFrontPanel 2}
            apexTempsDti                                  OBJECT IDENTIFIER ::= {apexModuleTemperatures 2}
--             apexTempsDtiFaultCondition                                       {apexTempsDti 1}
--             apexTempsDtiMicroCtrl                                            {apexTempsDti 2}
            apexTempsHost                                 OBJECT IDENTIFIER ::= {apexModuleTemperatures 3}
               apexTempsHostGeneral                       OBJECT IDENTIFIER ::= {apexTempsHost 1}
--             apexTempsHostTable                                               {apexTempsHost 2}
--                apexTempsHostEntry                                            {apexTempsHostTable 1}
--                   apexTempsHostModuleNum                                     {apexTempsHostEntry 1}
--                   apexTempsHostFaultCondition                                {apexTempsHostEntry 2}
--                   apexTempsHostMicroCtrl                                     {apexTempsHostEntry 3}
--                   apexTempsHostSensor1                                       {apexTempsHostEntry 4}
--                   apexTempsHostSensor2                                       {apexTempsHostEntry 5}
--                   apexTempsHostSensor3                                       {apexTempsHostEntry 6}
--                   apexTempsHostSensor4                                       {apexTempsHostEntry 7}
--                   apexTempsHostSensor5                                       {apexTempsHostEntry 8}
            apexTemps10Gbe                                OBJECT IDENTIFIER ::= {apexModuleTemperatures 4}
               apexTemps10GbeGeneral                      OBJECT IDENTIFIER ::= {apexTemps10Gbe 1}
--             apexTemps10GbeTable                                              {apexTemps10Gbe 2}
--                apexTemps10GbeEntry                                           {apexTemps10GbeTable 1}
--                   apexTemps10GbeModuleNum                                    {apexTemps10GbeEntry 1}
--                   apexTemps10GbeFaultCondition                               {apexTemps10GbeEntry 2}
--                   apexTemps10GbeMicroCtrl                                    {apexTemps10GbeEntry 3}
            apexTempsQamBlade                             OBJECT IDENTIFIER ::= {apexModuleTemperatures 5}
               apexTempsQamBladeGeneral                   OBJECT IDENTIFIER ::= {apexTempsQamBlade 1}
--             apexTempsQamBladeTable                                           {apexTempsQamBlade 2}
--                apexTempsQamBladeEntry                                        {apexTempsQamBladeTable 1}
--                   apexTempsQamBladeNum                                       {apexTempsQamBladeEntry 1}
--                   apexTempsQamBladeFaultCondition                            {apexTempsQamBladeEntry 2}
--                   apexTempsQamBladeMicroCtrl                                 {apexTempsQamBladeEntry 3}
--                   apexTempsQamBladeSensor1                                   {apexTempsQamBladeEntry 4}
--                   apexTempsQamBladeSensor2                                   {apexTempsQamBladeEntry 5}
--                   apexTempsQamBladeSensor3                                   {apexTempsQamBladeEntry 6}
--                   apexTempsQamBladeSensor4                                   {apexTempsQamBladeEntry 7}
--                   apexTempsQamBladeSensor5                                   {apexTempsQamBladeEntry 8}
--                   apexTempsQamBladeSensor6                                   {apexTempsQamBladeEntry 9}
            apexTempsRfModule                             OBJECT IDENTIFIER ::= {apexModuleTemperatures 6}
               apexTempsRfModuleGeneral                   OBJECT IDENTIFIER ::= {apexTempsRfModule 1}
--             apexTempsRfModuleTable                                           {apexTempsRfModule 2}
--                apexTempsRfModuleEntry                                        {apexTempsRfModuleTable 1}
--                   apexTempsRfModuleNum                                       {apexTempsRfModuleEntry 1}
--                   apexTempsRfModuleFpga                                      {apexTempsRfModuleEntry 2}
--                   apexTempsRfModuleRfHigh                                    {apexTempsRfModuleEntry 3}
            apexTempsRfSwitch                             OBJECT IDENTIFIER ::= {apexModuleTemperatures 7}
               apexTempsRfSwitchGeneral                   OBJECT IDENTIFIER ::= {apexTempsRfSwitch 1}
--             apexTempsRfSwitchTable                                           {apexTempsRfSwitch 2}
--                apexTempsRfSwitchEntry                                        {apexTempsRfSwitchTable 1}
--                   apexTempsRfSwitchModuleNum                                 {apexTempsRfSwitchEntry 1}
--                   apexTempsRfSwitchFaultCondition                            {apexTempsRfSwitchEntry 2}
--                   apexTempsRfSwitchMicroCtrl                                 {apexTempsRfSwitchEntry 3}
--                   apexTempsRfSwitchSensor1                                   {apexTempsRfSwitchEntry 4}
            apexTempsFanFiller                            OBJECT IDENTIFIER ::= {apexModuleTemperatures 8}
               apexTempsFanFillerGeneral                  OBJECT IDENTIFIER ::= {apexTempsFanFiller 1}
--             apexTempsFanFillerTable                                          {apexTempsFanFiller 2}
--                apexTempsFanFillerEntry                                       {apexTempsFanFillerTable 1}
--                   apexTempsFanFillerModuleNum                                {apexTempsFanFillerEntry 1}
--                   apexTempsFanFillerFaultCondition                           {apexTempsFanFillerEntry 2}
--                   apexTempsFanFillerMicroCtrl                                {apexTempsFanFillerEntry 3}
--                   apexTempsFanFillerSensor1                                  {apexTempsFanFillerEntry 4}
--                   apexTempsFanFillerSensor2                                  {apexTempsFanFillerEntry 5}
--                   apexTempsFanFillerSensor3                                  {apexTempsFanFillerEntry 6}
   apexPowerSupply                                        OBJECT IDENTIFIER ::= {apex3000 4}
      apexPsConfig                                        OBJECT IDENTIFIER ::= {apexPowerSupply 1}
         apexPsConfigGeneral                              OBJECT IDENTIFIER ::= {apexPsConfig 1}
      apexPsStatus                                        OBJECT IDENTIFIER ::= {apexPowerSupply 2}
         apexPsStatusGeneral                              OBJECT IDENTIFIER ::= {apexPsStatus 1}
--       apexPsStatusTable                                                      {apexPsStatus 2}
--          apexPsStatusEntry                                                   {apexPsStatusTable 1}
--             apexPsStatusPsNum                                                {apexPsStatusEntry 1}
--             apexPsStatusInstalled                                            {apexPsStatusEntry 2}
--             apexPsStatusFirmwareVersion                                      {apexPsStatusEntry 3}
--             apexPsStatusVoltageOut                                           {apexPsStatusEntry 4}
--             apexPsStatusCurrentOut                                           {apexPsStatusEntry 5}
--             apexPsStatusVoltageInput                                         {apexPsStatusEntry 6}
--             apexPsStatusCurrentInput                                         {apexPsStatusEntry 7}
--             apexPsStatusPowerInput                                           {apexPsStatusEntry 8}
--             apexPsStatusTemperature                                          {apexPsStatusEntry 9}
--             apexPsStatusFanSpeed                                             {apexPsStatusEntry 10}
--             apexPsStatusFan1Speed                                            {apexPsStatusEntry 11}
--             apexPsStatusFan2Speed                                            {apexPsStatusEntry 12}
--             apexPsStatusCurrentOutControl                                    {apexPsStatusEntry 13}
--             apexPsStatusVoltOutControl                                       {apexPsStatusEntry 14}
--             apexPsStatusFanControl                                           {apexPsStatusEntry 15}
--             apexPsStatusFaultCondition                                       {apexPsStatusEntry 16}
--             apexPsStatusCurrentOutFault                                      {apexPsStatusEntry 17}
--             apexPsStatusVoltOutFault                                         {apexPsStatusEntry 18}
--             apexPsStatusVoltInputFault                                       {apexPsStatusEntry 19}
--             apexPsStatusTempFault                                            {apexPsStatusEntry 20}
--             apexPsStatusFanFault                                             {apexPsStatusEntry 21}
--             apexPsStatusMfrSpecFault                                         {apexPsStatusEntry 22}
   apexAsi                                                OBJECT IDENTIFIER ::= {apex3000 5}
      apexAsiConfig                                       OBJECT IDENTIFIER ::= {apexAsi 1}
         apexAsiConfigGeneral                             OBJECT IDENTIFIER ::= {apexAsiConfig 1}
--       apexAsiMonitorPortConfigTable                                          {apexAsiConfig 2}
--          apexAsiMonitorPortConfigEntry                                       {apexAsiMonitorPortConfigTable 1}
--             apexAsiMonitorPortBladeNum                                       {apexAsiMonitorPortConfigEntry 1}
--             apexAsiMonitorPortOutputTsNum                                    {apexAsiMonitorPortConfigEntry 2}
--             apexAsiMonitorPortEncryption                                     {apexAsiMonitorPortConfigEntry 3}
   apexFastEnet                                           OBJECT IDENTIFIER ::= {apex3000 6}
      apexFastEnetConfig                                  OBJECT IDENTIFIER ::= {apexFastEnet 1}
         apexFastEnetConfigGeneral                        OBJECT IDENTIFIER ::= {apexFastEnetConfig 1}
--          apexFastEnetDefaultGateway                                          {apexFastEnetConfigGeneral 1}
--          apexFastEnetRoutingApplyChange                                      {apexFastEnetConfigGeneral 2}
--          apexFastEnetIpConfigApplyChange                                     {apexFastEnetConfigGeneral 3}
--          apexGenericQamDeviceApplyChange                                     {apexFastEnetConfigGeneral 4}
--       apexFastEnetRoutingTable                                               {apexFastEnetConfig 2}
--          apexFastEnetRoutingEntry                                            {apexFastEnetRoutingTable 1}
--             apexFastEnetRoutingIndex                                         {apexFastEnetRoutingEntry 1}
--             apexFastEnetRoutingDestinIp                                      {apexFastEnetRoutingEntry 2}
--             apexFastEnetRoutingGatewayIp                                     {apexFastEnetRoutingEntry 3}
--             apexFastEnetRoutingSubnetMask                                    {apexFastEnetRoutingEntry 4}
--       apexGenericQamDeviceTable                                              {apexFastEnetConfig 3}
--          apexGenericQamDeviceEntry                                           {apexGenericQamDeviceTable 1}
--             apexGenericQamDeviceIndex                                        {apexGenericQamDeviceEntry 1}
--             apexGenericQamDeviceEnetInterface                                {apexGenericQamDeviceEntry 2}
--             apexGenericQamDeviceIpAddr                                       {apexGenericQamDeviceEntry 3}
--             apexGenericQamDeviceSubnetMask                                   {apexGenericQamDeviceEntry 4}
      apexFastEnetStatus                                  OBJECT IDENTIFIER ::= {apexFastEnet 2}
         apexFastEnetStatusGeneral                        OBJECT IDENTIFIER ::= {apexFastEnetStatus 1}
--          apexFastEnetIpConfigApplyText                                       {apexFastEnetStatusGeneral 1}
--          apexGenericQamDeviceApplyText                                       {apexFastEnetStatusGeneral 2}
--       apexGqdStatTable                                                       {apexFastEnetStatus 2}
--          apexGqdStatEntry                                                    {apexGqdStatTable 1}
--             apexGqdStatDeviceIndex                                           {apexGqdStatEntry 1}
--             apexGqdStatNumSdvSessions                                        {apexGqdStatEntry 2}
--             apexGqdStatNumOutputTs                                           {apexGqdStatEntry 3}
      apexOamp                                            OBJECT IDENTIFIER ::= {apexFastEnet 3}
         apexOampConfig                                   OBJECT IDENTIFIER ::= {apexOamp 1}
            apexOampConfigGeneral                         OBJECT IDENTIFIER ::= {apexOampConfig 1}
--             apexOampIpAddr                                                   {apexOampConfigGeneral 1}
--             apexOampSubnetMask                                               {apexOampConfigGeneral 2}
--             apexOampAutoNegotiate                                            {apexOampConfigGeneral 3}
         apexOampStatus                                   OBJECT IDENTIFIER ::= {apexOamp 2}
            apexOampStatusGeneral                         OBJECT IDENTIFIER ::= {apexOampStatus 1}
--          apexOampStatusTable                                                 {apexOampStatus 2}
--             apexOampStatusEntry                                              {apexOampStatusTable 2}
--                apexOampHostModuleNum                                         {apexOampStatusEntry 1}
--                apexOampMacAddr                                               {apexOampStatusEntry 2}
--                apexOampSpeed                                                 {apexOampStatusEntry 3}
--                apexOampDuplexMode                                            {apexOampStatusEntry 4}
--                apexOampLinkActive                                            {apexOampStatusEntry 5}
--                apexOampBootIpAddr                                            {apexOampStatusEntry 6}
--                apexOampBootSubnetMask                                        {apexOampStatusEntry 7}
--                apexOampBootDefaultGateway                                    {apexOampStatusEntry 8}
      apexDataIp                                          OBJECT IDENTIFIER ::= {apexFastEnet 4}
         apexDataIpConfig                                 OBJECT IDENTIFIER ::= {apexDataIp 1}
            apexDataIpConfigGeneral                       OBJECT IDENTIFIER ::= {apexDataIpConfig 1}
--             apexDataIpAddr                                                   {apexDataIpConfigGeneral 1}
--             apexDataIpSubnetMask                                             {apexDataIpConfigGeneral 2}
--             apexDataIpAutoNegotiate                                          {apexDataIpConfigGeneral 3}
         apexDataIpStatus                                 OBJECT IDENTIFIER ::= {apexDataIp 2}
            apexDataIpStatusGeneral                       OBJECT IDENTIFIER ::= {apexDataIpStatus 1}
--          apexDataIpStatusTable                                               {apexDataIpStatus 2}
--             apexDataIpStatusEntry                                            {apexDataIpStatusTable 2}
--                apexDataIpHostModuleNum                                       {apexDataIpStatusEntry 1}
--                apexDataIpMacAddr                                             {apexDataIpStatusEntry 2}
--                apexDataIpSpeed                                               {apexDataIpStatusEntry 3}
--                apexDataIpDuplexMode                                          {apexDataIpStatusEntry 4}
--                apexDataIpLinkActive                                          {apexDataIpStatusEntry 5}
   apexGbe                                                OBJECT IDENTIFIER ::= {apex3000 7}
      apexGbeConfig                                       OBJECT IDENTIFIER ::= {apexGbe 1}
         apexGbeConfigGeneral                             OBJECT IDENTIFIER ::= {apexGbeConfig 1}
--          apexGbeDefaultGateway                                               {apexGbeConfigGeneral 1}
--          apexGbeGarpPeriodicity                                              {apexGbeConfigGeneral 2}
--          apexGbeConfigTableApplyChange                                       {apexGbeConfigGeneral 3}
--          apexGbeNominalBufferLevel                                           {apexGbeConfigGeneral 4}
--          apexGbeConfInputUnicastTimeout                                      {apexGbeConfigGeneral 5}
--          apexGbeConfInputMulticastTimeout                                    {apexGbeConfigGeneral 6}
--          apexGbeConfLossOfInputTsType                                        {apexGbeConfigGeneral 7}
--          apexGbeConfFrameCounterTableResetAll                                {apexGbeConfigGeneral 8}
--          apexGbeConfFrameBufferAlarmThreshold                                {apexGbeConfigGeneral 9}
--       apexGbeConfigTable                                                     {apexGbeConfig 2}
--          apexGbeConfigEntry                                                  {apexGbeConfigTable 1}
--             apexGbeConfigInterfaceNum                                        {apexGbeConfigEntry 1}
--             apexGbeConfigOperatingMode                                       {apexGbeConfigEntry 2}
--             apexGbeConfigIpAddr                                              {apexGbeConfigEntry 3}
--             apexGbeConfigIpSubnetMask                                        {apexGbeConfigEntry 4}
--             apexGbeConfigAutoNegotiate                                       {apexGbeConfigEntry 5}
--             apexGbeConfigBackupInterface                                     {apexGbeConfigEntry 6}
--             apexGbeConfigSuspendFailover                                     {apexGbeConfigEntry 7}
--             apexGbeConfigAutoSwitchBackEnable                                {apexGbeConfigEntry 8}
--             apexGbeConfigMirrorGbe                                           {apexGbeConfigEntry 9}
--             apexGbeConfigMirrorQamBlade                                      {apexGbeConfigEntry 10}
--             apexGbeConfigFailoverMacAddress                                  {apexGbeConfigEntry 11}
--       apexGbeFrameCounterResetTable                                          {apexGbeConfig 3}
--          apexGbeFrameCounterResetEntry                                       {apexGbeFrameCounterResetTable 1}
--             apexGbeFrameCounterResetGbeIfNum                                 {apexGbeFrameCounterResetEntry 1}
--             apexGbeFrameCounterReset                                         {apexGbeFrameCounterResetEntry 2}
         apexGbeConfigInterfaceRedundancy                 OBJECT IDENTIFIER ::= {apexGbeConfig 4}
            apexGbeConfigInterfaceRedundancyGeneral       OBJECT IDENTIFIER ::= {apexGbeConfigInterfaceRedundancy 1}
--             apexGbeConfIfRedundAutoSwitchBackPeriod                          {apexGbeConfigInterfaceRedundancyGeneral 1}
--          apexGbeConfigInterfaceRedundancyForceTable                          {apexGbeConfigInterfaceRedundancy 2}
--             apexGbeConfigInterfaceRedundancyForceEntry                       {apexGbeConfigInterfaceRedundancyForceTable 1}
--                apexGbeConfIfRedundForceIndex                                 {apexGbeConfigInterfaceRedundancyForceEntry 1}
--                apexGbeConfIfRedundForceFailover                              {apexGbeConfigInterfaceRedundancyForceEntry 2}
      apexGbeStatus                                       OBJECT IDENTIFIER ::= {apexGbe 2}
         apexGbeStatusGeneral                             OBJECT IDENTIFIER ::= {apexGbeStatus 1}
--          apexGbeMaxInputTs                                                   {apexGbeStatusGeneral 1}
--          apexGbeTotalInputTsCount                                            {apexGbeStatusGeneral 2}
--          apexGbeTotalSecInputTsCount                                         {apexGbeStatusGeneral 3}
--          apexGbeMulticastInputTsCount                                        {apexGbeStatusGeneral 4}
--          apexGbeSinglecastInputTsCount                                       {apexGbeStatusGeneral 5}
--          apexGbeRoutedPacketUpdateInterval                                   {apexGbeStatusGeneral 6}
--       apexGbeStatusTable                                                     {apexGbeStatus 2}
--          apexGbeStatusEntry                                                  {apexGbeStatusTable 1}
--             apexGbeStatusGbeInterfaceNum                                     {apexGbeStatusEntry 1}
--             apexGbeStatusMacAddr                                             {apexGbeStatusEntry 2}
--             apexGbeStatusLinkActive                                          {apexGbeStatusEntry 3}
--             apexGbeStatusIgmpVersion                                         {apexGbeStatusEntry 4}
--             apexGbeStatusLossOfPhysicalInput                                 {apexGbeStatusEntry 5}
--             apexGbeStatusRedundState                                         {apexGbeStatusEntry 6}
--             apexGbeStatusRedundFailedInterface                               {apexGbeStatusEntry 7}
--             apexGbeStatusRedundFailoverStatus                                {apexGbeStatusEntry 8}
--             apexGbeStatusInvalidApplyText                                    {apexGbeStatusEntry 9}
--             apexGbeStatusSpeed                                               {apexGbeStatusEntry 10}
--       apexGbeInputTsAssignedTable                                            {apexGbeStatus 3}
--          apexGbeInputTsAssignedEntry                                         {apexGbeInputTsAssignedTable 1}
--             apexGbeInputTsAssignedGbeInterfaceNum                            {apexGbeInputTsAssignedEntry 1}
--             apexGbeInputTsAssignedCount                                      {apexGbeInputTsAssignedEntry 2}
--             apexGbeSecInputTsAssignedCount                                   {apexGbeInputTsAssignedEntry 3}
--             apexGbeInputTsInUseCount                                         {apexGbeInputTsAssignedEntry 4}
--             apexGbeInputTsDepiEngaged                                        {apexGbeInputTsAssignedEntry 5}
--       apexGbeStatusRoutedPacketTable                                         {apexGbeStatus 4}
--          apexGbeStatusRoutedPacketEntry                                      {apexGbeStatusRoutedPacketTable 1}
--             apexGbeStatusRoutedPacketBladeNum                                {apexGbeStatusRoutedPacketEntry 1}
--             apexGbeStatusRoutedPacketOutputTsNum                             {apexGbeStatusRoutedPacketEntry 2}
--             apexGbeStatusTotRoutedPackets                                    {apexGbeStatusRoutedPacketEntry 3}
--             apexGbeStatusNumRoutedPackets                                    {apexGbeStatusRoutedPacketEntry 4}
--       apexGbeStatusQamRoutedPacketTable                                      {apexGbeStatus 5}
--          apexGbeStatusQamRoutedPacketEntry                                   {apexGbeStatusQamRoutedPacketTable 1}
--             apexGbeStatusQamRoutedPacketBladeNum                             {apexGbeStatusQamRoutedPacketEntry 1}
--             apexGbeStatusQamRoutedPacketCurStreamCount                       {apexGbeStatusQamRoutedPacketEntry 2}
--             apexGbeStatusQamRoutedPacketTotStreamCount                       {apexGbeStatusQamRoutedPacketEntry 3}
         apexGbeStatusFrameCounter                        OBJECT IDENTIFIER ::= {apexGbeStatus 6}
            apexGbeStatusFrameCounterGeneral              OBJECT IDENTIFIER ::= {apexGbeStatusFrameCounter 1}
--             apexGbeFrameCounterUpdateInterval                                {apexGbeStatusFrameCounterGeneral 2}
--          apexGbeStatusFrameCounterTable                                      {apexGbeStatusFrameCounter 2}
--             apexGbeStatusFrameCounterEntry                                   {apexGbeStatusFrameCounterTable 1}
--                apexGbeFrameCounterGbeInterfaceNum                            {apexGbeStatusFrameCounterEntry 1}
--                apexGbeTotalRxSinglecastFrames                                {apexGbeStatusFrameCounterEntry 2}
--                apexGbeTotalRxMulticastFrames                                 {apexGbeStatusFrameCounterEntry 3}
--                apexGbeTotalRxBroadcastFrames                                 {apexGbeStatusFrameCounterEntry 4}
--                apexGbeTotalRxErrorFrames                                     {apexGbeStatusFrameCounterEntry 5}
--                apexGbeTotalRxFrames                                          {apexGbeStatusFrameCounterEntry 6}
--                apexGbeRxSinglecastFrames                                     {apexGbeStatusFrameCounterEntry 7}
--                apexGbeRxMulticastFrames                                      {apexGbeStatusFrameCounterEntry 8}
--                apexGbeRxBroadcastFrames                                      {apexGbeStatusFrameCounterEntry 9}
--                apexGbeRxErrorFrames                                          {apexGbeStatusFrameCounterEntry 10}
--                apexGbeRxFrames                                               {apexGbeStatusFrameCounterEntry 11}
--                apexGbeTotalTxGoodFrames                                      {apexGbeStatusFrameCounterEntry 12}
--                apexGbeTotalTxErrorFrames                                     {apexGbeStatusFrameCounterEntry 13}
--                apexGbeTxGoodFrames                                           {apexGbeStatusFrameCounterEntry 14}
--                apexGbeTxErrorFrames                                          {apexGbeStatusFrameCounterEntry 15}
--                apexGbeRxStreamRate                                           {apexGbeStatusFrameCounterEntry 16}
         apexGbeFrameBufferStats                          OBJECT IDENTIFIER ::= {apexGbeStatus 7}
            apexGbeFrameBufferStatsGeneral                OBJECT IDENTIFIER ::= {apexGbeFrameBufferStats 1}
--          apexGbeFrameBufferStatsTable                                        {apexGbeFrameBufferStats 2}
--             apexGbeFrameBufferStatsEntry                                     {apexGbeFrameBufferStatsTable 1}
--                apexGbeFrameBufferBladeNum                                    {apexGbeFrameBufferStatsEntry 1}
--                apexGbeFrameBufferResetLevelLimit                             {apexGbeFrameBufferStatsEntry 2}
--                apexGbeFrameBufferHighMsLevel                                 {apexGbeFrameBufferStatsEntry 3}
--                apexGbeFrameBufferHighPercentFull                             {apexGbeFrameBufferStatsEntry 4}
--                apexGbeFrameBufferLowMsLevel                                  {apexGbeFrameBufferStatsEntry 5}
--                apexGbeFrameBufferLowPercentFull                              {apexGbeFrameBufferStatsEntry 6}
         apexGbeStatusInputTransportStream                OBJECT IDENTIFIER ::= {apexGbeStatus 8}
            apexGbeStatusInputTsGeneral                   OBJECT IDENTIFIER ::= {apexGbeStatusInputTransportStream 1}
--             apexGbeStatusInputTsUpdateInterval                               {apexGbeStatusInputTsGeneral 1}
--          apexGbeStatusInputTsTable                                           {apexGbeStatusInputTransportStream 2}
--             apexGbeStatusInputTsEntry                                        {apexGbeStatusInputTsTable 1}
--                apexGbeStatInTsBladeNum                                       {apexGbeStatusInputTsEntry 1}
--                apexGbeStatInTsInputTsNum                                     {apexGbeStatusInputTsEntry 2}
--                apexGbeStatInTsSamplingPeriod                                 {apexGbeStatusInputTsEntry 3}
--                apexGbeStatInTsCurDataCount                                   {apexGbeStatusInputTsEntry 4}
--                apexGbeStatInTsMinDataCount                                   {apexGbeStatusInputTsEntry 5}
--                apexGbeStatInTsPeakDataCount                                  {apexGbeStatusInputTsEntry 6}
--                apexGbeStatInTsCurStreamCount                                 {apexGbeStatusInputTsEntry 7}
--                apexGbeStatInTsMinStreamCount                                 {apexGbeStatusInputTsEntry 8}
--                apexGbeStatInTsPeakStreamCount                                {apexGbeStatusInputTsEntry 9}
--          apexGbeStatusInputTsErrorTable                                      {apexGbeStatusInputTransportStream 3}
--             apexGbeStatusInputTsErrorEntry                                   {apexGbeStatusInputTsErrorTable 1}
--                apexGbeStatInTsErrorBladeNum                                  {apexGbeStatusInputTsErrorEntry 1}
--                apexGbeStatInTsErrorInputTsNum                                {apexGbeStatusInputTsErrorEntry 2}
--                apexGbeStatInTsPriErrorSummary                                {apexGbeStatusInputTsErrorEntry 3}
--                apexGbeStatInTsPriHighBitRateError                            {apexGbeStatusInputTsErrorEntry 4}
--                apexGbeStatInTsPriFailJoinMulticast                           {apexGbeStatusInputTsErrorEntry 5}
--                apexGbeStatInTsPriLossOfInputStream                           {apexGbeStatusInputTsErrorEntry 6}
--                apexGbeStatInTsRedundFailoverError                            {apexGbeStatusInputTsErrorEntry 7}
--                apexGbeStatInTsSecErrorSummary                                {apexGbeStatusInputTsErrorEntry 8}
--                apexGbeStatInTsSecHighBitRateError                            {apexGbeStatusInputTsErrorEntry 9}
--                apexGbeStatInTsSecFailJoinMulticast                           {apexGbeStatusInputTsErrorEntry 10}
--                apexGbeStatInTsSecLossOfInputStream                           {apexGbeStatusInputTsErrorEntry 11}
--          apexGbeStatusInputTsBufferLevelTable                                {apexGbeStatusInputTransportStream 4}
--             apexGbeStatusInputTsBufferLevelEntry                             {apexGbeStatusInputTsBufferLevelTable 1}
--                apexGbeStatInTsBufferLevelBladeNum                            {apexGbeStatusInputTsBufferLevelEntry 1}
--                apexGbeStatInTsBufferLevelTsNum                               {apexGbeStatusInputTsBufferLevelEntry 2}
--                apexGbeStatInTsBufferLevelInputInfo                           {apexGbeStatusInputTsBufferLevelEntry 3}
--                apexGbeStatInTsBufferLevelPriSecIndicator                     {apexGbeStatusInputTsBufferLevelEntry 4}
--                apexGbeStatInTsBufferLevelCur                                 {apexGbeStatusInputTsBufferLevelEntry 5}
--                apexGbeStatInTsBufferLevelMin                                 {apexGbeStatusInputTsBufferLevelEntry 6}
--                apexGbeStatInTsBufferLevelMax                                 {apexGbeStatusInputTsBufferLevelEntry 7}
--                apexGbeStatInTsBufferLevelResetCount                          {apexGbeStatusInputTsBufferLevelEntry 8}
--          apexGbeStatusInputTsStatTable                                       {apexGbeStatusInputTransportStream 5}
--             apexGbeStatusInputTsStatEntry                                    {apexGbeStatusInputTsStatTable 1}
--                apexGbeStatusInputTsStatBladeNum                              {apexGbeStatusInputTsStatEntry 1}
--                apexGbeStatusInputTsStatTsNum                                 {apexGbeStatusInputTsStatEntry 1}
--                apexGbeStatusInputTsStatStreamInUse                           {apexGbeStatusInputTsStatEntry 2}
--                apexGbeStatusInputTsStatRoutingType                           {apexGbeStatusInputTsStatEntry 3}
--                apexGbeStatusInputTsStatPriState                              {apexGbeStatusInputTsStatEntry 4}
--                apexGbeStatusInputTsStatPriInputInterface                     {apexGbeStatusInputTsStatEntry 5}
--                apexGbeStatusInputTsStatPriInputUdp                           {apexGbeStatusInputTsStatEntry 6}
--                apexGbeStatusInputTsStatPriInputDestinationIp                 {apexGbeStatusInputTsStatEntry 7}
--                apexGbeStatusInputTsStatPriInputSourceIp                      {apexGbeStatusInputTsStatEntry 8}
--                apexGbeStatusInputTsStatSecState                              {apexGbeStatusInputTsStatEntry 9}
--                apexGbeStatusInputTsStatSecInputInterface                     {apexGbeStatusInputTsStatEntry 10}
--                apexGbeStatusInputTsStatSecInputUdp                           {apexGbeStatusInputTsStatEntry 11}
--                apexGbeStatusInputTsStatSecInputDestinationIp                 {apexGbeStatusInputTsStatEntry 12}
--                apexGbeStatusInputTsStatSecInputSourceIp                      {apexGbeStatusInputTsStatEntry 13}
--          apexGbeStatusQamInputStatTable                                      {apexGbeStatusInputTransportStream 6}
--             apexGbeStatusQamInputStatEntry                                   {apexGbeStatusQamInputStatTable 1}
--                apexGbeStatusQamInputStatBladeNum                             {apexGbeStatusQamInputStatEntry 1}
--                apexGbeStatusQamInputStatCurDataCount                         {apexGbeStatusQamInputStatEntry 2}
--                apexGbeStatusQamInputStatCurStreamCount                       {apexGbeStatusQamInputStatEntry 3}
--                apexGbeStatusQamInputStatTotDataCount                         {apexGbeStatusQamInputStatEntry 4}
--                apexGbeStatusQamInputStatTotStreamCount                       {apexGbeStatusQamInputStatEntry 5}
      apexGbeSfp                                          OBJECT IDENTIFIER ::= {apexGbe 3}
         apexGbeSfpConfig                                 OBJECT IDENTIFIER ::= {apexGbeSfp 1}
            apexGbeSfpConfigGeneral                       OBJECT IDENTIFIER ::= {apexGbeSfpConfig 1}
--             apexGbeSfpUpdateStatus                                           {apexGbeSfpConfigGeneral 1}
         apexGbeSfpStatus                                 OBJECT IDENTIFIER ::= {apexGbeSfp 2}
            apexGbeSfpStatusGeneral                       OBJECT IDENTIFIER ::= {apexGbeSfpStatus 1}
--          apexGbeSfpStatusTable                                               {apexGbeSfpStatus 2}
--             apexGbeSfpStatusEntry                                            {apexGbeSfpStatusTable 1}
--                apexGbeSfpStatusGbeIfNum                                      {apexGbeSfpStatusEntry 1}
--                apexGbeSfpStatusVendorId                                      {apexGbeSfpStatusEntry 2}
--                apexGbeSfpStatusDiagInfo                                      {apexGbeSfpStatusEntry 3}
   apexRf                                                 OBJECT IDENTIFIER ::= {apex3000 8}
      apexRfConfig                                        OBJECT IDENTIFIER ::= {apexRf 1}
         apexRfConfigGeneral                              OBJECT IDENTIFIER ::= {apexRfConfig 1}
--          apexRfConfigTransmissionMode                                        {apexRfConfigGeneral 1}
--       apexRfConfigBladeApplyTable                                            {apexRfConfig 2}
--          apexRfConfigBladeApplyEntry                                         {apexRfConfigBladeApplyTable 1}
--             apexRfConfigBladeApplyBladeNum                                   {apexRfConfigBladeApplyEntry 1}
--             apexRfConfigBladeApplyChange                                     {apexRfConfigBladeApplyEntry 2}
--             apexRfConfigBladeInvalidApplyText                                {apexRfConfigBladeApplyEntry 3}
         apexRfConfigBlade1                               OBJECT IDENTIFIER ::= {apexRfConfig 3}
            apexRfConfigBlade1General                     OBJECT IDENTIFIER ::= {apexRfConfigBlade1 1}
--          apexRfConfigBlade1ModesTable                  OBJECT IDENTIFIER ::= {apexRfConfigBlade1 2}
--             apexRfConfigBlade1ModesEntry                                     {apexRfConfigBlade1ModesTable 1}
--                apexRfConfigBlade1ModesIndex                                  {apexRfConfigBlade1ModesEntry 1}
--                apexRfConfigBlade1ModesModulationModeAnnexB                   {apexRfConfigBlade1ModesEntry 2}
--                apexRfConfigBlade1ModesInterleaverDepthAnnexB                 {apexRfConfigBlade1ModesEntry 3}
--                apexRfConfigBlade1ModesModulationModeAnnexA                   {apexRfConfigBlade1ModesEntry 4}
--                apexRfConfigBlade1ModesSymbolRateAnnexA                       {apexRfConfigBlade1ModesEntry 5}
--                apexRfConfigBlade1ModesModulationModeAnnexC                   {apexRfConfigBlade1ModesEntry 6}
--                apexRfConfigBlade1ModesSymbolRateAnnexC                       {apexRfConfigBlade1ModesEntry 7}
--          apexRfConfigBlade1RfPortTable                 OBJECT IDENTIFIER ::= {apexRfConfigBlade1 3}
--             apexRfConfigBlade1RfPortEntry                                    {apexRfConfigBlade1RfPortTable 1}
--                apexRfConfigBlade1RfPortNum                                   {apexRfConfigBlade1RfPortEntry 1}
--                apexRfConfigBlade1RfPortSpectrumInversion                     {apexRfConfigBlade1RfPortEntry 2}
--                apexRfConfigBlade1RfPortMute                                  {apexRfConfigBlade1RfPortEntry 3}
--                apexRfConfigBlade1RfPortRfLevel                               {apexRfConfigBlade1RfPortEntry 4}
--                apexRfConfigBlade1RfPortDiagSuppressMode                      {apexRfConfigBlade1RfPortEntry 5}
--                apexRfConfigBlade1RfPortDiagSuppressChannel                   {apexRfConfigBlade1RfPortEntry 6}
--                apexRfConfigBlade1RfPortNprimeMax                             {apexRfConfigBlade1RfPortEntry 7}
--                apexRfConfigBlade1RfPortNprimeMaxMode                         {apexRfConfigBlade1RfPortEntry 8}
--          apexRfConfigBlade1SuperBlockFreqTable         OBJECT IDENTIFIER ::= {apexRfConfigBlade1 4}
--             apexRfConfigBlade1SuperBlockFreqEntry                            {apexRfConfigBlade1SuperBlockFreqTable 1}
--                apexRfConfigBlade1SuperBlockFreqRfPortNum                     {apexRfConfigBlade1SuperBlockFreqEntry 1}
--                apexRfConfigBlade1SuperBlockFreqBlockNum                      {apexRfConfigBlade1SuperBlockFreqEntry 2}
--                apexRfConfigBlade1SuperBlockFreqAnnexB                        {apexRfConfigBlade1SuperBlockFreqEntry 3}
--                apexRfConfigBlade1SuperBlockFreqAnnexC                        {apexRfConfigBlade1SuperBlockFreqEntry 4}
--                apexRfConfigBlade1SuperBlockFreqAnnexA                        {apexRfConfigBlade1SuperBlockFreqEntry 5}
--          apexRfConfigBlade1SubBlockFreqTable           OBJECT IDENTIFIER ::= {apexRfConfigBlade1 5}
--             apexRfConfigBlade1SubBlockFreqEntry                              {apexRfConfigBlade1SubBlockFreqTable 1}
--                apexRfConfigBlade1SubBlockFreqRfPortNum                       {apexRfConfigBlade1SubBlockFreqEntry 1}
--                apexRfConfigBlade1SubBlockFreqBlockNum                        {apexRfConfigBlade1SubBlockFreqEntry 2}
--                apexRfConfigBlade1SubBlockFreqAnnexB                          {apexRfConfigBlade1SubBlockFreqEntry 3}
--                apexRfConfigBlade1SubBlockFreqAnnexC                          {apexRfConfigBlade1SubBlockFreqEntry 4}
--                apexRfConfigBlade1SubBlockFreqAnnexA                          {apexRfConfigBlade1SubBlockFreqEntry 5}
--                apexRfConfigBlade1SubBlockChanSpacingAnnexA                   {apexRfConfigBlade1SubBlockFreqEntry 6}
--          apexRfConfigBlade1ChannelTable                OBJECT IDENTIFIER ::= {apexRfConfigBlade1 6}
--             apexRfConfigBlade1ChannelEntry                                   {apexRfConfigBlade1ChannelTable 1}
--                apexRfConfigBlade1ChannelRfPortNum                            {apexRfConfigBlade1ChannelEntry 1}
--                apexRfConfigBlade1ChannelChanNum                              {apexRfConfigBlade1ChannelEntry 2}
--                apexRfConfigBlade1ChannelFrequencyGridSelect                  {apexRfConfigBlade1ChannelEntry 3}
--                apexRfConfigBlade1ChannelModeComboSelectAnnexA                {apexRfConfigBlade1ChannelEntry 4}
--                apexRfConfigBlade1ChannelModeComboSelectAnnexB                {apexRfConfigBlade1ChannelEntry 5}
--                apexRfConfigBlade1ChannelModeComboSelectAnnexC                {apexRfConfigBlade1ChannelEntry 6}
--                apexRfConfigBlade1ChannelRfLevelAdjust                        {apexRfConfigBlade1ChannelEntry 7}
--                apexRfConfigBlade1ChannelTestMode                             {apexRfConfigBlade1ChannelEntry 8}
--                apexRfConfigBlade1ChannelMute                                 {apexRfConfigBlade1ChannelEntry 9}
         apexRfConfigBlade2                               OBJECT IDENTIFIER ::= {apexRfConfig 4}
            apexRfConfigBlade2General                     OBJECT IDENTIFIER ::= {apexRfConfigBlade2 1}
--          apexRfConfigBlade2ModesTable                  OBJECT IDENTIFIER ::= {apexRfConfigBlade2 2}
--             apexRfConfigBlade2ModesEntry                                     {apexRfConfigBlade2ModesTable 1}
--                apexRfConfigBlade2ModesIndex                                  {apexRfConfigBlade2ModesEntry 1}
--                apexRfConfigBlade2ModesModulationModeAnnexB                   {apexRfConfigBlade2ModesEntry 2}
--                apexRfConfigBlade2ModesInterleaverDepthAnnexB                 {apexRfConfigBlade2ModesEntry 3}
--                apexRfConfigBlade2ModesModulationModeAnnexA                   {apexRfConfigBlade2ModesEntry 4}
--                apexRfConfigBlade2ModesSymbolRateAnnexA                       {apexRfConfigBlade2ModesEntry 5}
--                apexRfConfigBlade2ModesModulationModeAnnexC                   {apexRfConfigBlade2ModesEntry 6}
--                apexRfConfigBlade2ModesSymbolRateAnnexC                       {apexRfConfigBlade2ModesEntry 7}
--          apexRfConfigBlade2RfPortTable                 OBJECT IDENTIFIER ::= {apexRfConfigBlade2 3}
--             apexRfConfigBlade2RfPortEntry                                    {apexRfConfigBlade2RfPortTable 1}
--                apexRfConfigBlade2RfPortNum                                   {apexRfConfigBlade2RfPortEntry 1}
--                apexRfConfigBlade2RfPortSpectrumInversion                     {apexRfConfigBlade2RfPortEntry 2}
--                apexRfConfigBlade2RfPortMute                                  {apexRfConfigBlade2RfPortEntry 3}
--                apexRfConfigBlade2RfPortRfLevel                               {apexRfConfigBlade2RfPortEntry 4}
--                apexRfConfigBlade2RfPortDiagSuppressMode                      {apexRfConfigBlade2RfPortEntry 5}
--                apexRfConfigBlade2RfPortDiagSuppressChannel                   {apexRfConfigBlade2RfPortEntry 6}
--                apexRfConfigBlade2RfPortNprimeMax                             {apexRfConfigBlade2RfPortEntry 7}
--                apexRfConfigBlade2RfPortNprimeMaxMode                         {apexRfConfigBlade2RfPortEntry 8}
--          apexRfConfigBlade2SuperBlockFreqTable         OBJECT IDENTIFIER ::= {apexRfConfigBlade2 4}
--             apexRfConfigBlade2SuperBlockFreqEntry                            {apexRfConfigBlade2SuperBlockFreqTable 1}
--                apexRfConfigBlade2SuperBlockFreqRfPortNum                     {apexRfConfigBlade2SuperBlockFreqEntry 1}
--                apexRfConfigBlade2SuperBlockFreqBlockNum                      {apexRfConfigBlade2SuperBlockFreqEntry 2}
--                apexRfConfigBlade2SuperBlockFreqAnnexB                        {apexRfConfigBlade2SuperBlockFreqEntry 3}
--                apexRfConfigBlade2SuperBlockFreqAnnexC                        {apexRfConfigBlade2SuperBlockFreqEntry 4}
--                apexRfConfigBlade2SuperBlockFreqAnnexA                        {apexRfConfigBlade2SuperBlockFreqEntry 5}
--          apexRfConfigBlade2SubBlockFreqTable           OBJECT IDENTIFIER ::= {apexRfConfigBlade2 5}
--             apexRfConfigBlade2SubBlockFreqEntry                              {apexRfConfigBlade2SubBlockFreqTable 1}
--                apexRfConfigBlade2SubBlockFreqRfPortNum                       {apexRfConfigBlade2SubBlockFreqEntry 1}
--                apexRfConfigBlade2SubBlockFreqBlockNum                        {apexRfConfigBlade2SubBlockFreqEntry 2}
--                apexRfConfigBlade2SubBlockFreqAnnexB                          {apexRfConfigBlade2SubBlockFreqEntry 3}
--                apexRfConfigBlade2SubBlockFreqAnnexC                          {apexRfConfigBlade2SubBlockFreqEntry 4}
--                apexRfConfigBlade2SubBlockFreqAnnexA                          {apexRfConfigBlade2SubBlockFreqEntry 5}
--                apexRfConfigBlade2SubBlockChanSpacingAnnexA                   {apexRfConfigBlade2SubBlockFreqEntry 6}
--          apexRfConfigBlade2ChannelTable                OBJECT IDENTIFIER ::= {apexRfConfigBlade2 6}
--             apexRfConfigBlade2ChannelEntry                                   {apexRfConfigBlade2ChannelTable 1}
--                apexRfConfigBlade2ChannelRfPortNum                            {apexRfConfigBlade2ChannelEntry 1}
--                apexRfConfigBlade2ChannelChanNum                              {apexRfConfigBlade2ChannelEntry 2}
--                apexRfConfigBlade2ChannelFrequencyGridSelect                  {apexRfConfigBlade2ChannelEntry 3}
--                apexRfConfigBlade2ChannelModeComboSelectAnnexA                {apexRfConfigBlade2ChannelEntry 4}
--                apexRfConfigBlade2ChannelModeComboSelectAnnexB                {apexRfConfigBlade2ChannelEntry 5}
--                apexRfConfigBlade2ChannelModeComboSelectAnnexC                {apexRfConfigBlade2ChannelEntry 6}
--                apexRfConfigBlade2ChannelRfLevelAdjust                        {apexRfConfigBlade2ChannelEntry 7}
--                apexRfConfigBlade2ChannelTestMode                             {apexRfConfigBlade2ChannelEntry 8}
--                apexRfConfigBlade2ChannelMute                                 {apexRfConfigBlade2ChannelEntry 9}
         apexRfConfigBlade3                               OBJECT IDENTIFIER ::= {apexRfConfig 5}
            apexRfConfigBlade3General                     OBJECT IDENTIFIER ::= {apexRfConfigBlade3 1}
--          apexRfConfigBlade3ModesTable                  OBJECT IDENTIFIER ::= {apexRfConfigBlade3 2}
--             apexRfConfigBlade3ModesEntry                                     {apexRfConfigBlade3ModesTable 1}
--                apexRfConfigBlade3ModesIndex                                  {apexRfConfigBlade3ModesEntry 1}
--                apexRfConfigBlade3ModesModulationModeAnnexB                   {apexRfConfigBlade3ModesEntry 2}
--                apexRfConfigBlade3ModesInterleaverDepthAnnexB                 {apexRfConfigBlade3ModesEntry 3}
--                apexRfConfigBlade3ModesModulationModeAnnexA                   {apexRfConfigBlade3ModesEntry 4}
--                apexRfConfigBlade3ModesSymbolRateAnnexA                       {apexRfConfigBlade3ModesEntry 5}
--                apexRfConfigBlade3ModesModulationModeAnnexC                   {apexRfConfigBlade3ModesEntry 6}
--                apexRfConfigBlade3ModesSymbolRateAnnexC                       {apexRfConfigBlade3ModesEntry 7}
--          apexRfConfigBlade3RfPortTable                 OBJECT IDENTIFIER ::= {apexRfConfigBlade3 3}
--             apexRfConfigBlade3RfPortEntry                                    {apexRfConfigBlade3RfPortTable 1}
--                apexRfConfigBlade3RfPortNum                                   {apexRfConfigBlade3RfPortEntry 1}
--                apexRfConfigBlade3RfPortSpectrumInversion                     {apexRfConfigBlade3RfPortEntry 2}
--                apexRfConfigBlade3RfPortMute                                  {apexRfConfigBlade3RfPortEntry 3}
--                apexRfConfigBlade3RfPortRfLevel                               {apexRfConfigBlade3RfPortEntry 4}
--                apexRfConfigBlade3RfPortDiagSuppressMode                      {apexRfConfigBlade3RfPortEntry 5}
--                apexRfConfigBlade3RfPortDiagSuppressChannel                   {apexRfConfigBlade3RfPortEntry 6}
--                apexRfConfigBlade3RfPortNprimeMax                             {apexRfConfigBlade3RfPortEntry 7}
--                apexRfConfigBlade3RfPortNprimeMaxMode                         {apexRfConfigBlade3RfPortEntry 8}
--          apexRfConfigBlade3SuperBlockFreqTable         OBJECT IDENTIFIER ::= {apexRfConfigBlade3 4}
--             apexRfConfigBlade3SuperBlockFreqEntry                            {apexRfConfigBlade3SuperBlockFreqTable 1}
--                apexRfConfigBlade3SuperBlockFreqRfPortNum                     {apexRfConfigBlade3SuperBlockFreqEntry 1}
--                apexRfConfigBlade3SuperBlockFreqBlockNum                      {apexRfConfigBlade3SuperBlockFreqEntry 2}
--                apexRfConfigBlade3SuperBlockFreqAnnexB                        {apexRfConfigBlade3SuperBlockFreqEntry 3}
--                apexRfConfigBlade3SuperBlockFreqAnnexC                        {apexRfConfigBlade3SuperBlockFreqEntry 4}
--                apexRfConfigBlade3SuperBlockFreqAnnexA                        {apexRfConfigBlade3SuperBlockFreqEntry 5}
--          apexRfConfigBlade3SubBlockFreqTable           OBJECT IDENTIFIER ::= {apexRfConfigBlade3 5}
--             apexRfConfigBlade3SubBlockFreqEntry                              {apexRfConfigBlade3SubBlockFreqTable 1}
--                apexRfConfigBlade3SubBlockFreqRfPortNum                       {apexRfConfigBlade3SubBlockFreqEntry 1}
--                apexRfConfigBlade3SubBlockFreqBlockNum                        {apexRfConfigBlade3SubBlockFreqEntry 2}
--                apexRfConfigBlade3SubBlockFreqAnnexB                          {apexRfConfigBlade3SubBlockFreqEntry 3}
--                apexRfConfigBlade3SubBlockFreqAnnexC                          {apexRfConfigBlade3SubBlockFreqEntry 4}
--                apexRfConfigBlade3SubBlockFreqAnnexA                          {apexRfConfigBlade3SubBlockFreqEntry 5}
--                apexRfConfigBlade3SubBlockChanSpacingAnnexA                   {apexRfConfigBlade3SubBlockFreqEntry 6}
--          apexRfConfigBlade3ChannelTable                OBJECT IDENTIFIER ::= {apexRfConfigBlade3 6}
--             apexRfConfigBlade3ChannelEntry                                   {apexRfConfigBlade3ChannelTable 1}
--                apexRfConfigBlade3ChannelRfPortNum                            {apexRfConfigBlade3ChannelEntry 1}
--                apexRfConfigBlade3ChannelChanNum                              {apexRfConfigBlade3ChannelEntry 2}
--                apexRfConfigBlade3ChannelFrequencyGridSelect                  {apexRfConfigBlade3ChannelEntry 3}
--                apexRfConfigBlade3ChannelModeComboSelectAnnexA                {apexRfConfigBlade3ChannelEntry 4}
--                apexRfConfigBlade3ChannelModeComboSelectAnnexB                {apexRfConfigBlade3ChannelEntry 5}
--                apexRfConfigBlade3ChannelModeComboSelectAnnexC                {apexRfConfigBlade3ChannelEntry 6}
--                apexRfConfigBlade3ChannelRfLevelAdjust                        {apexRfConfigBlade3ChannelEntry 7}
--                apexRfConfigBlade3ChannelTestMode                             {apexRfConfigBlade3ChannelEntry 8}
--                apexRfConfigBlade3ChannelMute                                 {apexRfConfigBlade3ChannelEntry 9}
         apexRfConfigBlade4                               OBJECT IDENTIFIER ::= {apexRfConfig 6}
            apexRfConfigBlade4General                     OBJECT IDENTIFIER ::= {apexRfConfigBlade4 1}
--          apexRfConfigBlade4ModesTable                  OBJECT IDENTIFIER ::= {apexRfConfigBlade4 2}
--             apexRfConfigBlade4ModesEntry                                     {apexRfConfigBlade4ModesTable 1}
--                apexRfConfigBlade4ModesIndex                                  {apexRfConfigBlade4ModesEntry 1}
--                apexRfConfigBlade4ModesModulationModeAnnexB                   {apexRfConfigBlade4ModesEntry 2}
--                apexRfConfigBlade4ModesInterleaverDepthAnnexB                 {apexRfConfigBlade4ModesEntry 3}
--                apexRfConfigBlade4ModesModulationModeAnnexA                   {apexRfConfigBlade4ModesEntry 4}
--                apexRfConfigBlade4ModesSymbolRateAnnexA                       {apexRfConfigBlade4ModesEntry 5}
--                apexRfConfigBlade4ModesModulationModeAnnexC                   {apexRfConfigBlade4ModesEntry 6}
--                apexRfConfigBlade4ModesSymbolRateAnnexC                       {apexRfConfigBlade4ModesEntry 7}
--          apexRfConfigBlade4RfPortTable                 OBJECT IDENTIFIER ::= {apexRfConfigBlade4 3}
--             apexRfConfigBlade4RfPortEntry                                    {apexRfConfigBlade4RfPortTable 1}
--                apexRfConfigBlade4RfPortNum                                   {apexRfConfigBlade4RfPortEntry 1}
--                apexRfConfigBlade4RfPortSpectrumInversion                     {apexRfConfigBlade4RfPortEntry 2}
--                apexRfConfigBlade4RfPortMute                                  {apexRfConfigBlade4RfPortEntry 3}
--                apexRfConfigBlade4RfPortRfLevel                               {apexRfConfigBlade4RfPortEntry 4}
--                apexRfConfigBlade4RfPortDiagSuppressMode                      {apexRfConfigBlade4RfPortEntry 5}
--                apexRfConfigBlade4RfPortDiagSuppressChannel                   {apexRfConfigBlade4RfPortEntry 6}
--                apexRfConfigBlade4RfPortNprimeMax                             {apexRfConfigBlade4RfPortEntry 7}
--                apexRfConfigBlade4RfPortNprimeMaxMode                         {apexRfConfigBlade4RfPortEntry 8}
--          apexRfConfigBlade4SuperBlockFreqTable         OBJECT IDENTIFIER ::= {apexRfConfigBlade4 4}
--             apexRfConfigBlade4SuperBlockFreqEntry                            {apexRfConfigBlade4SuperBlockFreqTable 1}
--                apexRfConfigBlade4SuperBlockFreqRfPortNum                     {apexRfConfigBlade4SuperBlockFreqEntry 1}
--                apexRfConfigBlade4SuperBlockFreqBlockNum                      {apexRfConfigBlade4SuperBlockFreqEntry 2}
--                apexRfConfigBlade4SuperBlockFreqAnnexB                        {apexRfConfigBlade4SuperBlockFreqEntry 3}
--                apexRfConfigBlade4SuperBlockFreqAnnexC                        {apexRfConfigBlade4SuperBlockFreqEntry 4}
--                apexRfConfigBlade4SuperBlockFreqAnnexA                        {apexRfConfigBlade4SuperBlockFreqEntry 5}
--          apexRfConfigBlade4SubBlockFreqTable           OBJECT IDENTIFIER ::= {apexRfConfigBlade4 5}
--             apexRfConfigBlade4SubBlockFreqEntry                              {apexRfConfigBlade4SubBlockFreqTable 1}
--                apexRfConfigBlade4SubBlockFreqRfPortNum                       {apexRfConfigBlade4SubBlockFreqEntry 1}
--                apexRfConfigBlade4SubBlockFreqBlockNum                        {apexRfConfigBlade4SubBlockFreqEntry 2}
--                apexRfConfigBlade4SubBlockFreqAnnexB                          {apexRfConfigBlade4SubBlockFreqEntry 3}
--                apexRfConfigBlade4SubBlockFreqAnnexC                          {apexRfConfigBlade4SubBlockFreqEntry 4}
--                apexRfConfigBlade4SubBlockFreqAnnexA                          {apexRfConfigBlade4SubBlockFreqEntry 5}
--                apexRfConfigBlade4SubBlockChanSpacingAnnexA                   {apexRfConfigBlade4SubBlockFreqEntry 6}
--          apexRfConfigBlade4ChannelTable                OBJECT IDENTIFIER ::= {apexRfConfigBlade4 6}
--             apexRfConfigBlade4ChannelEntry                                   {apexRfConfigBlade4ChannelTable 1}
--                apexRfConfigBlade4ChannelRfPortNum                            {apexRfConfigBlade4ChannelEntry 1}
--                apexRfConfigBlade4ChannelChanNum                              {apexRfConfigBlade4ChannelEntry 2}
--                apexRfConfigBlade4ChannelFrequencyGridSelect                  {apexRfConfigBlade4ChannelEntry 3}
--                apexRfConfigBlade4ChannelModeComboSelectAnnexA                {apexRfConfigBlade4ChannelEntry 4}
--                apexRfConfigBlade4ChannelModeComboSelectAnnexB                {apexRfConfigBlade4ChannelEntry 5}
--                apexRfConfigBlade4ChannelModeComboSelectAnnexC                {apexRfConfigBlade4ChannelEntry 6}
--                apexRfConfigBlade4ChannelRfLevelAdjust                        {apexRfConfigBlade4ChannelEntry 7}
--                apexRfConfigBlade4ChannelTestMode                             {apexRfConfigBlade4ChannelEntry 8}
--                apexRfConfigBlade4ChannelMute                                 {apexRfConfigBlade4ChannelEntry 9}
         apexRfConfigBlade5                               OBJECT IDENTIFIER ::= {apexRfConfig 7}
            apexRfConfigBlade5General                     OBJECT IDENTIFIER ::= {apexRfConfigBlade5 1}
--          apexRfConfigBlade5ModesTable                  OBJECT IDENTIFIER ::= {apexRfConfigBlade5 2}
--             apexRfConfigBlade5ModesEntry                                     {apexRfConfigBlade5ModesTable 1}
--                apexRfConfigBlade5ModesIndex                                  {apexRfConfigBlade5ModesEntry 1}
--                apexRfConfigBlade5ModesModulationModeAnnexB                   {apexRfConfigBlade5ModesEntry 2}
--                apexRfConfigBlade5ModesInterleaverDepthAnnexB                 {apexRfConfigBlade5ModesEntry 3}
--                apexRfConfigBlade5ModesModulationModeAnnexA                   {apexRfConfigBlade5ModesEntry 4}
--                apexRfConfigBlade5ModesSymbolRateAnnexA                       {apexRfConfigBlade5ModesEntry 5}
--                apexRfConfigBlade5ModesModulationModeAnnexC                   {apexRfConfigBlade5ModesEntry 6}
--                apexRfConfigBlade5ModesSymbolRateAnnexC                       {apexRfConfigBlade5ModesEntry 7}
--          apexRfConfigBlade5RfPortTable                 OBJECT IDENTIFIER ::= {apexRfConfigBlade5 3}
--             apexRfConfigBlade5RfPortEntry                                    {apexRfConfigBlade5RfPortTable 1}
--                apexRfConfigBlade5RfPortNum                                   {apexRfConfigBlade5RfPortEntry 1}
--                apexRfConfigBlade5RfPortSpectrumInversion                     {apexRfConfigBlade5RfPortEntry 2}
--                apexRfConfigBlade5RfPortMute                                  {apexRfConfigBlade5RfPortEntry 3}
--                apexRfConfigBlade5RfPortRfLevel                               {apexRfConfigBlade5RfPortEntry 4}
--                apexRfConfigBlade5RfPortDiagSuppressMode                      {apexRfConfigBlade5RfPortEntry 5}
--                apexRfConfigBlade5RfPortDiagSuppressChannel                   {apexRfConfigBlade5RfPortEntry 6}
--                apexRfConfigBlade5RfPortNprimeMax                             {apexRfConfigBlade5RfPortEntry 7}
--                apexRfConfigBlade5RfPortNprimeMaxMode                         {apexRfConfigBlade5RfPortEntry 8}
--          apexRfConfigBlade5SuperBlockFreqTable         OBJECT IDENTIFIER ::= {apexRfConfigBlade5 4}
--             apexRfConfigBlade5SuperBlockFreqEntry                            {apexRfConfigBlade5SuperBlockFreqTable 1}
--                apexRfConfigBlade5SuperBlockFreqRfPortNum                     {apexRfConfigBlade5SuperBlockFreqEntry 1}
--                apexRfConfigBlade5SuperBlockFreqBlockNum                      {apexRfConfigBlade5SuperBlockFreqEntry 2}
--                apexRfConfigBlade5SuperBlockFreqAnnexB                        {apexRfConfigBlade5SuperBlockFreqEntry 3}
--                apexRfConfigBlade5SuperBlockFreqAnnexC                        {apexRfConfigBlade5SuperBlockFreqEntry 4}
--                apexRfConfigBlade5SuperBlockFreqAnnexA                        {apexRfConfigBlade5SuperBlockFreqEntry 5}
--          apexRfConfigBlade5SubBlockFreqTable           OBJECT IDENTIFIER ::= {apexRfConfigBlade5 5}
--             apexRfConfigBlade5SubBlockFreqEntry                              {apexRfConfigBlade5SubBlockFreqTable 1}
--                apexRfConfigBlade5SubBlockFreqRfPortNum                       {apexRfConfigBlade5SubBlockFreqEntry 1}
--                apexRfConfigBlade5SubBlockFreqBlockNum                        {apexRfConfigBlade5SubBlockFreqEntry 2}
--                apexRfConfigBlade5SubBlockFreqAnnexB                          {apexRfConfigBlade5SubBlockFreqEntry 3}
--                apexRfConfigBlade5SubBlockFreqAnnexC                          {apexRfConfigBlade5SubBlockFreqEntry 4}
--                apexRfConfigBlade5SubBlockFreqAnnexA                          {apexRfConfigBlade5SubBlockFreqEntry 5}
--                apexRfConfigBlade5SubBlockChanSpacingAnnexA                   {apexRfConfigBlade5SubBlockFreqEntry 6}
--          apexRfConfigBlade5ChannelTable                OBJECT IDENTIFIER ::= {apexRfConfigBlade5 6}
--             apexRfConfigBlade5ChannelEntry                                   {apexRfConfigBlade5ChannelTable 1}
--                apexRfConfigBlade5ChannelRfPortNum                            {apexRfConfigBlade5ChannelEntry 1}
--                apexRfConfigBlade5ChannelChanNum                              {apexRfConfigBlade5ChannelEntry 2}
--                apexRfConfigBlade5ChannelFrequencyGridSelect                  {apexRfConfigBlade5ChannelEntry 3}
--                apexRfConfigBlade5ChannelModeComboSelectAnnexA                {apexRfConfigBlade5ChannelEntry 4}
--                apexRfConfigBlade5ChannelModeComboSelectAnnexB                {apexRfConfigBlade5ChannelEntry 5}
--                apexRfConfigBlade5ChannelModeComboSelectAnnexC                {apexRfConfigBlade5ChannelEntry 6}
--                apexRfConfigBlade5ChannelRfLevelAdjust                        {apexRfConfigBlade5ChannelEntry 7}
--                apexRfConfigBlade5ChannelTestMode                             {apexRfConfigBlade5ChannelEntry 8}
--                apexRfConfigBlade5ChannelMute                                 {apexRfConfigBlade5ChannelEntry 9}
         apexRfConfigBlade6                               OBJECT IDENTIFIER ::= {apexRfConfig 8}
            apexRfConfigBlade6General                     OBJECT IDENTIFIER ::= {apexRfConfigBlade6 1}
--          apexRfConfigBlade6ModesTable                  OBJECT IDENTIFIER ::= {apexRfConfigBlade6 2}
--             apexRfConfigBlade6ModesEntry                                     {apexRfConfigBlade6ModesTable 1}
--                apexRfConfigBlade6ModesIndex                                  {apexRfConfigBlade6ModesEntry 1}
--                apexRfConfigBlade6ModesModulationModeAnnexB                   {apexRfConfigBlade6ModesEntry 2}
--                apexRfConfigBlade6ModesInterleaverDepthAnnexB                 {apexRfConfigBlade6ModesEntry 3}
--                apexRfConfigBlade6ModesModulationModeAnnexA                   {apexRfConfigBlade6ModesEntry 4}
--                apexRfConfigBlade6ModesSymbolRateAnnexA                       {apexRfConfigBlade6ModesEntry 5}
--                apexRfConfigBlade6ModesModulationModeAnnexC                   {apexRfConfigBlade6ModesEntry 6}
--                apexRfConfigBlade6ModesSymbolRateAnnexC                       {apexRfConfigBlade6ModesEntry 7}
--          apexRfConfigBlade6RfPortTable                 OBJECT IDENTIFIER ::= {apexRfConfigBlade6 3}
--             apexRfConfigBlade6RfPortEntry                                    {apexRfConfigBlade6RfPortTable 1}
--                apexRfConfigBlade6RfPortNum                                   {apexRfConfigBlade6RfPortEntry 1}
--                apexRfConfigBlade6RfPortSpectrumInversion                     {apexRfConfigBlade6RfPortEntry 2}
--                apexRfConfigBlade6RfPortMute                                  {apexRfConfigBlade6RfPortEntry 3}
--                apexRfConfigBlade6RfPortRfLevel                               {apexRfConfigBlade6RfPortEntry 4}
--                apexRfConfigBlade6RfPortDiagSuppressMode                      {apexRfConfigBlade6RfPortEntry 5}
--                apexRfConfigBlade6RfPortDiagSuppressChannel                   {apexRfConfigBlade6RfPortEntry 6}
--                apexRfConfigBlade6RfPortNprimeMax                             {apexRfConfigBlade6RfPortEntry 7}
--                apexRfConfigBlade6RfPortNprimeMaxMode                         {apexRfConfigBlade6RfPortEntry 8}
--          apexRfConfigBlade6SuperBlockFreqTable         OBJECT IDENTIFIER ::= {apexRfConfigBlade6 4}
--             apexRfConfigBlade6SuperBlockFreqEntry                            {apexRfConfigBlade6SuperBlockFreqTable 1}
--                apexRfConfigBlade6SuperBlockFreqRfPortNum                     {apexRfConfigBlade6SuperBlockFreqEntry 1}
--                apexRfConfigBlade6SuperBlockFreqBlockNum                      {apexRfConfigBlade6SuperBlockFreqEntry 2}
--                apexRfConfigBlade6SuperBlockFreqAnnexB                        {apexRfConfigBlade6SuperBlockFreqEntry 3}
--                apexRfConfigBlade6SuperBlockFreqAnnexC                        {apexRfConfigBlade6SuperBlockFreqEntry 4}
--                apexRfConfigBlade6SuperBlockFreqAnnexA                        {apexRfConfigBlade6SuperBlockFreqEntry 5}
--          apexRfConfigBlade6SubBlockFreqTable           OBJECT IDENTIFIER ::= {apexRfConfigBlade6 5}
--             apexRfConfigBlade6SubBlockFreqEntry                              {apexRfConfigBlade6SubBlockFreqTable 1}
--                apexRfConfigBlade6SubBlockFreqRfPortNum                       {apexRfConfigBlade6SubBlockFreqEntry 1}
--                apexRfConfigBlade6SubBlockFreqBlockNum                        {apexRfConfigBlade6SubBlockFreqEntry 2}
--                apexRfConfigBlade6SubBlockFreqAnnexB                          {apexRfConfigBlade6SubBlockFreqEntry 3}
--                apexRfConfigBlade6SubBlockFreqAnnexC                          {apexRfConfigBlade6SubBlockFreqEntry 4}
--                apexRfConfigBlade6SubBlockFreqAnnexA                          {apexRfConfigBlade6SubBlockFreqEntry 5}
--                apexRfConfigBlade6SubBlockChanSpacingAnnexA                   {apexRfConfigBlade6SubBlockFreqEntry 6}
--          apexRfConfigBlade6ChannelTable                OBJECT IDENTIFIER ::= {apexRfConfigBlade6 6}
--             apexRfConfigBlade6ChannelEntry                                   {apexRfConfigBlade6ChannelTable 1}
--                apexRfConfigBlade6ChannelRfPortNum                            {apexRfConfigBlade6ChannelEntry 1}
--                apexRfConfigBlade6ChannelChanNum                              {apexRfConfigBlade6ChannelEntry 2}
--                apexRfConfigBlade6ChannelFrequencyGridSelect                  {apexRfConfigBlade6ChannelEntry 3}
--                apexRfConfigBlade6ChannelModeComboSelectAnnexA                {apexRfConfigBlade6ChannelEntry 4}
--                apexRfConfigBlade6ChannelModeComboSelectAnnexB                {apexRfConfigBlade6ChannelEntry 5}
--                apexRfConfigBlade6ChannelModeComboSelectAnnexC                {apexRfConfigBlade6ChannelEntry 6}
--                apexRfConfigBlade6ChannelRfLevelAdjust                        {apexRfConfigBlade6ChannelEntry 7}
--                apexRfConfigBlade6ChannelTestMode                             {apexRfConfigBlade6ChannelEntry 8}
--                apexRfConfigBlade6ChannelMute                                 {apexRfConfigBlade6ChannelEntry 9}
         apexRfConfigBlade7                               OBJECT IDENTIFIER ::= {apexRfConfig 9}
            apexRfConfigBlade7General                     OBJECT IDENTIFIER ::= {apexRfConfigBlade7 1}
--          apexRfConfigBlade7ModesTable                  OBJECT IDENTIFIER ::= {apexRfConfigBlade7 2}
--             apexRfConfigBlade7ModesEntry                                     {apexRfConfigBlade7ModesTable 1}
--                apexRfConfigBlade7ModesIndex                                  {apexRfConfigBlade7ModesEntry 1}
--                apexRfConfigBlade7ModesModulationModeAnnexB                   {apexRfConfigBlade7ModesEntry 2}
--                apexRfConfigBlade7ModesInterleaverDepthAnnexB                 {apexRfConfigBlade7ModesEntry 3}
--                apexRfConfigBlade7ModesModulationModeAnnexA                   {apexRfConfigBlade7ModesEntry 4}
--                apexRfConfigBlade7ModesSymbolRateAnnexA                       {apexRfConfigBlade7ModesEntry 5}
--                apexRfConfigBlade7ModesModulationModeAnnexC                   {apexRfConfigBlade7ModesEntry 6}
--                apexRfConfigBlade7ModesSymbolRateAnnexC                       {apexRfConfigBlade7ModesEntry 7}
--          apexRfConfigBlade7RfPortTable                 OBJECT IDENTIFIER ::= {apexRfConfigBlade7 3}
--             apexRfConfigBlade7RfPortEntry                                    {apexRfConfigBlade7RfPortTable 1}
--                apexRfConfigBlade7RfPortNum                                   {apexRfConfigBlade7RfPortEntry 1}
--                apexRfConfigBlade7RfPortSpectrumInversion                     {apexRfConfigBlade7RfPortEntry 2}
--                apexRfConfigBlade7RfPortMute                                  {apexRfConfigBlade7RfPortEntry 3}
--                apexRfConfigBlade7RfPortRfLevel                               {apexRfConfigBlade7RfPortEntry 4}
--                apexRfConfigBlade7RfPortDiagSuppressMode                      {apexRfConfigBlade7RfPortEntry 5}
--                apexRfConfigBlade7RfPortDiagSuppressChannel                   {apexRfConfigBlade7RfPortEntry 6}
--                apexRfConfigBlade7RfPortNprimeMax                             {apexRfConfigBlade7RfPortEntry 7}
--                apexRfConfigBlade7RfPortNprimeMaxMode                         {apexRfConfigBlade7RfPortEntry 8}
--          apexRfConfigBlade7SuperBlockFreqTable         OBJECT IDENTIFIER ::= {apexRfConfigBlade7 4}
--             apexRfConfigBlade7SuperBlockFreqEntry                            {apexRfConfigBlade7SuperBlockFreqTable 1}
--                apexRfConfigBlade7SuperBlockFreqRfPortNum                     {apexRfConfigBlade7SuperBlockFreqEntry 1}
--                apexRfConfigBlade7SuperBlockFreqBlockNum                      {apexRfConfigBlade7SuperBlockFreqEntry 2}
--                apexRfConfigBlade7SuperBlockFreqAnnexB                        {apexRfConfigBlade7SuperBlockFreqEntry 3}
--                apexRfConfigBlade7SuperBlockFreqAnnexC                        {apexRfConfigBlade7SuperBlockFreqEntry 4}
--                apexRfConfigBlade7SuperBlockFreqAnnexA                        {apexRfConfigBlade7SuperBlockFreqEntry 5}
--          apexRfConfigBlade7SubBlockFreqTable           OBJECT IDENTIFIER ::= {apexRfConfigBlade7 5}
--             apexRfConfigBlade7SubBlockFreqEntry                              {apexRfConfigBlade7SubBlockFreqTable 1}
--                apexRfConfigBlade7SubBlockFreqRfPortNum                       {apexRfConfigBlade7SubBlockFreqEntry 1}
--                apexRfConfigBlade7SubBlockFreqBlockNum                        {apexRfConfigBlade7SubBlockFreqEntry 2}
--                apexRfConfigBlade7SubBlockFreqAnnexB                          {apexRfConfigBlade7SubBlockFreqEntry 3}
--                apexRfConfigBlade7SubBlockFreqAnnexC                          {apexRfConfigBlade7SubBlockFreqEntry 4}
--                apexRfConfigBlade7SubBlockFreqAnnexA                          {apexRfConfigBlade7SubBlockFreqEntry 5}
--                apexRfConfigBlade7SubBlockChanSpacingAnnexA                   {apexRfConfigBlade7SubBlockFreqEntry 6}
--          apexRfConfigBlade7ChannelTable                OBJECT IDENTIFIER ::= {apexRfConfigBlade7 6}
--             apexRfConfigBlade7ChannelEntry                                   {apexRfConfigBlade7ChannelTable 1}
--                apexRfConfigBlade7ChannelRfPortNum                            {apexRfConfigBlade7ChannelEntry 1}
--                apexRfConfigBlade7ChannelChanNum                              {apexRfConfigBlade7ChannelEntry 2}
--                apexRfConfigBlade7ChannelFrequencyGridSelect                  {apexRfConfigBlade7ChannelEntry 3}
--                apexRfConfigBlade7ChannelModeComboSelectAnnexA                {apexRfConfigBlade7ChannelEntry 4}
--                apexRfConfigBlade7ChannelModeComboSelectAnnexB                {apexRfConfigBlade7ChannelEntry 5}
--                apexRfConfigBlade7ChannelModeComboSelectAnnexC                {apexRfConfigBlade7ChannelEntry 6}
--                apexRfConfigBlade7ChannelRfLevelAdjust                        {apexRfConfigBlade7ChannelEntry 7}
--                apexRfConfigBlade7ChannelTestMode                             {apexRfConfigBlade7ChannelEntry 8}
--                apexRfConfigBlade7ChannelMute                                 {apexRfConfigBlade7ChannelEntry 9}
         apexRfConfigBlade8                               OBJECT IDENTIFIER ::= {apexRfConfig 10}
            apexRfConfigBlade8General                     OBJECT IDENTIFIER ::= {apexRfConfigBlade8 1}
--          apexRfConfigBlade8ModesTable                  OBJECT IDENTIFIER ::= {apexRfConfigBlade8 2}
--             apexRfConfigBlade8ModesEntry                                     {apexRfConfigBlade8ModesTable 1}
--                apexRfConfigBlade8ModesIndex                                  {apexRfConfigBlade8ModesEntry 1}
--                apexRfConfigBlade8ModesModulationModeAnnexB                   {apexRfConfigBlade8ModesEntry 2}
--                apexRfConfigBlade8ModesInterleaverDepthAnnexB                 {apexRfConfigBlade8ModesEntry 3}
--                apexRfConfigBlade8ModesModulationModeAnnexA                   {apexRfConfigBlade8ModesEntry 4}
--                apexRfConfigBlade8ModesSymbolRateAnnexA                       {apexRfConfigBlade8ModesEntry 5}
--                apexRfConfigBlade8ModesModulationModeAnnexC                   {apexRfConfigBlade8ModesEntry 6}
--                apexRfConfigBlade8ModesSymbolRateAnnexC                       {apexRfConfigBlade8ModesEntry 7}
--          apexRfConfigBlade8RfPortTable                 OBJECT IDENTIFIER ::= {apexRfConfigBlade8 3}
--             apexRfConfigBlade8RfPortEntry                                    {apexRfConfigBlade8RfPortTable 1}
--                apexRfConfigBlade8RfPortNum                                   {apexRfConfigBlade8RfPortEntry 1}
--                apexRfConfigBlade8RfPortSpectrumInversion                     {apexRfConfigBlade8RfPortEntry 2}
--                apexRfConfigBlade8RfPortMute                                  {apexRfConfigBlade8RfPortEntry 3}
--                apexRfConfigBlade8RfPortRfLevel                               {apexRfConfigBlade8RfPortEntry 4}
--                apexRfConfigBlade8RfPortDiagSuppressMode                      {apexRfConfigBlade8RfPortEntry 5}
--                apexRfConfigBlade8RfPortDiagSuppressChannel                   {apexRfConfigBlade8RfPortEntry 6}
--                apexRfConfigBlade8RfPortNprimeMax                             {apexRfConfigBlade8RfPortEntry 7}
--                apexRfConfigBlade8RfPortNprimeMaxMode                         {apexRfConfigBlade8RfPortEntry 8}
--          apexRfConfigBlade8SuperBlockFreqTable         OBJECT IDENTIFIER ::= {apexRfConfigBlade8 4}
--             apexRfConfigBlade8SuperBlockFreqEntry                            {apexRfConfigBlade8SuperBlockFreqTable 1}
--                apexRfConfigBlade8SuperBlockFreqRfPortNum                     {apexRfConfigBlade8SuperBlockFreqEntry 1}
--                apexRfConfigBlade8SuperBlockFreqBlockNum                      {apexRfConfigBlade8SuperBlockFreqEntry 2}
--                apexRfConfigBlade8SuperBlockFreqAnnexB                        {apexRfConfigBlade8SuperBlockFreqEntry 3}
--                apexRfConfigBlade8SuperBlockFreqAnnexC                        {apexRfConfigBlade8SuperBlockFreqEntry 4}
--                apexRfConfigBlade8SuperBlockFreqAnnexA                        {apexRfConfigBlade8SuperBlockFreqEntry 5}
--          apexRfConfigBlade8SubBlockFreqTable           OBJECT IDENTIFIER ::= {apexRfConfigBlade8 5}
--             apexRfConfigBlade8SubBlockFreqEntry                              {apexRfConfigBlade8SubBlockFreqTable 1}
--                apexRfConfigBlade8SubBlockFreqRfPortNum                       {apexRfConfigBlade8SubBlockFreqEntry 1}
--                apexRfConfigBlade8SubBlockFreqBlockNum                        {apexRfConfigBlade8SubBlockFreqEntry 2}
--                apexRfConfigBlade8SubBlockFreqAnnexB                          {apexRfConfigBlade8SubBlockFreqEntry 3}
--                apexRfConfigBlade8SubBlockFreqAnnexC                          {apexRfConfigBlade8SubBlockFreqEntry 4}
--                apexRfConfigBlade8SubBlockFreqAnnexA                          {apexRfConfigBlade8SubBlockFreqEntry 5}
--                apexRfConfigBlade8SubBlockChanSpacingAnnexA                   {apexRfConfigBlade8SubBlockFreqEntry 6}
--          apexRfConfigBlade8ChannelTable                OBJECT IDENTIFIER ::= {apexRfConfigBlade8 6}
--             apexRfConfigBlade8ChannelEntry                                   {apexRfConfigBlade8ChannelTable 1}
--                apexRfConfigBlade8ChannelRfPortNum                            {apexRfConfigBlade8ChannelEntry 1}
--                apexRfConfigBlade8ChannelChanNum                              {apexRfConfigBlade8ChannelEntry 2}
--                apexRfConfigBlade8ChannelFrequencyGridSelect                  {apexRfConfigBlade8ChannelEntry 3}
--                apexRfConfigBlade8ChannelModeComboSelectAnnexA                {apexRfConfigBlade8ChannelEntry 4}
--                apexRfConfigBlade8ChannelModeComboSelectAnnexB                {apexRfConfigBlade8ChannelEntry 5}
--                apexRfConfigBlade8ChannelModeComboSelectAnnexC                {apexRfConfigBlade8ChannelEntry 6}
--                apexRfConfigBlade8ChannelRfLevelAdjust                        {apexRfConfigBlade8ChannelEntry 7}
--                apexRfConfigBlade8ChannelTestMode                             {apexRfConfigBlade8ChannelEntry 8}
--                apexRfConfigBlade8ChannelMute                                 {apexRfConfigBlade8ChannelEntry 9}
--       apexRfConfigRfLevelThresholdTable                OBJECT IDENTIFIER ::= {apexRfConfig 11}
--          apexRfConfigRfLevelThresholdEntry                                   {apexRfConfigRfLevelThresholdTable 1}
--             apexRfConfigRfLevelThresholdBladeNum                             {apexRfConfigRfLevelThresholdEntry 1}
--             apexRfConfigRfLevelThresholdLow                                  {apexRfConfigRfLevelThresholdEntry 2}
--             apexRfConfigRfLevelThresholdHigh                                 {apexRfConfigRfLevelThresholdEntry 3}
      apexRfStatus                                        OBJECT IDENTIFIER ::= {apexRf 2}
         apexRfStatusGeneral                              OBJECT IDENTIFIER ::= {apexRfStatus 1}
--          apexRfStatusTransmissionMode                                        {apexRfStatusGeneral 1}
--       apexRfStatusFrequencyGridTable                                         {apexRfStatus 2}
--          apexRfStatusFrequencyGridEntry                                      {apexRfStatusFrequencyGridTable 1}
--             apexRfStatusFrequencyGridBladeNum                                {apexRfStatusFrequencyGridEntry 1}
--             apexRfStatusFrequencyGridRfPortNum                               {apexRfStatusFrequencyGridEntry 2}
--             apexRfStatusFrequencyGridIndex                                   {apexRfStatusFrequencyGridEntry 3}
--             apexRfStatusFrequencyGridFrequency                               {apexRfStatusFrequencyGridEntry 4}
--       apexRfStatusRfPortTable                                                {apexRfStatus 3}
--          apexRfStatusRfPortEntry                                             {apexRfStatusRfPortTable 1}
--             apexRfStatusRfPortBladeNum                                       {apexRfStatusRfPortEntry 1}
--             apexRfStatusRfPortNum                                            {apexRfStatusRfPortEntry 2}
--             apexRfStatusRfPortMute                                           {apexRfStatusRfPortEntry 3}
--             apexRfStatusRfPortRfLevelNominal                                 {apexRfStatusRfPortEntry 4}
--             apexRfStatusRfPortRfLevelSet                                     {apexRfStatusRfPortEntry 5}
--             apexRfStatusRfPortSpectrumInversion                              {apexRfStatusRfPortEntry 6}
--             apexRfStatusRfPortDiagSuppressMode                               {apexRfStatusRfPortEntry 7}
--             apexRfStatusRfPortDiagSuppressChannel                            {apexRfStatusRfPortEntry 8}
--             apexRfStatusRfPortNprimeMax                                      {apexRfStatusRfPortEntry 9}
--       apexRfStatusChannelTable                                               {apexRfStatus 4}
--          apexRfStatusChannelEntry                                            {apexRfStatusChannelTable 1}
--             apexRfStatusChannelBladeNum                                      {apexRfStatusChannelEntry 1}
--             apexRfStatusChannelRfPortNum                                     {apexRfStatusChannelEntry 2}
--             apexRfStatusChannelChanNum                                       {apexRfStatusChannelEntry 3}
--             apexRfStatusChannelFrequency                                     {apexRfStatusChannelEntry 4}
--             apexRfStatusChannelModulationMode                                {apexRfStatusChannelEntry 5}
--             apexRfStatusChannelSymbolRate                                    {apexRfStatusChannelEntry 6}
--             apexRfStatusChannelInformationRate                               {apexRfStatusChannelEntry 7}
--             apexRfStatusChannelInterleaverDepth                              {apexRfStatusChannelEntry 8}
--             apexRfStatusChannelRfLevelSet                                    {apexRfStatusChannelEntry 9}
--             apexRfStatusChannelOutputMode                                    {apexRfStatusChannelEntry 10}
--       apexRfStatusChannelActiveTable                                         {apexRfStatus 5}
--          apexRfStatusChannelActiveEntry                                      {apexRfStatusChannelActiveTable 1}
--             apexRfStatusChannelActiveBladeNum                                {apexRfStatusChannelActiveEntry 1}
--             apexRfStatusChannelActiveRfPortNum                               {apexRfStatusChannelActiveEntry 2}
--             apexRfStatusChannelActiveChanNum                                 {apexRfStatusChannelActiveEntry 3}
--             apexRfStatusChannelActive                                        {apexRfStatusChannelActiveEntry 4}
--       apexRfStatusChannelAvailableTable                                      {apexRfStatus 6}
--          apexRfStatusChannelAvailableEntry                                   {apexRfStatusChannelAvailableTable 1}
--             apexRfStatusChannelAvailableBladeNum                             {apexRfStatusChannelAvailableEntry 1}
--             apexRfStatusChannelAvailableRfPortNum                            {apexRfStatusChannelAvailableEntry 2}
--             apexRfStatusChannelAvailableChanNum                              {apexRfStatusChannelAvailableEntry 3}
--             apexRfStatusChannelAvailable                                     {apexRfStatusChannelAvailableEntry 4}
--       apexRfErrorRfPortTable                                                 {apexRfStatus 7}
--          apexRfErrorRfPortEntry                                              {apexRfErrorRfPortTable 1}
--             apexRfErrorRfPortBladeNum                                        {apexRfErrorRfPortEntry 1}
--             apexRfErrorRfPortRfPortNum                                       {apexRfErrorRfPortEntry 2}
--             apexRfErrorRfPortFaultCondition                                  {apexRfErrorRfPortEntry 3}
--             apexRfErrorRfPortChannelFaultSummary                             {apexRfErrorRfPortEntry 4}
--             apexRfErrorRfPortRfLevelBlade                                    {apexRfErrorRfPortEntry 5}
--             apexRfErrorRfPortRfLevelSwitch                                   {apexRfErrorRfPortEntry 6}
--             apexRfErrorRfPortDataError                                       {apexRfErrorRfPortEntry 7}
--             apexRfErrorRfPortChannelsInError                                 {apexRfErrorRfPortEntry 8}
--             apexRfErrorRfPortSwitchError                                     {apexRfErrorRfPortEntry 9}
--       apexRfErrorChannelTable                                                {apexRfStatus 8}
--          apexRfErrorChannelEntry                                             {apexRfErrorChannelTable 1}
--             apexRfErrorChannelBladeNum                                       {apexRfErrorChannelEntry 1}
--             apexRfErrorChannelRfPortNum                                      {apexRfErrorChannelEntry 2}
--             apexRfErrorChannelChanNum                                        {apexRfErrorChannelEntry 3}
--             apexRfErrorChannelFaultCondition                                 {apexRfErrorChannelEntry 4}
--             apexRfErrorChannelDataError                                      {apexRfErrorChannelEntry 5}
--       apexRfStatusRfPortLevelTable                                           {apexRfStatus 9}
--          apexRfStatusRfPortLevelEntry                                        {apexRfStatusRfPortLevelTable 1}
--             apexRfStatusRfPortLevelBladeNum                                  {apexRfStatusRfPortLevelEntry 1}
--             apexRfStatusRfPortLevelRfNum                                     {apexRfStatusRfPortLevelEntry 2}
--             apexRfStatusRfPortLevelReadBlade                                 {apexRfStatusRfPortLevelEntry 3}
--             apexRfStatusRfPortLevelReadSwitch                                {apexRfStatusRfPortLevelEntry 4}
--       apexRfStatusRfCountsTable                                              {apexRfStatus 10}
--          apexRfStatusRfCountsEntry                                           {apexRfStatusRfCountsTable 1}
--             apexRfStatusRfCountsBladeNum                                     {apexRfStatusRfPortEntry 1}
--             apexRfStatusRfCountsRfNum                                        {apexRfStatusRfPortEntry 2}
--             apexRfStatusRfCountsChannelsAssignable                           {apexRfStatusRfPortEntry 3}
--             apexRfStatusRfCountsChannelsAssigned                             {apexRfStatusRfPortEntry 4}
--             apexRfStatusRfCountsChannelsActive                               {apexRfStatusRfPortEntry 5}
--             apexRfStatusRfCountsChannelsMuted                                {apexRfStatusRfPortEntry 6}
--             apexRfStatusRfCountsChannelsTestMode                             {apexRfStatusRfPortEntry 7}
--             apexRfStatusRfCountsChannelsAvailable                            {apexRfStatusRfPortEntry 8}
   apexSessionControl                                     OBJECT IDENTIFIER ::= {apex3000 9}
      apexSessionControlConfig                            OBJECT IDENTIFIER ::= {apexSessionControl 1}
         apexSessionControlConfigGeneral                  OBJECT IDENTIFIER ::= {apexSessionControlConfig 1}
--          apexSesContConfProtocol                                             {apexSessionControlConfigGeneral 1}
--          apexSesContConfTableApplyChange                                     {apexSessionControlConfigGeneral 2}
--          apexSesContConfInputPreEncryptCheck                                 {apexSessionControlConfigGeneral 3}
--          apexSesContConfFollowDtcp                                           {apexSessionControlConfigGeneral 4}
--          apexSesContConfReportUdpMappings                                    {apexSessionControlConfigGeneral 5}
--       apexSesContBlade1ConfTable                                             {apexSessionControlConfig 2}
--          apexSesContBlade1ConfEntry                                          {apexSesContBlade1ConfTable 1}
--          apexSesContBlade1ConfOutputTsNum                                    {apexSesContBlade1ConfEntry 1}
--          apexSesContBlade1ConfGbePrimaryInterface                            {apexSesContBlade1ConfEntry 2}
--          apexSesContBlade1ConfGbeSecondaryInterface                          {apexSesContBlade1ConfEntry 3}
--          apexSesContBlade1ConfQamDeviceIndex                                 {apexSesContBlade1ConfEntry 4}
--          apexSesContBlade1ConfCmdOutputPort                                  {apexSesContBlade1ConfEntry 5}
--       apexSesContBlade2ConfTable                                             {apexSessionControlConfig 3}
--          apexSesContBlade2ConfEntry                                          {apexSesContBlade2ConfTable 1}
--          apexSesContBlade2ConfOutputTsNum                                    {apexSesContBlade2ConfEntry 1}
--          apexSesContBlade2ConfGbePrimaryInterface                            {apexSesContBlade2ConfEntry 2}
--          apexSesContBlade2ConfGbeSecondaryInterface                          {apexSesContBlade2ConfEntry 3}
--          apexSesContBlade2ConfQamDeviceIndex                                 {apexSesContBlade2ConfEntry 4}
--          apexSesContBlade2ConfCmdOutputPort                                  {apexSesContBlade2ConfEntry 5}
--       apexSesContBlade3ConfTable                                             {apexSessionControlConfig 4}
--          apexSesContBlade3ConfEntry                                          {apexSesContBlade3ConfTable 1}
--          apexSesContBlade3ConfOutputTsNum                                    {apexSesContBlade3ConfEntry 1}
--          apexSesContBlade3ConfGbePrimaryInterface                            {apexSesContBlade3ConfEntry 2}
--          apexSesContBlade3ConfGbeSecondaryInterface                          {apexSesContBlade3ConfEntry 3}
--          apexSesContBlade3ConfQamDeviceIndex                                 {apexSesContBlade3ConfEntry 4}
--          apexSesContBlade3ConfCmdOutputPort                                  {apexSesContBlade3ConfEntry 5}
--       apexSesContBlade4ConfTable                                             {apexSessionControlConfig 5}
--          apexSesContBlade4ConfEntry                                          {apexSesContBlade4ConfTable 1}
--          apexSesContBlade4ConfOutputTsNum                                    {apexSesContBlade4ConfEntry 1}
--          apexSesContBlade4ConfGbePrimaryInterface                            {apexSesContBlade4ConfEntry 2}
--          apexSesContBlade4ConfGbeSecondaryInterface                          {apexSesContBlade4ConfEntry 3}
--          apexSesContBlade4ConfQamDeviceIndex                                 {apexSesContBlade4ConfEntry 4}
--          apexSesContBlade4ConfCmdOutputPort                                  {apexSesContBlade4ConfEntry 5}
--       apexSesContBlade5ConfTable                                             {apexSessionControlConfig 6}
--          apexSesContBlade5ConfEntry                                          {apexSesContBlade5ConfTable 1}
--          apexSesContBlade5ConfOutputTsNum                                    {apexSesContBlade5ConfEntry 1}
--          apexSesContBlade5ConfGbePrimaryInterface                            {apexSesContBlade5ConfEntry 2}
--          apexSesContBlade5ConfGbeSecondaryInterface                          {apexSesContBlade5ConfEntry 3}
--          apexSesContBlade5ConfQamDeviceIndex                                 {apexSesContBlade5ConfEntry 4}
--          apexSesContBlade5ConfCmdOutputPort                                  {apexSesContBlade5ConfEntry 5}
--       apexSesContBlade6ConfTable                                             {apexSessionControlConfig 7}
--          apexSesContBlade6ConfEntry                                          {apexSesContBlade6ConfTable 1}
--          apexSesContBlade6ConfOutputTsNum                                    {apexSesContBlade6ConfEntry 1}
--          apexSesContBlade6ConfGbePrimaryInterface                            {apexSesContBlade6ConfEntry 2}
--          apexSesContBlade6ConfGbeSecondaryInterface                          {apexSesContBlade6ConfEntry 3}
--          apexSesContBlade6ConfQamDeviceIndex                                 {apexSesContBlade6ConfEntry 4}
--          apexSesContBlade6ConfCmdOutputPort                                  {apexSesContBlade6ConfEntry 5}
--       apexSesContBlade7ConfTable                                             {apexSessionControlConfig 8}
--          apexSesContBlade7ConfEntry                                          {apexSesContBlade7ConfTable 1}
--          apexSesContBlade7ConfOutputTsNum                                    {apexSesContBlade7ConfEntry 1}
--          apexSesContBlade7ConfGbePrimaryInterface                            {apexSesContBlade7ConfEntry 2}
--          apexSesContBlade7ConfGbeSecondaryInterface                          {apexSesContBlade7ConfEntry 3}
--          apexSesContBlade7ConfQamDeviceIndex                                 {apexSesContBlade7ConfEntry 4}
--          apexSesContBlade7ConfCmdOutputPort                                  {apexSesContBlade7ConfEntry 5}
--       apexSesContBlade8ConfTable                                             {apexSessionControlConfig 9}
--          apexSesContBlade8ConfEntry                                          {apexSesContBlade8ConfTable 1}
--          apexSesContBlade8ConfOutputTsNum                                    {apexSesContBlade8ConfEntry 1}
--          apexSesContBlade8ConfGbePrimaryInterface                            {apexSesContBlade8ConfEntry 2}
--          apexSesContBlade8ConfGbeSecondaryInterface                          {apexSesContBlade8ConfEntry 3}
--          apexSesContBlade8ConfQamDeviceIndex                                 {apexSesContBlade8ConfEntry 4}
--          apexSesContBlade8ConfCmdOutputPort                                  {apexSesContBlade8ConfEntry 5}
      apexSessionControlStatus                            OBJECT IDENTIFIER ::= {apexSessionControl 2}
         apexSessionControlStatusGeneral                  OBJECT IDENTIFIER ::= {apexSessionControlStatus 1}
--          apexSesContStatusTableApplyText                                     {apexSessionControlStatusGeneral 1}
--          apexSesContStatusReportUdpMapApplyText                              {apexSessionControlStatusGeneral 2}
      apexRpc                                             OBJECT IDENTIFIER ::= {apexSessionControl 3}
         apexRpcConfig                                    OBJECT IDENTIFIER ::= {apexRpc 1}
            apexRpcConfigGeneral                          OBJECT IDENTIFIER ::= {apexRpcConfig 1}
--             apexRpcDataCarouselProgram                                       {apexRpcConfigGeneral 1}
--             apexRpcReportAllSessions                                         {apexRpcConfigGeneral 2}
--             apexRpcDeviceName                                                {apexRpcConfigGeneral 3}
--             apexRpcDeviceType                                                {apexRpcConfigGeneral 4}
--             apexRpcControlInterface                                          {apexRpcConfigGeneral 5}
--             apexRpcNumShellSessions                                          {apexRpcConfigGeneral 6}
--             apexRpcAvgBandwidthEnable                                        {apexRpcConfigGeneral 7}
--             apexRpcApplyChange                                               {apexRpcConfigGeneral 8}
--             apexRpcTeardownSessions                                          {apexRpcConfigGeneral 9}
--             apexRpcIncludeGenericQamDevices                                  {apexRpcConfigGeneral 10}
--             apexRpcReportSessionInfoPmt                                      {apexRpcConfigGeneral 11}
--             apexRpcEdgeAnnounceEnable                                        {apexRpcConfigGeneral 12}
            apexRpcBlade1Config                           OBJECT IDENTIFIER ::= {apexRpcConfig 2}
--             apexRpcBlade1RfPortTable                                         {apexRpcBlade1Config 1}
--                apexRpcBlade1RfPortEntry                                      {apexRpcBlade1RfPortTable 1}
--                   apexRpcBlade1RfPortNum                                     {apexRpcBlade1RfPortEntry 1}
--                   apexRpcBlade1RfPortName                                    {apexRpcBlade1RfPortEntry 2}
--                   apexRpcBlade1RfPortServiceGroup                            {apexRpcBlade1RfPortEntry 3}
--             apexRpcBlade1RfChannelTable                                      {apexRpcBlade1Config 2}
--                apexRpcBlade1RfChannelEntry                                   {apexRpcBlade1RfChannelTable 1}
--                   apexRpcBlade1RfChannelNum                                  {apexRpcBlade1RfChannelEntry 1}
--                   apexRpcBlade1RfChannelName                                 {apexRpcBlade1RfChannelEntry 2}
            apexRpcBlade2Config                           OBJECT IDENTIFIER ::= {apexRpcConfig 3}
--             apexRpcBlade2RfPortTable                                         {apexRpcBlade2Config 1}
--                apexRpcBlade2RfPortEntry                                      {apexRpcBlade2RfPortTable 1}
--                   apexRpcBlade2RfPortNum                                     {apexRpcBlade2RfPortEntry 1}
--                   apexRpcBlade2RfPortName                                    {apexRpcBlade2RfPortEntry 2}
--                   apexRpcBlade2RfPortServiceGroup                            {apexRpcBlade2RfPortEntry 3}
--             apexRpcBlade2RfChannelTable                                      {apexRpcBlade2Config 2}
--                apexRpcBlade2RfChannelEntry                                   {apexRpcBlade2RfChannelTable 1}
--                   apexRpcBlade2RfChannelNum                                  {apexRpcBlade2RfChannelEntry 1}
--                   apexRpcBlade2RfChannelName                                 {apexRpcBlade2RfChannelEntry 2}
            apexRpcBlade3Config                           OBJECT IDENTIFIER ::= {apexRpcConfig 4}
--             apexRpcBlade3RfPortTable                                         {apexRpcBlade3Config 1}
--                apexRpcBlade3RfPortEntry                                      {apexRpcBlade3RfPortTable 1}
--                   apexRpcBlade3RfPortNum                                     {apexRpcBlade3RfPortEntry 1}
--                   apexRpcBlade3RfPortName                                    {apexRpcBlade3RfPortEntry 2}
--                   apexRpcBlade3RfPortServiceGroup                            {apexRpcBlade3RfPortEntry 3}
--             apexRpcBlade3RfChannelTable                                      {apexRpcBlade3Config 2}
--                apexRpcBlade3RfChannelEntry                                   {apexRpcBlade3RfChannelTable 1}
--                   apexRpcBlade3RfChannelNum                                  {apexRpcBlade3RfChannelEntry 1}
--                   apexRpcBlade3RfChannelName                                 {apexRpcBlade3RfChannelEntry 2}
            apexRpcBlade4Config                           OBJECT IDENTIFIER ::= {apexRpcConfig 5}
--             apexRpcBlade4RfPortTable                                         {apexRpcBlade4Config 1}
--                apexRpcBlade4RfPortEntry                                      {apexRpcBlade4RfPortTable 1}
--                   apexRpcBlade4RfPortNum                                     {apexRpcBlade4RfPortEntry 1}
--                   apexRpcBlade4RfPortName                                    {apexRpcBlade4RfPortEntry 2}
--                   apexRpcBlade4RfPortServiceGroup                            {apexRpcBlade4RfPortEntry 3}
--             apexRpcBlade4RfChannelTable                                      {apexRpcBlade4Config 2}
--                apexRpcBlade4RfChannelEntry                                   {apexRpcBlade4RfChannelTable 1}
--                   apexRpcBlade4RfChannelNum                                  {apexRpcBlade4RfChannelEntry 1}
--                   apexRpcBlade4RfChannelName                                 {apexRpcBlade4RfChannelEntry 2}
            apexRpcBlade5Config                           OBJECT IDENTIFIER ::= {apexRpcConfig 6}
--             apexRpcBlade5RfPortTable                                         {apexRpcBlade5Config 1}
--                apexRpcBlade5RfPortEntry                                      {apexRpcBlade5RfPortTable 1}
--                   apexRpcBlade5RfPortNum                                     {apexRpcBlade5RfPortEntry 1}
--                   apexRpcBlade5RfPortName                                    {apexRpcBlade5RfPortEntry 2}
--                   apexRpcBlade5RfPortServiceGroup                            {apexRpcBlade5RfPortEntry 3}
--             apexRpcBlade5RfChannelTable                                      {apexRpcBlade5Config 2}
--                apexRpcBlade5RfChannelEntry                                   {apexRpcBlade5RfChannelTable 1}
--                   apexRpcBlade5RfChannelNum                                  {apexRpcBlade5RfChannelEntry 1}
--                   apexRpcBlade5RfChannelName                                 {apexRpcBlade5RfChannelEntry 2}
            apexRpcBlade6Config                           OBJECT IDENTIFIER ::= {apexRpcConfig 7}
--             apexRpcBlade6RfPortTable                                         {apexRpcBlade6Config 1}
--                apexRpcBlade6RfPortEntry                                      {apexRpcBlade6RfPortTable 1}
--                   apexRpcBlade6RfPortNum                                     {apexRpcBlade6RfPortEntry 1}
--                   apexRpcBlade6RfPortName                                    {apexRpcBlade6RfPortEntry 2}
--                   apexRpcBlade6RfPortServiceGroup                            {apexRpcBlade6RfPortEntry 3}
--             apexRpcBlade6RfChannelTable                                      {apexRpcBlade6Config 2}
--                apexRpcBlade6RfChannelEntry                                   {apexRpcBlade6RfChannelTable 1}
--                   apexRpcBlade6RfChannelNum                                  {apexRpcBlade6RfChannelEntry 1}
--                   apexRpcBlade6RfChannelName                                 {apexRpcBlade6RfChannelEntry 2}
            apexRpcBlade7Config                           OBJECT IDENTIFIER ::= {apexRpcConfig 8}
--             apexRpcBlade7RfPortTable                                         {apexRpcBlade7Config 1}
--                apexRpcBlade7RfPortEntry                                      {apexRpcBlade7RfPortTable 1}
--                   apexRpcBlade7RfPortNum                                     {apexRpcBlade7RfPortEntry 1}
--                   apexRpcBlade7RfPortName                                    {apexRpcBlade7RfPortEntry 2}
--                   apexRpcBlade7RfPortServiceGroup                            {apexRpcBlade7RfPortEntry 3}
--             apexRpcBlade7RfChannelTable                                      {apexRpcBlade7Config 2}
--                apexRpcBlade7RfChannelEntry                                   {apexRpcBlade7RfChannelTable 1}
--                   apexRpcBlade7RfChannelNum                                  {apexRpcBlade7RfChannelEntry 1}
--                   apexRpcBlade7RfChannelName                                 {apexRpcBlade7RfChannelEntry 2}
            apexRpcBlade8Config                           OBJECT IDENTIFIER ::= {apexRpcConfig 9}
--             apexRpcBlade8RfPortTable                                         {apexRpcBlade8Config 1}
--                apexRpcBlade8RfPortEntry                                      {apexRpcBlade8RfPortTable 1}
--                   apexRpcBlade8RfPortNum                                     {apexRpcBlade8RfPortEntry 1}
--                   apexRpcBlade8RfPortName                                    {apexRpcBlade8RfPortEntry 2}
--                   apexRpcBlade8RfPortServiceGroup                            {apexRpcBlade8RfPortEntry 3}
--             apexRpcBlade8RfChannelTable                                      {apexRpcBlade8Config 2}
--                apexRpcBlade8RfChannelEntry                                   {apexRpcBlade8RfChannelTable 1}
--                   apexRpcBlade8RfChannelNum                                  {apexRpcBlade8RfChannelEntry 1}
--                   apexRpcBlade8RfChannelName                                 {apexRpcBlade8RfChannelEntry 2}
         apexRpcStatus                                    OBJECT IDENTIFIER ::= {apexRpc 2}
            apexRpcStatusGeneral                          OBJECT IDENTIFIER ::= {apexRpcStatus 1}
--          apexRpcSessionStatTable                                             {apexRpcStatus 2}
--             apexRpcSessionStatEntry                                          {apexRpcSessionStatTable 1}
--                apexRpcSessionStatBladeNum                                    {apexRpcSessionStatEntry 1}
--                apexRpcSessionStatIndex                                       {apexRpcSessionStatEntry 2}
--                apexRpcSessionStatInputTsIndex                                {apexRpcSessionStatEntry 3}
--                apexRpcSessionStatInputProgramNum                             {apexRpcSessionStatEntry 4}
--                apexRpcSessionStatSourceIpAddr3                               {apexRpcSessionStatEntry 5}
--                apexRpcSessionStatOutputQamChannel                            {apexRpcSessionStatEntry 6}
--                apexRpcSessionStatOutputProgramNum                            {apexRpcSessionStatEntry 7}
--                apexRpcSessionStatProgramBandwidth                            {apexRpcSessionStatEntry 8}
--                apexRpcSessionStatSessionType                                 {apexRpcSessionStatEntry 9}
--                apexRpcSessionStatSessionIdWord1                              {apexRpcSessionStatEntry 10}
--                apexRpcSessionStatSessionIdWord2                              {apexRpcSessionStatEntry 11}
--                apexRpcSessionStatSessionIdWord3                              {apexRpcSessionStatEntry 12}
--                apexRpcSessionStatManagerIpAddr                               {apexRpcSessionStatEntry 13}
--                apexRpcSessionStatCmdOutputPort                               {apexRpcSessionStatEntry 14}
--          apexRpcQamStatTable                                                 {apexRpcStatus 3}
--             apexRpcQamStatEntry                                              {apexRpcQamStatTable 1}
--                apexRpcQamStatQamChannelBladeNum                              {apexRpcQamStatEntry 1}
--                apexRpcQamStatQamChannelOtsNum                                {apexRpcQamStatEntry 2}
--                apexRpcQamStatNumSdvSessions                                  {apexRpcQamStatEntry 3}
--                apexRpcQamStatNumVodBcSessions                                {apexRpcQamStatEntry 4}
--                apexRpcQamStatSdvGroupBandwidth                               {apexRpcQamStatEntry 5}
--                apexRpcQamStatTotalInUseBandwidth                             {apexRpcQamStatEntry 6}
--          apexRpcSessionInputInfoStatTable                                    {apexRpcStatus 4}
--             apexRpcSessionInputInfoStatEntry                                 {apexRpcSessionInputInfoStatTable 1}
--                apexRpcSessionInputInfoStatBladeNum                           {apexRpcSessionInputInfoStatEntry 1}
--                apexRpcSessionInputInfoStatIndex                              {apexRpcSessionInputInfoStatEntry 2}
--                apexRpcSessionInputInfoStatPri                                {apexRpcSessionInputInfoStatEntry 3}
--                apexRpcSessionInputInfoStatSec                                {apexRpcSessionInputInfoStatEntry 4}
--          apexRpcSetupFailureStatTable                                        {apexRpcStatus 5}
--             apexRpcSetupFailureStatEntry                                     {apexRpcSetupFailureStatTable 1}
--                apexRpcSetupFailureStatBladeNum                               {apexRpcSetupFailureStatEntry 1}
--                apexRpcSetupFailureStatCount                                  {apexRpcSetupFailureStatEntry 2}
      apexRtsp                                            OBJECT IDENTIFIER ::= {apexSessionControl 4}
         apexRtspConfig                                   OBJECT IDENTIFIER ::= {apexRtsp 1}
            apexRtspConfigGeneral                         OBJECT IDENTIFIER ::= {apexRtspConfig 1}
            apexRtspConfController                        OBJECT IDENTIFIER ::= {apexRtspConfig 2}
--             apexRtspConfControllerApplyChange                                {apexRtspConfController 1}
--             apexRtspConfControllerIp                                         {apexRtspConfController 2}
--             apexRtspConfControllerPort                                       {apexRtspConfController 3}
--             apexRtspConfControllerHoldTime                                   {apexRtspConfController 4}
--             apexRtspConfControllerBandwidthDelta                             {apexRtspConfController 5}
--             apexRtspConfControllerStreamingZone                              {apexRtspConfController 6}
--             apexRtspConfControllerDeviceName                                 {apexRtspConfController 7}
--             apexRtspConfControllerSdvEdgeEncryption                          {apexRtspConfController 8}
--             apexRtspConfControllerDefaultServiceProviderId                   {apexRtspConfController 9}
--             apexRtspConfControllerDisableAnnounceMsg                         {apexRtspConfController 10}
--             apexRtspConfControllerTeardownSessions                           {apexRtspConfController 11}
--             apexRtspConfControllerNextHopServerInterface                     {apexRtspConfController 12}
--             apexRtspConfControllerVendorName                                 {apexRtspConfController 13}
--          apexRtspConfQamChannelApplyTable                                    {apexRtspConfig 3}
--             apexRtspConfQamChannelApplyEntry                                 {apexRtspConfQamChannelApplyTable 1}
--                apexRtspConfQamChannelApplyBladeNum                           {apexRtspConfQamChannelApplyEntry 1}
--                apexRtspConfQamChannelApplyOtsNum                             {apexRtspConfQamChannelApplyEntry 2}
--                apexRtspConfQamChannelApplyChange                             {apexRtspConfQamChannelApplyEntry 3}
--          apexRtspConfQamChannelTable                                         {apexRtspConfig 4}
--             apexRtspConfQamChannelEntry                                      {apexRtspConfQamChannelTable 1}
--                apexRtspConfQamChannelBladeNum                                {apexRtspConfQamChannelEntry 1}
--                apexRtspConfQamChannelOtsNum                                  {apexRtspConfQamChannelEntry 2}
--                apexRtspConfQamChannelGroupName                               {apexRtspConfQamChannelEntry 3}
--          apexRtspConfGbeEdgeGroupTable                                       {apexRtspConfig 5}
--             apexRtspConfGbeEdgeGroupEntry                                    {apexRtspConfGbeEdgeGroupTable 1}
--                apexRtspConfGbeEdgeGroupNum                                   {apexRtspConfGbeEdgeGroupEntry 1}
--                apexRtspConfGbeEdgeGroupName                                  {apexRtspConfGbeEdgeGroupEntry 2}
            apexRtspConfMha                               OBJECT IDENTIFIER ::= {apexRtspConfig 6}
--             apexRtspConfMhaAddressDomain                                     {apexRtspConfMha 1}
--             apexRtspConfMhaPort                                              {apexRtspConfMha 2}
            apexRtspConfMhaSbe                            OBJECT IDENTIFIER ::= {apexRtspConfig 7}
--             apexRtspConfMhaSbeEncryptionMode                                 {apexRtspConfMhaSbe 1}
--             apexRtspConfMhaSbeCciLevel                                       {apexRtspConfMhaSbe 2}
--             apexRtspConfMhaSbeApsLevel                                       {apexRtspConfMhaSbe 3}
--             apexRtspConfMhaSbeCitSetting                                     {apexRtspConfMhaSbe 4}
--             apexRtspConfMhaSbeApplyChange                                    {apexRtspConfMhaSbe 5}
         apexRtspStatus                                   OBJECT IDENTIFIER ::= {apexRtsp 2}
            apexRtspStatusGeneral                         OBJECT IDENTIFIER ::= {apexRtspStatus 1}
--             apexRtspStatusSetupRequestRate                                   {apexRtspStatusGeneral 1}
--             apexRtspStatusTeardownRate                                       {apexRtspStatusGeneral 2}
--             apexRtspStatusAnnounceRequestRate                                {apexRtspStatusGeneral 3}
--             apexRtspStatusAckRate                                            {apexRtspStatusGeneral 4}
--             apexRtspStatusSessionCount                                       {apexRtspStatusGeneral 5}
--          apexRtspSessionStatTable                                            {apexRtspStatus 2}
--             apexRtspSessionStatEntry                                         {apexRtspSessionStatTable 1}
--                apexRtspSessionStatBladeNum                                   {apexRtspSessionStatEntry 1}
--                apexRtspSessionStatIndex                                      {apexRtspSessionStatEntry 2}
--                apexRtspSessionStatInputTsIndex                               {apexRtspSessionStatEntry 3}
--                apexRtspSessionStatInputProgramNum                            {apexRtspSessionStatEntry 4}
--                apexRtspSessionStatOutputQamChannel                           {apexRtspSessionStatEntry 5}
--                apexRtspSessionStatOutputProgramNum                           {apexRtspSessionStatEntry 6}
--                apexRtspSessionStatProgramBandwidth                           {apexRtspSessionStatEntry 7}
--                apexRtspSessionStatManagerIpAddr                              {apexRtspSessionStatEntry 8}
--          apexRtspSessionIdTable                                              {apexRtspStatus 3}
--             apexRtspSessionIdEntry                                           {apexRtspSessionIdTable 1}
--                apexRtspSessionIdBladeNum                                     {apexRtspSessionIdEntry 1}
--                apexRtspSessionIdIndex                                        {apexRtspSessionIdEntry 2}
--                apexRtspSessionId                                             {apexRtspSessionIdEntry 3}
--          apexRtspQamStatTable                                                {apexRtspStatus 4}
--             apexRtspQamStatEntry                                             {apexRtspQamStatTable 1}
--                apexRtspQamStatQamChannelBladeNum                             {apexRtspQamStatEntry 1}
--                apexRtspQamStatQamChannelOtsNum                               {apexRtspQamStatEntry 2}
--                apexRtspQamStatNumSessions                                    {apexRtspQamStatEntry 3}
--                apexRtspQamStatAllocatedBandwidth                             {apexRtspQamStatEntry 4}
            apexRtspStatController                        OBJECT IDENTIFIER ::= {apexRtspStatus 5}
--                apexRtspStatControllerDiscovery                               {apexRtspStatControllerEntry 1}
--                apexRtspStatControllerConnection                              {apexRtspStatControllerEntry 2}
--                apexRtspStatControllerCommFault                               {apexRtspStatControllerEntry 3}
--          apexRtspStatQamChannelTable                                         {apexRtspStatus 6}
--             apexRtspStatQamChannelEntry                                      {apexRtspStatQamChannelTable 1}
--                apexRtspStatQamChannelBladeNum                                {apexRtspStatQamChannelEntry 1}
--                apexRtspStatQamChannelOtsNum                                  {apexRtspStatQamChannelEntry 2}
--                apexRtspStatQamChannelName                                    {apexRtspStatQamChannelEntry 3}
--          apexRtspStatQamMptsModeTable                                        {apexRtspStatus 7}
--             apexRtspStatQamMptsModeEntry                                     {apexRtspStatQamMptsModeTable 1}
--                apexRtspStatQamMptsModeBladeNum                               {apexRtspStatQamMptsModeEntry 1}
--                apexRtspStatQamMptsModeOtsNum                                 {apexRtspStatQamMptsModeEntry 2}
--                apexRtspStatQamMptsModeQamChannelMode                         {apexRtspStatQamMptsModeEntry 3}
--          apexRtspSessionInputInfoStatTable                                   {apexRtspStatus 8}
--             apexRtspSessionInputInfoStatEntry                                {apexRtspSessionInputInfoStatTable 1}
--                apexRtspSessionInputInfoStatBladeNum                          {apexRtspSessionInputInfoStatEntry 1}
--                apexRtspSessionInputInfoStatIndex                             {apexRtspSessionInputInfoStatEntry 2}
--                apexRtspSessionInputInfoStatPri                               {apexRtspSessionInputInfoStatEntry 3}
--                apexRtspSessionInputInfoStatSec                               {apexRtspSessionInputInfoStatEntry 4}
--          apexRtspStatBwReportedTable                                         {apexRtspStatus 9}
--             apexRtspStatBwReportedEntry                                      {apexRtspStatBwReportedTable 1}
--                apexRtspStatBwReportedGbePortNum                              {apexRtspStatBwReportedEntry 1}
--                apexRtspStatBwReportedAvailableBw                             {apexRtspStatBwReportedEntry 2}
--                apexRtspStatBwReportedSentToErm                               {apexRtspStatBwReportedEntry 3}
--                apexRtspStatBwReportedRsrvUdpMap                              {apexRtspStatBwReportedEntry 4}
--                apexRtspStatBwReportedRsrvRpcOnly                             {apexRtspStatBwReportedEntry 5}
--                apexRtspStatBwReportedRsrvDepiMap                             {apexRtspStatBwReportedEntry 6}
--          apexRtspStatBladeBwTable                                            {apexRtspStatus 10}
--             apexRtspStatBladeBwEntry                                         {apexRtspStatBladeBwTable 1}
--                apexRtspStatBladeBwBladeNum                                   {apexRtspStatBladeBwEntry 1}
--                apexRtspStatBladeBwManualRoute                                {apexRtspStatBladeBwEntry 2}
--                apexRtspStatBladeBwUdpMap                                     {apexRtspStatBladeBwEntry 3}
--                apexRtspStatBladeBwSdvMap                                     {apexRtspStatBladeBwEntry 4}
--                apexRtspStatBladeBwTotal                                      {apexRtspStatBladeBwEntry 5}
--                apexRtspStatBladeBwDepiMap                                    {apexRtspStatBladeBwEntry 6}
--          apexRtspSetupFailureStatTable                                       {apexRtspStatus 11}
--             apexRtspSetupFailureStatEntry                                    {apexRtspSetupFailureStatTable 1}
--                apexRtspSetupFailureStatBladeNum                              {apexRtspSetupFailureStatEntry 1}
--                apexRtspSetupFailureStatCount                                 {apexRtspSetupFailureStatEntry 2}
   apexManualRouting                                      OBJECT IDENTIFIER ::= {apex3000 10}
      apexManualRoutingConfig                             OBJECT IDENTIFIER ::= {apexManualRouting 1}
         apexManualRoutingConfigGeneral                   OBJECT IDENTIFIER ::= {apexManualRoutingConfig 1}
--          apexManualRouteEnableDisableApply                                   {apexManualRoutingConfigGeneral 1}         
--          apexManRtePassThruEnableDisableApply                                {apexManualRoutingConfigGeneral 2}         
         apexManualRouteBlade1                            OBJECT IDENTIFIER ::= {apexManualRoutingConfig 2}
--          apexManualRouteBlade1ApplyTable                                     {apexManualRouteBlade1 1}
--             apexManualRouteBlade1ApplyEntry                                  {apexManualRouteBlade1ApplyTable 1}
--                apexManualRouteBlade1ApplyIndex                               {apexManualRouteBlade1ApplyEntry 1}
--                apexManualRouteBlade1ApplyChange                              {apexManualRouteBlade1ApplyEntry 2}
--          apexManualRouteBlade1Table                                          {apexManualRouteBlade1 2}
--             apexManualRouteBlade1Entry                                       {apexManualRouteBlade1Table 1}
--                apexManualRouteBlade1Index                                    {apexManualRouteBlade1Entry 1}
--                apexManualRouteBlade1Enable                                   {apexManualRouteBlade1Entry 2}
--                apexManualRouteBlade1InputInterface                           {apexManualRouteBlade1Entry 3}
--                apexManualRouteBlade1InputUdp                                 {apexManualRouteBlade1Entry 4}
--                apexManualRouteBlade1InputMulticastIp                         {apexManualRouteBlade1Entry 5}
--                apexManualRouteBlade1InputSourceIp                            {apexManualRouteBlade1Entry 6}
--                apexManualRouteBlade1InputProgNum                             {apexManualRouteBlade1Entry 7}
--                apexManualRouteBlade1InputPreEncryptCheck                     {apexManualRouteBlade1Entry 8}
--                apexManualRouteBlade1OutputTsNum                              {apexManualRouteBlade1Entry 9}
--                apexManualRouteBlade1OutputProgNum                            {apexManualRouteBlade1Entry 10}
--                apexManualRouteBlade1FollowDtcp                               {apexManualRouteBlade1Entry 11}
--          apexManRtePassThruBlade1ApplyTable                                  {apexManualRouteBlade1 3}
--             apexManRtePassThruBlade1ApplyEntry                               {apexManRtePassThruBlade1ApplyTable 1}
--                apexManRtePassThruBlade1ApplyOutputTsNum                      {apexManRtePassThruBlade1ApplyEntry 1}
--                apexManRtePassThruBlade1ApplyChange                           {apexManRtePassThruBlade1ApplyEntry 2}
--          apexManRtePassThruBlade1Table                                       {apexManualRouteBlade1 4}
--             apexManRtePassThruBlade1Entry                                    {apexManRtePassThruBlade1Table 1}
--                apexManRtePassThruBlade1OutputTsNum                           {apexManRtePassThruBlade1Entry 1}
--                apexManRtePassThruBlade1Enable                                {apexManRtePassThruBlade1Entry 2}
--                apexManRtePassThruBlade1InputInterface                        {apexManRtePassThruBlade1Entry 3}
--                apexManRtePassThruBlade1InputUdp                              {apexManRtePassThruBlade1Entry 4}
--                apexManRtePassThruBlade1InputMulticastIp                      {apexManRtePassThruBlade1Entry 5}
--                apexManRtePassThruBlade1InputSourceIp                         {apexManRtePassThruBlade1Entry 6}
         apexManualRouteBlade2                            OBJECT IDENTIFIER ::= {apexManualRoutingConfig 3}
--          apexManualRouteBlade2ApplyTable                                     {apexManualRouteBlade2 1}
--             apexManualRouteBlade2ApplyEntry                                  {apexManualRouteBlade2ApplyTable 1}
--                apexManualRouteBlade2ApplyIndex                               {apexManualRouteBlade2ApplyEntry 1}
--                apexManualRouteBlade2ApplyChange                              {apexManualRouteBlade2ApplyEntry 2}
--          apexManualRouteBlade2Table                                          {apexManualRouteBlade2 2}
--             apexManualRouteBlade2Entry                                       {apexManualRouteBlade2Table 1}
--                apexManualRouteBlade2Index                                    {apexManualRouteBlade2Entry 1}
--                apexManualRouteBlade2Enable                                   {apexManualRouteBlade2Entry 2}
--                apexManualRouteBlade2InputInterface                           {apexManualRouteBlade2Entry 3}
--                apexManualRouteBlade2InputUdp                                 {apexManualRouteBlade2Entry 4}
--                apexManualRouteBlade2InputMulticastIp                         {apexManualRouteBlade2Entry 5}
--                apexManualRouteBlade2InputSourceIp                            {apexManualRouteBlade2Entry 6}
--                apexManualRouteBlade2InputProgNum                             {apexManualRouteBlade2Entry 7}
--                apexManualRouteBlade2InputPreEncryptCheck                     {apexManualRouteBlade2Entry 8}
--                apexManualRouteBlade2OutputTsNum                              {apexManualRouteBlade2Entry 9}
--                apexManualRouteBlade2OutputProgNum                            {apexManualRouteBlade2Entry 10}
--                apexManualRouteBlade2FollowDtcp                               {apexManualRouteBlade2Entry 11}
--          apexManRtePassThruBlade2ApplyTable                                  {apexManualRouteBlade2 3}
--             apexManRtePassThruBlade2ApplyEntry                               {apexManRtePassThruBlade2ApplyTable 1}
--                apexManRtePassThruBlade2ApplyOutputTsNum                      {apexManRtePassThruBlade2ApplyEntry 1}
--                apexManRtePassThruBlade2ApplyChange                           {apexManRtePassThruBlade2ApplyEntry 2}
--          apexManRtePassThruBlade2Table                                       {apexManualRouteBlade2 4}
--             apexManRtePassThruBlade2Entry                                    {apexManRtePassThruBlade2Table 1}
--                apexManRtePassThruBlade2OutputTsNum                           {apexManRtePassThruBlade2Entry 1}
--                apexManRtePassThruBlade2Enable                                {apexManRtePassThruBlade2Entry 2}
--                apexManRtePassThruBlade2InputInterface                        {apexManRtePassThruBlade2Entry 3}
--                apexManRtePassThruBlade2InputUdp                              {apexManRtePassThruBlade2Entry 4}
--                apexManRtePassThruBlade2InputMulticastIp                      {apexManRtePassThruBlade2Entry 5}
--                apexManRtePassThruBlade2InputSourceIp                         {apexManRtePassThruBlade2Entry 6}
         apexManualRouteBlade3                            OBJECT IDENTIFIER ::= {apexManualRoutingConfig 4}
--          apexManualRouteBlade3ApplyTable                                     {apexManualRouteBlade3 1}
--             apexManualRouteBlade3ApplyEntry                                  {apexManualRouteBlade3ApplyTable 1}
--                apexManualRouteBlade3ApplyIndex                               {apexManualRouteBlade3ApplyEntry 1}
--                apexManualRouteBlade3ApplyChange                              {apexManualRouteBlade3ApplyEntry 2}
--          apexManualRouteBlade3Table                                          {apexManualRouteBlade3 2}
--             apexManualRouteBlade3Entry                                       {apexManualRouteBlade3Table 1}
--                apexManualRouteBlade3Index                                    {apexManualRouteBlade3Entry 1}
--                apexManualRouteBlade3Enable                                   {apexManualRouteBlade3Entry 2}
--                apexManualRouteBlade3InputInterface                           {apexManualRouteBlade3Entry 3}
--                apexManualRouteBlade3InputUdp                                 {apexManualRouteBlade3Entry 4}
--                apexManualRouteBlade3InputMulticastIp                         {apexManualRouteBlade3Entry 5}
--                apexManualRouteBlade3InputSourceIp                            {apexManualRouteBlade3Entry 6}
--                apexManualRouteBlade3InputProgNum                             {apexManualRouteBlade3Entry 7}
--                apexManualRouteBlade3InputPreEncryptCheck                     {apexManualRouteBlade3Entry 8}
--                apexManualRouteBlade3OutputTsNum                              {apexManualRouteBlade3Entry 9}
--                apexManualRouteBlade3OutputProgNum                            {apexManualRouteBlade3Entry 10}
--                apexManualRouteBlade3FollowDtcp                               {apexManualRouteBlade3Entry 11}
--          apexManRtePassThruBlade3ApplyTable                                  {apexManualRouteBlade3 3}
--             apexManRtePassThruBlade3ApplyEntry                               {apexManRtePassThruBlade3ApplyTable 1}
--                apexManRtePassThruBlade3ApplyOutputTsNum                      {apexManRtePassThruBlade3ApplyEntry 1}
--                apexManRtePassThruBlade3ApplyChange                           {apexManRtePassThruBlade3ApplyEntry 2}
--          apexManRtePassThruBlade3Table                                       {apexManualRouteBlade3 4}
--             apexManRtePassThruBlade3Entry                                    {apexManRtePassThruBlade3Table 1}
--                apexManRtePassThruBlade3OutputTsNum                           {apexManRtePassThruBlade3Entry 1}
--                apexManRtePassThruBlade3Enable                                {apexManRtePassThruBlade3Entry 2}
--                apexManRtePassThruBlade3InputInterface                        {apexManRtePassThruBlade3Entry 3}
--                apexManRtePassThruBlade3InputUdp                              {apexManRtePassThruBlade3Entry 4}
--                apexManRtePassThruBlade3InputMulticastIp                      {apexManRtePassThruBlade3Entry 5}
--                apexManRtePassThruBlade3InputSourceIp                         {apexManRtePassThruBlade3Entry 6}
         apexManualRouteBlade4                            OBJECT IDENTIFIER ::= {apexManualRoutingConfig 5}
--          apexManualRouteBlade4ApplyTable                                     {apexManualRouteBlade4 1}
--             apexManualRouteBlade4ApplyEntry                                  {apexManualRouteBlade4ApplyTable 1}
--                apexManualRouteBlade4ApplyIndex                               {apexManualRouteBlade4ApplyEntry 1}
--                apexManualRouteBlade4ApplyChange                              {apexManualRouteBlade4ApplyEntry 2}
--          apexManualRouteBlade4Table                                          {apexManualRouteBlade4 2}
--             apexManualRouteBlade4Entry                                       {apexManualRouteBlade4Table 1}
--                apexManualRouteBlade4Index                                    {apexManualRouteBlade4Entry 1}
--                apexManualRouteBlade4Enable                                   {apexManualRouteBlade4Entry 2}
--                apexManualRouteBlade4InputInterface                           {apexManualRouteBlade4Entry 3}
--                apexManualRouteBlade4InputUdp                                 {apexManualRouteBlade4Entry 4}
--                apexManualRouteBlade4InputMulticastIp                         {apexManualRouteBlade4Entry 5}
--                apexManualRouteBlade4InputSourceIp                            {apexManualRouteBlade4Entry 6}
--                apexManualRouteBlade4InputProgNum                             {apexManualRouteBlade4Entry 7}
--                apexManualRouteBlade4InputPreEncryptCheck                     {apexManualRouteBlade4Entry 8}
--                apexManualRouteBlade4OutputTsNum                              {apexManualRouteBlade4Entry 9}
--                apexManualRouteBlade4OutputProgNum                            {apexManualRouteBlade4Entry 10}
--                apexManualRouteBlade4FollowDtcp                               {apexManualRouteBlade4Entry 11}
--          apexManRtePassThruBlade4ApplyTable                                  {apexManualRouteBlade4 3}
--             apexManRtePassThruBlade4ApplyEntry                               {apexManRtePassThruBlade4ApplyTable 1}
--                apexManRtePassThruBlade4ApplyOutputTsNum                      {apexManRtePassThruBlade4ApplyEntry 1}
--                apexManRtePassThruBlade4ApplyChange                           {apexManRtePassThruBlade4ApplyEntry 2}
--          apexManRtePassThruBlade4Table                                       {apexManualRouteBlade4 4}
--             apexManRtePassThruBlade4Entry                                    {apexManRtePassThruBlade4Table 1}
--                apexManRtePassThruBlade4OutputTsNum                           {apexManRtePassThruBlade4Entry 1}
--                apexManRtePassThruBlade4Enable                                {apexManRtePassThruBlade4Entry 2}
--                apexManRtePassThruBlade4InputInterface                        {apexManRtePassThruBlade4Entry 3}
--                apexManRtePassThruBlade4InputUdp                              {apexManRtePassThruBlade4Entry 4}
--                apexManRtePassThruBlade4InputMulticastIp                      {apexManRtePassThruBlade4Entry 5}
--                apexManRtePassThruBlade4InputSourceIp                         {apexManRtePassThruBlade4Entry 6}
         apexManualRouteBlade5                            OBJECT IDENTIFIER ::= {apexManualRoutingConfig 6}
--          apexManualRouteBlade5ApplyTable                                     {apexManualRouteBlade5 1}
--             apexManualRouteBlade5ApplyEntry                                  {apexManualRouteBlade5ApplyTable 1}
--                apexManualRouteBlade5ApplyIndex                               {apexManualRouteBlade5ApplyEntry 1}
--                apexManualRouteBlade5ApplyChange                              {apexManualRouteBlade5ApplyEntry 2}
--          apexManualRouteBlade5Table                                          {apexManualRouteBlade5 2}
--             apexManualRouteBlade5Entry                                       {apexManualRouteBlade5Table 1}
--                apexManualRouteBlade5Index                                    {apexManualRouteBlade5Entry 1}
--                apexManualRouteBlade5Enable                                   {apexManualRouteBlade5Entry 2}
--                apexManualRouteBlade5InputInterface                           {apexManualRouteBlade5Entry 3}
--                apexManualRouteBlade5InputUdp                                 {apexManualRouteBlade5Entry 4}
--                apexManualRouteBlade5InputMulticastIp                         {apexManualRouteBlade5Entry 5}
--                apexManualRouteBlade5InputSourceIp                            {apexManualRouteBlade5Entry 6}
--                apexManualRouteBlade5InputProgNum                             {apexManualRouteBlade5Entry 7}
--                apexManualRouteBlade5InputPreEncryptCheck                     {apexManualRouteBlade5Entry 8}
--                apexManualRouteBlade5OutputTsNum                              {apexManualRouteBlade5Entry 9}
--                apexManualRouteBlade5OutputProgNum                            {apexManualRouteBlade5Entry 10}
--                apexManualRouteBlade5FollowDtcp                               {apexManualRouteBlade5Entry 11}
--          apexManRtePassThruBlade5ApplyTable                                  {apexManualRouteBlade5 3}
--             apexManRtePassThruBlade5ApplyEntry                               {apexManRtePassThruBlade5ApplyTable 1}
--                apexManRtePassThruBlade5ApplyOutputTsNum                      {apexManRtePassThruBlade5ApplyEntry 1}
--                apexManRtePassThruBlade5ApplyChange                           {apexManRtePassThruBlade5ApplyEntry 2}
--          apexManRtePassThruBlade5Table                                       {apexManualRouteBlade5 4}
--             apexManRtePassThruBlade5Entry                                    {apexManRtePassThruBlade5Table 1}
--                apexManRtePassThruBlade5OutputTsNum                           {apexManRtePassThruBlade5Entry 1}
--                apexManRtePassThruBlade5Enable                                {apexManRtePassThruBlade5Entry 2}
--                apexManRtePassThruBlade5InputInterface                        {apexManRtePassThruBlade5Entry 3}
--                apexManRtePassThruBlade5InputUdp                              {apexManRtePassThruBlade5Entry 4}
--                apexManRtePassThruBlade5InputMulticastIp                      {apexManRtePassThruBlade5Entry 5}
--                apexManRtePassThruBlade5InputSourceIp                         {apexManRtePassThruBlade5Entry 6}
         apexManualRouteBlade6                            OBJECT IDENTIFIER ::= {apexManualRoutingConfig 7}
--          apexManualRouteBlade6ApplyTable                                     {apexManualRouteBlade6 1}
--             apexManualRouteBlade6ApplyEntry                                  {apexManualRouteBlade6ApplyTable 1}
--                apexManualRouteBlade6ApplyIndex                               {apexManualRouteBlade6ApplyEntry 1}
--                apexManualRouteBlade6ApplyChange                              {apexManualRouteBlade6ApplyEntry 2}
--          apexManualRouteBlade6Table                                          {apexManualRouteBlade6 2}
--             apexManualRouteBlade6Entry                                       {apexManualRouteBlade6Table 1}
--                apexManualRouteBlade6Index                                    {apexManualRouteBlade6Entry 1}
--                apexManualRouteBlade6Enable                                   {apexManualRouteBlade6Entry 2}
--                apexManualRouteBlade6InputInterface                           {apexManualRouteBlade6Entry 3}
--                apexManualRouteBlade6InputUdp                                 {apexManualRouteBlade6Entry 4}
--                apexManualRouteBlade6InputMulticastIp                         {apexManualRouteBlade6Entry 5}
--                apexManualRouteBlade6InputSourceIp                            {apexManualRouteBlade6Entry 6}
--                apexManualRouteBlade6InputProgNum                             {apexManualRouteBlade6Entry 7}
--                apexManualRouteBlade6InputPreEncryptCheck                     {apexManualRouteBlade6Entry 8}
--                apexManualRouteBlade6OutputTsNum                              {apexManualRouteBlade6Entry 9}
--                apexManualRouteBlade6OutputProgNum                            {apexManualRouteBlade6Entry 10}
--                apexManualRouteBlade6FollowDtcp                               {apexManualRouteBlade6Entry 11}
--          apexManRtePassThruBlade6ApplyTable                                  {apexManualRouteBlade6 3}
--             apexManRtePassThruBlade6ApplyEntry                               {apexManRtePassThruBlade6ApplyTable 1}
--                apexManRtePassThruBlade6ApplyOutputTsNum                      {apexManRtePassThruBlade6ApplyEntry 1}
--                apexManRtePassThruBlade6ApplyChange                           {apexManRtePassThruBlade6ApplyEntry 2}
--          apexManRtePassThruBlade6Table                                       {apexManualRouteBlade6 4}
--             apexManRtePassThruBlade6Entry                                    {apexManRtePassThruBlade6Table 1}
--                apexManRtePassThruBlade6OutputTsNum                           {apexManRtePassThruBlade6Entry 1}
--                apexManRtePassThruBlade6Enable                                {apexManRtePassThruBlade6Entry 2}
--                apexManRtePassThruBlade6InputInterface                        {apexManRtePassThruBlade6Entry 3}
--                apexManRtePassThruBlade6InputUdp                              {apexManRtePassThruBlade6Entry 4}
--                apexManRtePassThruBlade6InputMulticastIp                      {apexManRtePassThruBlade6Entry 5}
--                apexManRtePassThruBlade6InputSourceIp                         {apexManRtePassThruBlade6Entry 6}
         apexManualRouteBlade7                            OBJECT IDENTIFIER ::= {apexManualRoutingConfig 8}
--          apexManualRouteBlade7ApplyTable                                     {apexManualRouteBlade7 1}
--             apexManualRouteBlade7ApplyEntry                                  {apexManualRouteBlade7ApplyTable 1}
--                apexManualRouteBlade7ApplyIndex                               {apexManualRouteBlade7ApplyEntry 1}
--                apexManualRouteBlade7ApplyChange                              {apexManualRouteBlade7ApplyEntry 2}
--          apexManualRouteBlade7Table                                          {apexManualRouteBlade7 2}
--             apexManualRouteBlade7Entry                                       {apexManualRouteBlade7Table 1}
--                apexManualRouteBlade7Index                                    {apexManualRouteBlade7Entry 1}
--                apexManualRouteBlade7Enable                                   {apexManualRouteBlade7Entry 2}
--                apexManualRouteBlade7InputInterface                           {apexManualRouteBlade7Entry 3}
--                apexManualRouteBlade7InputUdp                                 {apexManualRouteBlade7Entry 4}
--                apexManualRouteBlade7InputMulticastIp                         {apexManualRouteBlade7Entry 5}
--                apexManualRouteBlade7InputSourceIp                            {apexManualRouteBlade7Entry 6}
--                apexManualRouteBlade7InputProgNum                             {apexManualRouteBlade7Entry 7}
--                apexManualRouteBlade7InputPreEncryptCheck                     {apexManualRouteBlade7Entry 8}
--                apexManualRouteBlade7OutputTsNum                              {apexManualRouteBlade7Entry 9}
--                apexManualRouteBlade7OutputProgNum                            {apexManualRouteBlade7Entry 10}
--                apexManualRouteBlade7FollowDtcp                               {apexManualRouteBlade7Entry 11}
--          apexManRtePassThruBlade7ApplyTable                                  {apexManualRouteBlade7 3}
--             apexManRtePassThruBlade7ApplyEntry                               {apexManRtePassThruBlade7ApplyTable 1}
--                apexManRtePassThruBlade7ApplyOutputTsNum                      {apexManRtePassThruBlade7ApplyEntry 1}
--                apexManRtePassThruBlade7ApplyChange                           {apexManRtePassThruBlade7ApplyEntry 2}
--          apexManRtePassThruBlade7Table                                       {apexManualRouteBlade7 4}
--             apexManRtePassThruBlade7Entry                                    {apexManRtePassThruBlade7Table 1}
--                apexManRtePassThruBlade7OutputTsNum                           {apexManRtePassThruBlade7Entry 1}
--                apexManRtePassThruBlade7Enable                                {apexManRtePassThruBlade7Entry 2}
--                apexManRtePassThruBlade7InputInterface                        {apexManRtePassThruBlade7Entry 3}
--                apexManRtePassThruBlade7InputUdp                              {apexManRtePassThruBlade7Entry 4}
--                apexManRtePassThruBlade7InputMulticastIp                      {apexManRtePassThruBlade7Entry 5}
--                apexManRtePassThruBlade7InputSourceIp                         {apexManRtePassThruBlade7Entry 6}
         apexManualRouteBlade8                            OBJECT IDENTIFIER ::= {apexManualRoutingConfig 9}
--          apexManualRouteBlade8ApplyTable                                     {apexManualRouteBlade8 1}
--             apexManualRouteBlade8ApplyEntry                                  {apexManualRouteBlade8ApplyTable 1}
--                apexManualRouteBlade8ApplyIndex                               {apexManualRouteBlade8ApplyEntry 1}
--                apexManualRouteBlade8ApplyChange                              {apexManualRouteBlade8ApplyEntry 2}
--          apexManualRouteBlade8Table                                          {apexManualRouteBlade8 2}
--             apexManualRouteBlade8Entry                                       {apexManualRouteBlade8Table 1}
--                apexManualRouteBlade8Index                                    {apexManualRouteBlade8Entry 1}
--                apexManualRouteBlade8Enable                                   {apexManualRouteBlade8Entry 2}
--                apexManualRouteBlade8InputInterface                           {apexManualRouteBlade8Entry 3}
--                apexManualRouteBlade8InputUdp                                 {apexManualRouteBlade8Entry 4}
--                apexManualRouteBlade8InputMulticastIp                         {apexManualRouteBlade8Entry 5}
--                apexManualRouteBlade8InputSourceIp                            {apexManualRouteBlade8Entry 6}
--                apexManualRouteBlade8InputProgNum                             {apexManualRouteBlade8Entry 7}
--                apexManualRouteBlade8InputPreEncryptCheck                     {apexManualRouteBlade8Entry 8}
--                apexManualRouteBlade8OutputTsNum                              {apexManualRouteBlade8Entry 9}
--                apexManualRouteBlade8OutputProgNum                            {apexManualRouteBlade8Entry 10}
--                apexManualRouteBlade8FollowDtcp                               {apexManualRouteBlade8Entry 11}
--          apexManRtePassThruBlade8ApplyTable                                  {apexManualRouteBlade8 3}
--             apexManRtePassThruBlade8ApplyEntry                               {apexManRtePassThruBlade8ApplyTable 1}
--                apexManRtePassThruBlade8ApplyOutputTsNum                      {apexManRtePassThruBlade8ApplyEntry 1}
--                apexManRtePassThruBlade8ApplyChange                           {apexManRtePassThruBlade8ApplyEntry 2}
--          apexManRtePassThruBlade8Table                                       {apexManualRouteBlade8 4}
--             apexManRtePassThruBlade8Entry                                    {apexManRtePassThruBlade8Table 1}
--                apexManRtePassThruBlade8OutputTsNum                           {apexManRtePassThruBlade8Entry 1}
--                apexManRtePassThruBlade8Enable                                {apexManRtePassThruBlade8Entry 2}
--                apexManRtePassThruBlade8InputInterface                        {apexManRtePassThruBlade8Entry 3}
--                apexManRtePassThruBlade8InputUdp                              {apexManRtePassThruBlade8Entry 4}
--                apexManRtePassThruBlade8InputMulticastIp                      {apexManRtePassThruBlade8Entry 5}
--                apexManRtePassThruBlade8InputSourceIp                         {apexManRtePassThruBlade8Entry 6}
      apexManualRoutingStatus                             OBJECT IDENTIFIER ::= {apexManualRouting 2}
         apexManualRoutingStatusGeneral                   OBJECT IDENTIFIER ::= {apexManualRoutingStatus 1}      
--       apexManualRouteStatusTable                                             {apexManualRoutingStatus 2}
--          apexManualRouteStatusEntry                                          {apexManualRouteStatusTable 1}
--             apexManualRouteStatusBladeNum                                    {apexManualRouteStatusEntry 1}
--             apexManualRouteInvalidApplyText                                  {apexManualRouteStatusEntry 2}     
--             apexManRtePassThruInvalidApplyText                               {apexManualRouteStatusEntry 3}     
   apexAncillaryPidMapping                                OBJECT IDENTIFIER ::= {apex3000 11}
      apexPidMapConfig                                    OBJECT IDENTIFIER ::= {apexAncillaryPidMapping 1}
         apexPidMapConfigGeneral                          OBJECT IDENTIFIER ::= {apexPidMapConfig 1}
--          apexPidMapEnableDisableApply                                        {apexPidMapConfigGeneral 1}         
         apexPidMapBlade1                                 OBJECT IDENTIFIER ::= {apexPidMapConfig 2}
--          apexPidMapBlade1ApplyTable                                          {apexPidMapBlade1 1}
--             apexPidMapBlade1ApplyEntry                                       {apexPidMapBlade1ApplyTable 1}
--                apexPidMapBlade1ApplyIndex                                    {apexPidMapBlade1ApplyEntry 1}
--                apexPidMapBlade1ApplyChange                                   {apexPidMapBlade1ApplyEntry 2}
--          apexPidMapBlade1Table                                               {apexPidMapBlade1 2}
--             apexPidMapBlade1Entry                                            {apexPidMapBlade1Table 1}
--                apexPidMapBlade1Index                                         {apexPidMapBlade1Entry 1}
--                apexPidMapBlade1Enable                                        {apexPidMapBlade1Entry 2}
--                apexPidMapBlade1InputInterface                                {apexPidMapBlade1Entry 3}
--                apexPidMapBlade1InputUdp                                      {apexPidMapBlade1Entry 4}
--                apexPidMapBlade1InputMulticastIp                              {apexPidMapBlade1Entry 5}
--                apexPidMapBlade1InputSourceIp                                 {apexPidMapBlade1Entry 6}
--                apexPidMapBlade1InputPid                                      {apexPidMapBlade1Entry 7}
--                apexPidMapBlade1OutputTsNum                                   {apexPidMapBlade1Entry 8}
--                apexPidMapBlade1OutputPid                                     {apexPidMapBlade1Entry 9}
         apexPidMapBlade2                                 OBJECT IDENTIFIER ::= {apexPidMapConfig 3}
--          apexPidMapBlade2ApplyTable                                          {apexPidMapBlade2 1}
--             apexPidMapBlade2ApplyEntry                                       {apexPidMapBlade2ApplyTable 1}
--                apexPidMapBlade2ApplyIndex                                    {apexPidMapBlade2ApplyEntry 1}
--                apexPidMapBlade2ApplyChange                                   {apexPidMapBlade2ApplyEntry 2}
--          apexPidMapBlade2Table                                               {apexPidMapBlade2 2}
--             apexPidMapBlade2Entry                                            {apexPidMapBlade2Table 1}
--                apexPidMapBlade2Index                                         {apexPidMapBlade2Entry 1}
--                apexPidMapBlade2Enable                                        {apexPidMapBlade2Entry 2}
--                apexPidMapBlade2InputInterface                                {apexPidMapBlade2Entry 3}
--                apexPidMapBlade2InputUdp                                      {apexPidMapBlade2Entry 4}
--                apexPidMapBlade2InputMulticastIp                              {apexPidMapBlade2Entry 5}
--                apexPidMapBlade2InputSourceIp                                 {apexPidMapBlade2Entry 6}
--                apexPidMapBlade2InputPid                                      {apexPidMapBlade2Entry 7}
--                apexPidMapBlade2OutputTsNum                                   {apexPidMapBlade2Entry 8}
--                apexPidMapBlade2OutputPid                                     {apexPidMapBlade2Entry 9}
         apexPidMapBlade3                                 OBJECT IDENTIFIER ::= {apexPidMapConfig 4}
--          apexPidMapBlade3ApplyTable                                          {apexPidMapBlade3 1}
--             apexPidMapBlade3ApplyEntry                                       {apexPidMapBlade3ApplyTable 1}
--                apexPidMapBlade3ApplyIndex                                    {apexPidMapBlade3ApplyEntry 1}
--                apexPidMapBlade3ApplyChange                                   {apexPidMapBlade3ApplyEntry 2}
--          apexPidMapBlade3Table                                               {apexPidMapBlade3 2}
--             apexPidMapBlade3Entry                                            {apexPidMapBlade3Table 1}
--                apexPidMapBlade3Index                                         {apexPidMapBlade3Entry 1}
--                apexPidMapBlade3Enable                                        {apexPidMapBlade3Entry 2}
--                apexPidMapBlade3InputInterface                                {apexPidMapBlade3Entry 3}
--                apexPidMapBlade3InputUdp                                      {apexPidMapBlade3Entry 4}
--                apexPidMapBlade3InputMulticastIp                              {apexPidMapBlade3Entry 5}
--                apexPidMapBlade3InputSourceIp                                 {apexPidMapBlade3Entry 6}
--                apexPidMapBlade3InputPid                                      {apexPidMapBlade3Entry 7}
--                apexPidMapBlade3OutputTsNum                                   {apexPidMapBlade3Entry 8}
--                apexPidMapBlade3OutputPid                                     {apexPidMapBlade3Entry 9}
         apexPidMapBlade4                                 OBJECT IDENTIFIER ::= {apexPidMapConfig 5}
--          apexPidMapBlade4ApplyTable                                          {apexPidMapBlade4 1}
--             apexPidMapBlade4ApplyEntry                                       {apexPidMapBlade4ApplyTable 1}
--                apexPidMapBlade4ApplyIndex                                    {apexPidMapBlade4ApplyEntry 1}
--                apexPidMapBlade4ApplyChange                                   {apexPidMapBlade4ApplyEntry 2}
--          apexPidMapBlade4Table                                               {apexPidMapBlade4 2}
--             apexPidMapBlade4Entry                                            {apexPidMapBlade4Table 1}
--                apexPidMapBlade4Index                                         {apexPidMapBlade4Entry 1}
--                apexPidMapBlade4Enable                                        {apexPidMapBlade4Entry 2}
--                apexPidMapBlade4InputInterface                                {apexPidMapBlade4Entry 3}
--                apexPidMapBlade4InputUdp                                      {apexPidMapBlade4Entry 4}
--                apexPidMapBlade4InputMulticastIp                              {apexPidMapBlade4Entry 5}
--                apexPidMapBlade4InputSourceIp                                 {apexPidMapBlade4Entry 6}
--                apexPidMapBlade4InputPid                                      {apexPidMapBlade4Entry 7}
--                apexPidMapBlade4OutputTsNum                                   {apexPidMapBlade4Entry 8}
--                apexPidMapBlade4OutputPid                                     {apexPidMapBlade4Entry 9}
         apexPidMapBlade5                                 OBJECT IDENTIFIER ::= {apexPidMapConfig 6}
--          apexPidMapBlade5ApplyTable                                          {apexPidMapBlade5 1}
--             apexPidMapBlade5ApplyEntry                                       {apexPidMapBlade5ApplyTable 1}
--                apexPidMapBlade5ApplyIndex                                    {apexPidMapBlade5ApplyEntry 1}
--                apexPidMapBlade5ApplyChange                                   {apexPidMapBlade5ApplyEntry 2}
--          apexPidMapBlade5Table                                               {apexPidMapBlade5 2}
--             apexPidMapBlade5Entry                                            {apexPidMapBlade5Table 1}
--                apexPidMapBlade5Index                                         {apexPidMapBlade5Entry 1}
--                apexPidMapBlade5Enable                                        {apexPidMapBlade5Entry 2}
--                apexPidMapBlade5InputInterface                                {apexPidMapBlade5Entry 3}
--                apexPidMapBlade5InputUdp                                      {apexPidMapBlade5Entry 4}
--                apexPidMapBlade5InputMulticastIp                              {apexPidMapBlade5Entry 5}
--                apexPidMapBlade5InputSourceIp                                 {apexPidMapBlade5Entry 6}
--                apexPidMapBlade5InputPid                                      {apexPidMapBlade5Entry 7}
--                apexPidMapBlade5OutputTsNum                                   {apexPidMapBlade5Entry 8}
--                apexPidMapBlade5OutputPid                                     {apexPidMapBlade5Entry 9}
         apexPidMapBlade6                                 OBJECT IDENTIFIER ::= {apexPidMapConfig 7}
--          apexPidMapBlade6ApplyTable                                          {apexPidMapBlade6 1}
--             apexPidMapBlade6ApplyEntry                                       {apexPidMapBlade6ApplyTable 1}
--                apexPidMapBlade6ApplyIndex                                    {apexPidMapBlade6ApplyEntry 1}
--                apexPidMapBlade6ApplyChange                                   {apexPidMapBlade6ApplyEntry 2}
--          apexPidMapBlade6Table                                               {apexPidMapBlade6 2}
--             apexPidMapBlade6Entry                                            {apexPidMapBlade6Table 1}
--                apexPidMapBlade6Index                                         {apexPidMapBlade6Entry 1}
--                apexPidMapBlade6Enable                                        {apexPidMapBlade6Entry 2}
--                apexPidMapBlade6InputInterface                                {apexPidMapBlade6Entry 3}
--                apexPidMapBlade6InputUdp                                      {apexPidMapBlade6Entry 4}
--                apexPidMapBlade6InputMulticastIp                              {apexPidMapBlade6Entry 5}
--                apexPidMapBlade6InputSourceIp                                 {apexPidMapBlade6Entry 6}
--                apexPidMapBlade6InputPid                                      {apexPidMapBlade6Entry 7}
--                apexPidMapBlade6OutputTsNum                                   {apexPidMapBlade6Entry 8}
--                apexPidMapBlade6OutputPid                                     {apexPidMapBlade6Entry 9}
         apexPidMapBlade7                                 OBJECT IDENTIFIER ::= {apexPidMapConfig 8}
--          apexPidMapBlade7ApplyTable                                          {apexPidMapBlade7 1}
--             apexPidMapBlade7ApplyEntry                                       {apexPidMapBlade7ApplyTable 1}
--                apexPidMapBlade7ApplyIndex                                    {apexPidMapBlade7ApplyEntry 1}
--                apexPidMapBlade7ApplyChange                                   {apexPidMapBlade7ApplyEntry 2}
--          apexPidMapBlade7Table                                               {apexPidMapBlade7 2}
--             apexPidMapBlade7Entry                                            {apexPidMapBlade7Table 1}
--                apexPidMapBlade7Index                                         {apexPidMapBlade7Entry 1}
--                apexPidMapBlade7Enable                                        {apexPidMapBlade7Entry 2}
--                apexPidMapBlade7InputInterface                                {apexPidMapBlade7Entry 3}
--                apexPidMapBlade7InputUdp                                      {apexPidMapBlade7Entry 4}
--                apexPidMapBlade7InputMulticastIp                              {apexPidMapBlade7Entry 5}
--                apexPidMapBlade7InputSourceIp                                 {apexPidMapBlade7Entry 6}
--                apexPidMapBlade7InputPid                                      {apexPidMapBlade7Entry 7}
--                apexPidMapBlade7OutputTsNum                                   {apexPidMapBlade7Entry 8}
--                apexPidMapBlade7OutputPid                                     {apexPidMapBlade7Entry 9}
         apexPidMapBlade8                                 OBJECT IDENTIFIER ::= {apexPidMapConfig 9}
--          apexPidMapBlade8ApplyTable                                          {apexPidMapBlade8 1}
--             apexPidMapBlade8ApplyEntry                                       {apexPidMapBlade8ApplyTable 1}
--                apexPidMapBlade8ApplyIndex                                    {apexPidMapBlade8ApplyEntry 1}
--                apexPidMapBlade8ApplyChange                                   {apexPidMapBlade8ApplyEntry 2}
--          apexPidMapBlade8Table                                               {apexPidMapBlade8 2}
--             apexPidMapBlade8Entry                                            {apexPidMapBlade8Table 1}
--                apexPidMapBlade8Index                                         {apexPidMapBlade8Entry 1}
--                apexPidMapBlade8Enable                                        {apexPidMapBlade8Entry 2}
--                apexPidMapBlade8InputInterface                                {apexPidMapBlade8Entry 3}
--                apexPidMapBlade8InputUdp                                      {apexPidMapBlade8Entry 4}
--                apexPidMapBlade8InputMulticastIp                              {apexPidMapBlade8Entry 5}
--                apexPidMapBlade8InputSourceIp                                 {apexPidMapBlade8Entry 6}
--                apexPidMapBlade8InputPid                                      {apexPidMapBlade8Entry 7}
--                apexPidMapBlade8OutputTsNum                                   {apexPidMapBlade8Entry 8}
--                apexPidMapBlade8OutputPid                                     {apexPidMapBlade8Entry 9}
      apexPidMapStatus                                    OBJECT IDENTIFIER ::= {apexAncillaryPidMapping 2}
         apexPidMapStatusGeneral                          OBJECT IDENTIFIER ::= {apexPidMapStatus 1}
--          apexPidMapMaxPidMappings                                            {apexPidMapStatusGeneral 1}       
--       apexPidMapStatusTable                                                  {apexPidMapStatus 2}
--          apexPidMapStatusEntry                                               {apexPidMapStatusTable 1}
--             apexPidMapBladeNum                                               {apexPidMapStatusEntry 1}
--             apexPidMapInvalidApplyText                                       {apexPidMapStatusEntry 2}
   apexInsertion                                          OBJECT IDENTIFIER ::= {apex3000 12}
      apexInsertionConfig                                 OBJECT IDENTIFIER ::= {apexInsertion 1}
         apexInsertionConfigGeneral                       OBJECT IDENTIFIER ::= {apexInsertionConfig 1}
      apexInsertionStatus                                 OBJECT IDENTIFIER ::= {apexInsertion 2}
         apexInsertionStatusGeneral                       OBJECT IDENTIFIER ::= {apexInsertionStatus 1}
--       apexInsertPacketStatisticsTable                                        {apexInsertionStatus 2}
--          apexInsertPacketStatisticsEntry                                     {apexInsertPacketStatisticsTable 1}
--             apexInsertPacketStatBladeNum                                     {apexInsertPacketStatisticsEntry 1}
--             apexInsertPacketStatOutputTsNum                                  {apexInsertPacketStatisticsEntry 2}
--             apexInsertPacketStatTotPkts                                      {apexInsertPacketStatisticsEntry 3}
--             apexInsertPacketStatNumPkts                                      {apexInsertPacketStatisticsEntry 4}
   apexOutputTransport                                    OBJECT IDENTIFIER ::= {apex3000 13}
      apexOutputTsConfig                                  OBJECT IDENTIFIER ::= {apexOutputTransport 1}
         apexOutputTsConfigGeneral                        OBJECT IDENTIFIER ::= {apexOutputTsConfig 1}
         apexOutputTsUtilizationMonitoring                OBJECT IDENTIFIER ::= {apexOutputTsConfig 2}
            apexOutputTsUtilizationMonitorGeneral         OBJECT IDENTIFIER ::= {apexOutputTsUtilizationMonitoring 1}
--             apexOutputTsUtilMonAlarmThreshold                                {apexOutputTsUtilizationMonitorGeneral 1}
--             apexOutputTsUtilMonSetAlarmDelay                                 {apexOutputTsUtilizationMonitorGeneral 2}
--             apexOutputTsUtilMonClearAlarmDelay                               {apexOutputTsUtilizationMonitorGeneral 3}
         apexOutputTsConfigBlade1                         OBJECT IDENTIFIER ::= {apexOutputTsConfig 3}
--          apexOutputTsConfBlade1ApplyTable                                    {apexOutputTsConfigBlade1 1}
--             apexOutputTsConfBlade1ApplyEntry                                 {apexOutputTsConfBlade1ApplyTable 1}
--                apexOutputTsConfBlade1ApplyIndex                              {apexOutputTsConfBlade1ApplyEntry 1}
--                apexOutputTsConfBlade1ApplyChange                             {apexOutputTsConfBlade1ApplyEntry 2}
--          apexOutputTsConfigBlade1Table                                       {apexOutputTsConfigBlade1 2}
--             apexOutputTsConfigBlade1Entry                                    {apexOutputTsConfigBlade1Table 1}
--                apexOutputTsConfBlade1OutputTsNum                             {apexOutputTsConfigBlade1Entry 1}
--                apexOutputTsConfBlade1PidRemappingMode                        {apexOutputTsConfigBlade1Entry 2}
--                apexOutputTsConfBlade1OperatingMode                           {apexOutputTsConfigBlade1Entry 3}
--                apexOutputTsConfBlade1OutPatTsId                              {apexOutputTsConfigBlade1Entry 4}
--                apexOutputTsConfBlade1EncryptionType                          {apexOutputTsConfigBlade1Entry 5}
--                apexOutputTsConfBlade1SimulcryptMode                          {apexOutputTsConfigBlade1Entry 6}
--                apexOutputTsConfBlade1DepiRemoteId                            {apexOutputTsConfigBlade1Entry 7}
--                apexOutputTsConfBlade1QamReplicationRfPort                    {apexOutputTsConfigBlade1Entry 8}
         apexOutputTsConfigBlade2                         OBJECT IDENTIFIER ::= {apexOutputTsConfig 4}
--          apexOutputTsConfBlade2ApplyTable                                    {apexOutputTsConfigBlade2 1}
--             apexOutputTsConfBlade2ApplyEntry                                 {apexOutputTsConfBlade2ApplyTable 1}
--                apexOutputTsConfBlade2ApplyIndex                              {apexOutputTsConfBlade2ApplyEntry 1}
--                apexOutputTsConfBlade2ApplyChange                             {apexOutputTsConfBlade2ApplyEntry 2}
--          apexOutputTsConfigBlade2Table                                       {apexOutputTsConfigBlade2 2}
--             apexOutputTsConfigBlade2Entry                                    {apexOutputTsConfigBlade2Table 1}
--                apexOutputTsConfBlade2OutputTsNum                             {apexOutputTsConfigBlade2Entry 1}
--                apexOutputTsConfBlade2PidRemappingMode                        {apexOutputTsConfigBlade2Entry 2}
--                apexOutputTsConfBlade2OperatingMode                           {apexOutputTsConfigBlade2Entry 3}
--                apexOutputTsConfBlade2OutPatTsId                              {apexOutputTsConfigBlade2Entry 4}
--                apexOutputTsConfBlade2EncryptionType                          {apexOutputTsConfigBlade2Entry 5}
--                apexOutputTsConfBlade2SimulcryptMode                          {apexOutputTsConfigBlade2Entry 6}
--                apexOutputTsConfBlade2DepiRemoteId                            {apexOutputTsConfigBlade2Entry 7}
--                apexOutputTsConfBlade2QamReplicationRfPort                    {apexOutputTsConfigBlade2Entry 8}
         apexOutputTsConfigBlade3                         OBJECT IDENTIFIER ::= {apexOutputTsConfig 5}
--          apexOutputTsConfBlade3ApplyTable                                    {apexOutputTsConfigBlade3 1}
--             apexOutputTsConfBlade3ApplyEntry                                 {apexOutputTsConfBlade3ApplyTable 1}
--                apexOutputTsConfBlade3ApplyIndex                              {apexOutputTsConfBlade3ApplyEntry 1}
--                apexOutputTsConfBlade3ApplyChange                             {apexOutputTsConfBlade3ApplyEntry 2}
--          apexOutputTsConfigBlade3Table                                       {apexOutputTsConfigBlade3 2}
--             apexOutputTsConfigBlade3Entry                                    {apexOutputTsConfigBlade3Table 1}
--                apexOutputTsConfBlade3OutputTsNum                             {apexOutputTsConfigBlade3Entry 1}
--                apexOutputTsConfBlade3PidRemappingMode                        {apexOutputTsConfigBlade3Entry 2}
--                apexOutputTsConfBlade3OperatingMode                           {apexOutputTsConfigBlade3Entry 3}
--                apexOutputTsConfBlade3OutPatTsId                              {apexOutputTsConfigBlade3Entry 4}
--                apexOutputTsConfBlade3EncryptionType                          {apexOutputTsConfigBlade3Entry 5}
--                apexOutputTsConfBlade3SimulcryptMode                          {apexOutputTsConfigBlade3Entry 6}
--                apexOutputTsConfBlade3DepiRemoteId                            {apexOutputTsConfigBlade3Entry 7}
--                apexOutputTsConfBlade3QamReplicationRfPort                    {apexOutputTsConfigBlade3Entry 8}
         apexOutputTsConfigBlade4                         OBJECT IDENTIFIER ::= {apexOutputTsConfig 6}
--          apexOutputTsConfBlade4ApplyTable                                    {apexOutputTsConfigBlade4 1}
--             apexOutputTsConfBlade4ApplyEntry                                 {apexOutputTsConfBlade4ApplyTable 1}
--                apexOutputTsConfBlade4ApplyIndex                              {apexOutputTsConfBlade4ApplyEntry 1}
--                apexOutputTsConfBlade4ApplyChange                             {apexOutputTsConfBlade4ApplyEntry 2}
--          apexOutputTsConfigBlade4Table                                       {apexOutputTsConfigBlade4 2}
--             apexOutputTsConfigBlade4Entry                                    {apexOutputTsConfigBlade4Table 1}
--                apexOutputTsConfBlade4OutputTsNum                             {apexOutputTsConfigBlade4Entry 1}
--                apexOutputTsConfBlade4PidRemappingMode                        {apexOutputTsConfigBlade4Entry 2}
--                apexOutputTsConfBlade4OperatingMode                           {apexOutputTsConfigBlade4Entry 3}
--                apexOutputTsConfBlade4OutPatTsId                              {apexOutputTsConfigBlade4Entry 4}
--                apexOutputTsConfBlade4EncryptionType                          {apexOutputTsConfigBlade4Entry 5}
--                apexOutputTsConfBlade4SimulcryptMode                          {apexOutputTsConfigBlade4Entry 6}
--                apexOutputTsConfBlade4DepiRemoteId                            {apexOutputTsConfigBlade4Entry 7}
--                apexOutputTsConfBlade4QamReplicationRfPort                    {apexOutputTsConfigBlade4Entry 8}
         apexOutputTsConfigBlade5                         OBJECT IDENTIFIER ::= {apexOutputTsConfig 7}
--          apexOutputTsConfBlade5ApplyTable                                    {apexOutputTsConfigBlade5 1}
--             apexOutputTsConfBlade5ApplyEntry                                 {apexOutputTsConfBlade5ApplyTable 1}
--                apexOutputTsConfBlade5ApplyIndex                              {apexOutputTsConfBlade5ApplyEntry 1}
--                apexOutputTsConfBlade5ApplyChange                             {apexOutputTsConfBlade5ApplyEntry 2}
--          apexOutputTsConfigBlade5Table                                       {apexOutputTsConfigBlade5 2}
--             apexOutputTsConfigBlade5Entry                                    {apexOutputTsConfigBlade5Table 1}
--                apexOutputTsConfBlade5OutputTsNum                             {apexOutputTsConfigBlade5Entry 1}
--                apexOutputTsConfBlade5PidRemappingMode                        {apexOutputTsConfigBlade5Entry 2}
--                apexOutputTsConfBlade5OperatingMode                           {apexOutputTsConfigBlade5Entry 3}
--                apexOutputTsConfBlade5OutPatTsId                              {apexOutputTsConfigBlade5Entry 4}
--                apexOutputTsConfBlade5EncryptionType                          {apexOutputTsConfigBlade5Entry 5}
--                apexOutputTsConfBlade5SimulcryptMode                          {apexOutputTsConfigBlade5Entry 6}
--                apexOutputTsConfBlade5DepiRemoteId                            {apexOutputTsConfigBlade5Entry 7}
--                apexOutputTsConfBlade5QamReplicationRfPort                    {apexOutputTsConfigBlade5Entry 8}
         apexOutputTsConfigBlade6                         OBJECT IDENTIFIER ::= {apexOutputTsConfig 8}
--          apexOutputTsConfBlade6ApplyTable                                    {apexOutputTsConfigBlade6 1}
--             apexOutputTsConfBlade6ApplyEntry                                 {apexOutputTsConfBlade6ApplyTable 1}
--                apexOutputTsConfBlade6ApplyIndex                              {apexOutputTsConfBlade6ApplyEntry 1}
--                apexOutputTsConfBlade6ApplyChange                             {apexOutputTsConfBlade6ApplyEntry 2}
--          apexOutputTsConfigBlade6Table                                       {apexOutputTsConfigBlade6 2}
--             apexOutputTsConfigBlade6Entry                                    {apexOutputTsConfigBlade6Table 1}
--                apexOutputTsConfBlade6OutputTsNum                             {apexOutputTsConfigBlade6Entry 1}
--                apexOutputTsConfBlade6PidRemappingMode                        {apexOutputTsConfigBlade6Entry 2}
--                apexOutputTsConfBlade6OperatingMode                           {apexOutputTsConfigBlade6Entry 3}
--                apexOutputTsConfBlade6OutPatTsId                              {apexOutputTsConfigBlade6Entry 4}
--                apexOutputTsConfBlade6EncryptionType                          {apexOutputTsConfigBlade6Entry 5}
--                apexOutputTsConfBlade6SimulcryptMode                          {apexOutputTsConfigBlade6Entry 6}
--                apexOutputTsConfBlade6DepiRemoteId                            {apexOutputTsConfigBlade6Entry 7}
--                apexOutputTsConfBlade6QamReplicationRfPort                    {apexOutputTsConfigBlade6Entry 8}
         apexOutputTsConfigBlade7                         OBJECT IDENTIFIER ::= {apexOutputTsConfig 9}
--          apexOutputTsConfBlade7ApplyTable                                    {apexOutputTsConfigBlade7 1}
--             apexOutputTsConfBlade7ApplyEntry                                 {apexOutputTsConfBlade7ApplyTable 1}
--                apexOutputTsConfBlade7ApplyIndex                              {apexOutputTsConfBlade7ApplyEntry 1}
--                apexOutputTsConfBlade7ApplyChange                             {apexOutputTsConfBlade7ApplyEntry 2}
--          apexOutputTsConfigBlade7Table                                       {apexOutputTsConfigBlade7 2}
--             apexOutputTsConfigBlade7Entry                                    {apexOutputTsConfigBlade7Table 1}
--                apexOutputTsConfBlade7OutputTsNum                             {apexOutputTsConfigBlade7Entry 1}
--                apexOutputTsConfBlade7PidRemappingMode                        {apexOutputTsConfigBlade7Entry 2}
--                apexOutputTsConfBlade7OperatingMode                           {apexOutputTsConfigBlade7Entry 3}
--                apexOutputTsConfBlade7OutPatTsId                              {apexOutputTsConfigBlade7Entry 4}
--                apexOutputTsConfBlade7EncryptionType                          {apexOutputTsConfigBlade7Entry 5}
--                apexOutputTsConfBlade7SimulcryptMode                          {apexOutputTsConfigBlade7Entry 6}
--                apexOutputTsConfBlade7DepiRemoteId                            {apexOutputTsConfigBlade7Entry 7}
--                apexOutputTsConfBlade7QamReplicationRfPort                    {apexOutputTsConfigBlade7Entry 8}
         apexOutputTsConfigBlade8                         OBJECT IDENTIFIER ::= {apexOutputTsConfig 10}
--          apexOutputTsConfBlade8ApplyTable                                    {apexOutputTsConfigBlade8 1}
--             apexOutputTsConfBlade8ApplyEntry                                 {apexOutputTsConfBlade8ApplyTable 1}
--                apexOutputTsConfBlade8ApplyIndex                              {apexOutputTsConfBlade8ApplyEntry 1}
--                apexOutputTsConfBlade8ApplyChange                             {apexOutputTsConfBlade8ApplyEntry 2}
--          apexOutputTsConfigBlade8Table                                       {apexOutputTsConfigBlade8 2}
--             apexOutputTsConfigBlade8Entry                                    {apexOutputTsConfigBlade8Table 1}
--                apexOutputTsConfBlade8OutputTsNum                             {apexOutputTsConfigBlade8Entry 1}
--                apexOutputTsConfBlade8PidRemappingMode                        {apexOutputTsConfigBlade8Entry 2}
--                apexOutputTsConfBlade8OperatingMode                           {apexOutputTsConfigBlade8Entry 3}
--                apexOutputTsConfBlade8OutPatTsId                              {apexOutputTsConfigBlade8Entry 4}
--                apexOutputTsConfBlade8EncryptionType                          {apexOutputTsConfigBlade8Entry 5}
--                apexOutputTsConfBlade8SimulcryptMode                          {apexOutputTsConfigBlade8Entry 6}
--                apexOutputTsConfBlade8DepiRemoteId                            {apexOutputTsConfigBlade8Entry 7}
--                apexOutputTsConfBlade8QamReplicationRfPort                    {apexOutputTsConfigBlade8Entry 8}
      apexOutputTsStatus                                  OBJECT IDENTIFIER ::= {apexOutputTransport 2}
         apexOutputTsStatusGeneral                        OBJECT IDENTIFIER ::= {apexOutputTsStatus 1}
         apexOutputTsUtilization                          OBJECT IDENTIFIER ::= {apexOutputTsStatus 2}
            apexOutputTsUtilizationGeneral                OBJECT IDENTIFIER ::= {apexOutputTsUtilization 1}
--             apexOutputTsUtilizationSamplePeriod                              {apexOutputTsUtilizationGeneral 1}
--          apexOutputTsUtilizationTable                                        {apexOutputTsUtilization 2}
--             apexOutputTsUtilizationEntry                                     {apexOutputTsUtilizationTable 1}
--                apexOutputTsUtilizBladeNum                                    {apexOutputTsUtilizationEntry 1}
--                apexOutputTsUtilizOutputTsNum                                 {apexOutputTsUtilizationEntry 2}
--                apexOutputTsUtilizDataFlag                                    {apexOutputTsUtilizationEntry 3}
--                apexOutputTsUtilizNumSamples                                  {apexOutputTsUtilizationEntry 4}
--                apexOutputTsUtilizThreshold                                   {apexOutputTsUtilizationEntry 5}
--                apexOutputTsUtilizTime                                        {apexOutputTsUtilizationEntry 6}
--                apexOutputTsUtilizCurPercent                                  {apexOutputTsUtilizationEntry 7}
--                apexOutputTsUtilizAvgPercent                                  {apexOutputTsUtilizationEntry 8}
--                apexOutputTsUtilizMinPercent                                  {apexOutputTsUtilizationEntry 9}
--                apexOutputTsUtilizPeakPercent                                 {apexOutputTsUtilizationEntry 10}
--                apexOutputTsUtilizCurRate                                     {apexOutputTsUtilizationEntry 11}
--                apexOutputTsUtilizAvgRate                                     {apexOutputTsUtilizationEntry 12}
--                apexOutputTsUtilizMinRate                                     {apexOutputTsUtilizationEntry 13}
--                apexOutputTsUtilizPeakRate                                    {apexOutputTsUtilizationEntry 14}
--                apexOutputTsUtilizThresholdAlarm                              {apexOutputTsUtilizationEntry 15}
--       apexOutputTsStatusTable                                                {apexOutputTsStatus 5}
--          apexOutputTsStatusEntry                                             {apexOutputTsStatusTable 1}
--             apexOutputTsStatusBladeNum                                       {apexOutputTsStatusEntry 1}
--             apexOutputTsStatusOutputTsNum                                    {apexOutputTsStatusEntry 2}
--             apexOutputTsStatusFault                                          {apexOutputTsStatusEntry 3}
--       apexOutputTsOverflowTable                                              {apexOutputTsStatus 6}
--          apexOutputTsOverflowEntry                                           {apexOutputTsOverflowTable 1}
--             apexOutputTsOverflowBladeNum                                     {apexOutputTsOverflowEntry 1}
--             apexOutputTsOverflowOutputTsNum                                  {apexOutputTsOverflowEntry 2}
--             apexOutputTsOverflowCurDropPackets                               {apexOutputTsOverflowEntry 3}
--             apexOutputTsOverflowTotalDropPackets                             {apexOutputTsOverflowEntry 4}
--             apexOutputTsOverflowAlarm                                        {apexOutputTsOverflowEntry 5}
--       apexOutputTsStatApplyTable                                             {apexOutputTsStatus 7}
--          apexOutputTsStatApplyEntry                                          {apexOutputTsStatApplyTable 1}
--             apexOutputTsStatApplyBladeNum                                    {apexOutputTsStatApplyEntry 1}
--             apexOutputTsStatusInvalidApplyText                               {apexOutputTsStatApplyEntry 2}
   apexPsi                                                OBJECT IDENTIFIER ::= {apex3000 14}
      apexPsiConfig                                       OBJECT IDENTIFIER ::= {apexPsi 1}
         apexPsiConfigGeneral                             OBJECT IDENTIFIER ::= {apexPsiConfig 1}
--          apexPsiDetectUnicastTimeout                                         {apexPsiConfigGeneral 1}
--          apexPsiDetectMulticastTimeout                                       {apexPsiConfigGeneral 2}
--          apexPsiRangeStart                                                   {apexPsiConfigGeneral 3}
--          apexPsiRangeStop                                                    {apexPsiConfigGeneral 4}
--          apexPatVersionIncrement                                             {apexPsiConfigGeneral 5}
--          apexPmtVersionIncrement                                             {apexPsiConfigGeneral 6}
--          apexEcmEmmFirstPid                                                  {apexPsiConfigGeneral 7}
--          apexEcmEmmNumberPids                                                {apexPsiConfigGeneral 8}
--          apexProgramBasedPmtOffset                                           {apexPsiConfigGeneral 9}
--          apexSupportPreencryptedSimulcrypt                                   {apexPsiConfigGeneral 10}
      apexPsiStatus                                       OBJECT IDENTIFIER ::= {apexPsi 2}
         apexPsiStatusGeneral                             OBJECT IDENTIFIER ::= {apexPsiStatus 1}
--       apexPsiStatusInputTable                                                {apexPsiStatus 2}
--          apexPsiStatusInputEntry                                             {apexPsiStatusInputTable 1}
--             apexPsiStatusInputBladeNum                                       {apexPsiStatusInputEntry 1}
--             apexPsiStatusInputIndex                                          {apexPsiStatusInputEntry 2}
--             apexPsiStatusInputPid                                            {apexPsiStatusInputEntry 3}
--             apexPsiStatusInputMessageType                                    {apexPsiStatusInputEntry 4}
--             apexPsiStatusInputProgramNumber                                  {apexPsiStatusInputEntry 5}
--             apexPsiStatusInputSegment                                        {apexPsiStatusInputEntry 6}
--             apexPsiStatusInputPart                                           {apexPsiStatusInputEntry 7}
--             apexPsiStatusInputBody                                           {apexPsiStatusInputEntry 8}
--             apexPsiStatusInputGpsTime                                        {apexPsiStatusInputEntry 9}
--             apexPsiStatusInputMissingTime                                    {apexPsiStatusInputEntry 10}
--             apexPsiStatusInputInfo                                           {apexPsiStatusInputEntry 11}
--       apexPsiStatusOutputTable                                               {apexPsiStatus 3}
--          apexPsiStatusOutputEntry                                            {apexPsiStatusOutputTable 1}
--             apexPsiStatusOutputBladeNum                                      {apexPsiStatusOutputEntry 1}
--             apexPsiStatusOutputIndex                                         {apexPsiStatusOutputEntry 2}
--             apexPsiStatusOutputPid                                           {apexPsiStatusOutputEntry 3}
--             apexPsiStatusOutputMessageType                                   {apexPsiStatusOutputEntry 4}
--             apexPsiStatusOutputProgramNumber                                 {apexPsiStatusOutputEntry 5}
--             apexPsiStatusOutputSegment                                       {apexPsiStatusOutputEntry 6}
--             apexPsiStatusOutputPart                                          {apexPsiStatusOutputEntry 7}
--             apexPsiStatusOutputBody                                          {apexPsiStatusOutputEntry 8}
--             apexPsiStatusOutputGpsTime                                       {apexPsiStatusOutputEntry 9}
   apexOutputProgram                                      OBJECT IDENTIFIER ::= {apex3000 15}
      apexOutputProgramConfig                             OBJECT IDENTIFIER ::= {apexOutputProgram 1}
         apexOutputProgramConfigGeneral                   OBJECT IDENTIFIER ::= {apexOutputProgramConfig 1}
      apexOutputProgramStatus                             OBJECT IDENTIFIER ::= {apexOutputProgram 2}
         apexOutputProgramStatusGeneral                   OBJECT IDENTIFIER ::= {apexOutputProgramStatus 1}
--       apexOutputProgramTable                                                 {apexOutputProgramStatus 2}
--          apexOutputProgramEntry                                              {apexOutputProgramTable 1}
--             apexOutputProgramBladeNum                                        {apexOutputProgramEntry 1}
--             apexOutputProgramOutputTsNum                                     {apexOutputProgramEntry 2}
--             apexOutputProgramOutputProgNum                                   {apexOutputProgramEntry 3}
--             apexOutputProgramInputTsIndex                                    {apexOutputProgramEntry 4}
--             apexOutputProgramInputProgNum                                    {apexOutputProgramEntry 5}
--             apexOutputProgramRoutingStatus                                   {apexOutputProgramEntry 6}
--             apexOutputProgramInputPreEncrypted                               {apexOutputProgramEntry 7}
--             apexOutputProgramError                                           {apexOutputProgramEntry 8}
--             apexOutputProgramEncryptionMode                                  {apexOutputProgramEntry 9}
--             apexOutputProgramEncryptionStatus                                {apexOutputProgramEntry 10}
--             apexOutputProgramEcmServiceId                                    {apexOutputProgramEntry 11}
--             apexOutputProgramCciLevel                                        {apexOutputProgramEntry 12}
--             apexOutputProgramApsLevel                                        {apexOutputProgramEntry 13}
--             apexOutputProgramCitSetting                                      {apexOutputProgramEntry 14}
--             apexOutputProgramNumberTiers                                     {apexOutputProgramEntry 15}
--             apexOutputProgramTierData                                        {apexOutputProgramEntry 16}
--             apexOutputProgramInputInfo                                       {apexOutputProgramEntry 17}
--             apexOutputProgramSourceId                                        {apexOutputProgramEntry 18}
--             apexOutputProgramProviderId                                      {apexOutputProgramEntry 19}
--             apexOutputProgramSourceDescription                               {apexOutputProgramEntry 20}
   apexAcp                                                OBJECT IDENTIFIER ::= {apex3000 16}
      apexAcpConfig                                       OBJECT IDENTIFIER ::= {apexAcp 1}
         apexAcpConfigGeneral                             OBJECT IDENTIFIER ::= {apexAcpConfig 1}
      apexAcpStatus                                       OBJECT IDENTIFIER ::= {apexAcp 2}
         apexAcpStatusGeneral                             OBJECT IDENTIFIER ::= {apexAcpStatus 1}
--       apexAcpStatusTable                                                     {apexAcpStatus 2}
--          apexAcpStatusEntry                                                  {apexAcpStatusTable 1}
--             apexAcpStatusBladeNum                                            {apexAcpStatusEntry 1}
--             apexAcpStatusIndex                                               {apexAcpStatusEntry 2}
--             apexAcpUnitAddress                                               {apexAcpStatusEntry 3}
--             apexAcpHealthByte                                                {apexAcpStatusEntry 4}
--             apexAcpEvenCsn                                                   {apexAcpStatusEntry 5}
--             apexAcpOddCsn                                                    {apexAcpStatusEntry 6}
--             apexAcpUnitAttribute                                             {apexAcpStatusEntry 7}
--       apexAcpStatusModuleTable                                               {apexAcpStatus 3}
--          apexAcpStatusModuleEntry                                            {apexAcpStatusModuleTable 1}
--             apexAcpStatusModuleBladeNum                                      {apexAcpStatusModuleEntry 1}
--             apexAcpStatusModulePresent                                       {apexAcpStatusModuleEntry 2}
--             apexAcpStatusModuleInitState                                     {apexAcpStatusModuleEntry 3}
   apexUdpPortMapping                                     OBJECT IDENTIFIER ::= {apex3000 17}
      apexUdpMapConfig                                    OBJECT IDENTIFIER ::= {apexUdpPortMapping 1}
         apexUdpMapConfigGeneral                          OBJECT IDENTIFIER ::= {apexUdpMapConfig 1}
--          apexUdpMapPreEncryptCheck                                           {apexUdpMapConfigGeneral 1}
--          apexUdpMapTsStartingIndex                                           {apexUdpMapConfigGeneral 2}
--          apexUdpMapFollowDtcp                                                {apexUdpMapConfigGeneral 3}
--          apexUdpMapVirtualIpApplyChange                                      {apexUdpMapConfigGeneral 4}
--          apexUdpMapAlgorithm                                                 {apexUdpMapConfigGeneral 5}
         apexUdpMapBlade1                                 OBJECT IDENTIFIER ::= {apexUdpMapConfig 2}
--          apexUdpMapBlade1ApplyTable                                          {apexUdpMapBlade1 1}
--             apexUdpMapBlade1ApplyEntry                                       {apexUdpMapBlade1ApplyTable 1}
--                apexUdpMapBlade1ApplyOutputTsNum                              {apexUdpMapBlade1ApplyEntry 1}
--                apexUdpMapBlade1ApplyChange                                   {apexUdpMapBlade1ApplyEntry 2}
--                apexUdpMapBlade1InvalidApplyText                              {apexUdpMapBlade1ApplyEntry 3}
--          apexUdpMapBlade1Table                                               {apexUdpMapBlade1 2}
--             apexUdpMapBlade1Entry                                            {apexUdpMapBlade1Table 1}
--                apexUdpMapBlade1OutputTsNum                                   {apexUdpMapBlade1Entry 1}
--                apexUdpMapBlade1StartProgNum                                  {apexUdpMapBlade1Entry 2}
--                apexUdpMapBlade1NumberProgs                                   {apexUdpMapBlade1Entry 3}
--                apexUdpMapBlade1VirtualIpIndex                                {apexUdpMapBlade1Entry 4}
--                apexUdpMapBlade1ConfOutputTsNum                               {apexUdpMapBlade1Entry 5}
--                apexUdpMapBlade1ConfInputInterface                            {apexUdpMapBlade1Entry 6}
--          apexUdpMapBlade1MulticastTable                                      {apexUdpMapBlade1 3}
--             apexUdpMapBlade1MulticastEntry                                   {apexUdpMapBlade1MulticastTable 1}
--                apexUdpMapBlade1MulticastIndex                                {apexUdpMapBlade1MulticastEntry 1}
--                apexUdpMapBlade1MulticastEnable                               {apexUdpMapBlade1MulticastEntry 2}
--                apexUdpMapBlade1MulticastVirtualIpIndex                       {apexUdpMapBlade1MulticastEntry 3}
--                apexUdpMapBlade1MulticastUdp                                  {apexUdpMapBlade1MulticastEntry 4}
--                apexUdpMapBlade1MulticastMcastIp                              {apexUdpMapBlade1MulticastEntry 5}
--                apexUdpMapBlade1MulticastSourceIp                             {apexUdpMapBlade1MulticastEntry 6}
--          apexUdpMapBlade1MulticastApplyTable                                 {apexUdpMapBlade1 4}
--             apexUdpMapBlade1MulticastApplyEntry                              {apexUdpMapBlade1MulticastApplyTable 1}
--                apexUdpMapBlade1MulticastApplyIndex                           {apexUdpMapBlade1MulticastApplyEntry 1}
--                apexUdpMapBlade1MulticastApplyChange                          {apexUdpMapBlade1MulticastApplyEntry 2}
         apexUdpMapBlade2                                 OBJECT IDENTIFIER ::= {apexUdpMapConfig 3}
--          apexUdpMapBlade2ApplyTable                                          {apexUdpMapBlade2 1}
--             apexUdpMapBlade2ApplyEntry                                       {apexUdpMapBlade2ApplyTable 1}
--                apexUdpMapBlade2ApplyOutputTsNum                              {apexUdpMapBlade2ApplyEntry 1}
--                apexUdpMapBlade2ApplyChange                                   {apexUdpMapBlade2ApplyEntry 2}
--                apexUdpMapBlade2InvalidApplyText                              {apexUdpMapBlade2ApplyEntry 3}
--          apexUdpMapBlade2Table                                               {apexUdpMapBlade2 2}
--             apexUdpMapBlade2Entry                                            {apexUdpMapBlade2Table 1}
--                apexUdpMapBlade2OutputTsNum                                   {apexUdpMapBlade2Entry 1}
--                apexUdpMapBlade2StartProgNum                                  {apexUdpMapBlade2Entry 2}
--                apexUdpMapBlade2NumberProgs                                   {apexUdpMapBlade2Entry 3}
--                apexUdpMapBlade2VirtualIpIndex                                {apexUdpMapBlade2Entry 4}
--                apexUdpMapBlade2ConfOutputTsNum                               {apexUdpMapBlade2Entry 5}
--                apexUdpMapBlade2ConfInputInterface                            {apexUdpMapBlade2Entry 6}
--          apexUdpMapBlade2MulticastTable                                      {apexUdpMapBlade2 3}
--             apexUdpMapBlade2MulticastEntry                                   {apexUdpMapBlade2MulticastTable 1}
--                apexUdpMapBlade2MulticastIndex                                {apexUdpMapBlade2MulticastEntry 1}
--                apexUdpMapBlade2MulticastEnable                               {apexUdpMapBlade2MulticastEntry 2}
--                apexUdpMapBlade2MulticastVirtualIpIndex                       {apexUdpMapBlade2MulticastEntry 3}
--                apexUdpMapBlade2MulticastUdp                                  {apexUdpMapBlade2MulticastEntry 4}
--                apexUdpMapBlade2MulticastMcastIp                              {apexUdpMapBlade2MulticastEntry 5}
--                apexUdpMapBlade2MulticastSourceIp                             {apexUdpMapBlade2MulticastEntry 6}
--          apexUdpMapBlade2MulticastApplyTable                                 {apexUdpMapBlade2 4}
--             apexUdpMapBlade2MulticastApplyEntry                              {apexUdpMapBlade2MulticastApplyTable 1}
--                apexUdpMapBlade2MulticastApplyIndex                           {apexUdpMapBlade2MulticastApplyEntry 1}
--                apexUdpMapBlade2MulticastApplyChange                          {apexUdpMapBlade2MulticastApplyEntry 2}
         apexUdpMapBlade3                                 OBJECT IDENTIFIER ::= {apexUdpMapConfig 4}
--          apexUdpMapBlade3ApplyTable                                          {apexUdpMapBlade3 1}
--             apexUdpMapBlade3ApplyEntry                                       {apexUdpMapBlade3ApplyTable 1}
--                apexUdpMapBlade3ApplyOutputTsNum                              {apexUdpMapBlade3ApplyEntry 1}
--                apexUdpMapBlade3ApplyChange                                   {apexUdpMapBlade3ApplyEntry 2}
--                apexUdpMapBlade3InvalidApplyText                              {apexUdpMapBlade3ApplyEntry 3}
--          apexUdpMapBlade3Table                                               {apexUdpMapBlade3 2}
--             apexUdpMapBlade3Entry                                            {apexUdpMapBlade3Table 1}
--                apexUdpMapBlade3OutputTsNum                                   {apexUdpMapBlade3Entry 1}
--                apexUdpMapBlade3StartProgNum                                  {apexUdpMapBlade3Entry 2}
--                apexUdpMapBlade3NumberProgs                                   {apexUdpMapBlade3Entry 3}
--                apexUdpMapBlade3VirtualIpIndex                                {apexUdpMapBlade3Entry 4}
--                apexUdpMapBlade3ConfOutputTsNum                               {apexUdpMapBlade3Entry 5}
--                apexUdpMapBlade3ConfInputInterface                            {apexUdpMapBlade3Entry 6}
--          apexUdpMapBlade3MulticastTable                                      {apexUdpMapBlade3 3}
--             apexUdpMapBlade3MulticastEntry                                   {apexUdpMapBlade3MulticastTable 1}
--                apexUdpMapBlade3MulticastIndex                                {apexUdpMapBlade3MulticastEntry 1}
--                apexUdpMapBlade3MulticastEnable                               {apexUdpMapBlade3MulticastEntry 2}
--                apexUdpMapBlade3MulticastVirtualIpIndex                       {apexUdpMapBlade3MulticastEntry 3}
--                apexUdpMapBlade3MulticastUdp                                  {apexUdpMapBlade3MulticastEntry 4}
--                apexUdpMapBlade3MulticastMcastIp                              {apexUdpMapBlade3MulticastEntry 5}
--                apexUdpMapBlade3MulticastSourceIp                             {apexUdpMapBlade3MulticastEntry 6}
--          apexUdpMapBlade3MulticastApplyTable                                 {apexUdpMapBlade3 4}
--             apexUdpMapBlade3MulticastApplyEntry                              {apexUdpMapBlade3MulticastApplyTable 1}
--                apexUdpMapBlade3MulticastApplyIndex                           {apexUdpMapBlade3MulticastApplyEntry 1}
--                apexUdpMapBlade3MulticastApplyChange                          {apexUdpMapBlade3MulticastApplyEntry 2}
         apexUdpMapBlade4                                 OBJECT IDENTIFIER ::= {apexUdpMapConfig 5}
--          apexUdpMapBlade4ApplyTable                                          {apexUdpMapBlade4 1}
--             apexUdpMapBlade4ApplyEntry                                       {apexUdpMapBlade4ApplyTable 1}
--                apexUdpMapBlade4ApplyOutputTsNum                              {apexUdpMapBlade4ApplyEntry 1}
--                apexUdpMapBlade4ApplyChange                                   {apexUdpMapBlade4ApplyEntry 2}
--                apexUdpMapBlade4InvalidApplyText                              {apexUdpMapBlade4ApplyEntry 3}
--          apexUdpMapBlade4Table                                               {apexUdpMapBlade4 2}
--             apexUdpMapBlade4Entry                                            {apexUdpMapBlade4Table 1}
--                apexUdpMapBlade4OutputTsNum                                   {apexUdpMapBlade4Entry 1}
--                apexUdpMapBlade4StartProgNum                                  {apexUdpMapBlade4Entry 2}
--                apexUdpMapBlade4NumberProgs                                   {apexUdpMapBlade4Entry 3}
--                apexUdpMapBlade4VirtualIpIndex                                {apexUdpMapBlade4Entry 4}
--                apexUdpMapBlade4ConfOutputTsNum                               {apexUdpMapBlade4Entry 5}
--                apexUdpMapBlade4ConfInputInterface                            {apexUdpMapBlade4Entry 6}
--          apexUdpMapBlade4MulticastTable                                      {apexUdpMapBlade4 3}
--             apexUdpMapBlade4MulticastEntry                                   {apexUdpMapBlade4MulticastTable 1}
--                apexUdpMapBlade4MulticastIndex                                {apexUdpMapBlade4MulticastEntry 1}
--                apexUdpMapBlade4MulticastEnable                               {apexUdpMapBlade4MulticastEntry 2}
--                apexUdpMapBlade4MulticastVirtualIpIndex                       {apexUdpMapBlade4MulticastEntry 3}
--                apexUdpMapBlade4MulticastUdp                                  {apexUdpMapBlade4MulticastEntry 4}
--                apexUdpMapBlade4MulticastMcastIp                              {apexUdpMapBlade4MulticastEntry 5}
--                apexUdpMapBlade4MulticastSourceIp                             {apexUdpMapBlade4MulticastEntry 6}
--          apexUdpMapBlade4MulticastApplyTable                                 {apexUdpMapBlade4 4}
--             apexUdpMapBlade4MulticastApplyEntry                              {apexUdpMapBlade4MulticastApplyTable 1}
--                apexUdpMapBlade4MulticastApplyIndex                           {apexUdpMapBlade4MulticastApplyEntry 1}
--                apexUdpMapBlade4MulticastApplyChange                          {apexUdpMapBlade4MulticastApplyEntry 2}
         apexUdpMapBlade5                                 OBJECT IDENTIFIER ::= {apexUdpMapConfig 6}
--          apexUdpMapBlade5ApplyTable                                          {apexUdpMapBlade5 1}
--             apexUdpMapBlade5ApplyEntry                                       {apexUdpMapBlade5ApplyTable 1}
--                apexUdpMapBlade5ApplyOutputTsNum                              {apexUdpMapBlade5ApplyEntry 1}
--                apexUdpMapBlade5ApplyChange                                   {apexUdpMapBlade5ApplyEntry 2}
--                apexUdpMapBlade5InvalidApplyText                              {apexUdpMapBlade5ApplyEntry 3}
--          apexUdpMapBlade5Table                                               {apexUdpMapBlade5 2}
--             apexUdpMapBlade5Entry                                            {apexUdpMapBlade5Table 1}
--                apexUdpMapBlade5OutputTsNum                                   {apexUdpMapBlade5Entry 1}
--                apexUdpMapBlade5StartProgNum                                  {apexUdpMapBlade5Entry 2}
--                apexUdpMapBlade5NumberProgs                                   {apexUdpMapBlade5Entry 3}
--                apexUdpMapBlade5VirtualIpIndex                                {apexUdpMapBlade5Entry 4}
--                apexUdpMapBlade5ConfOutputTsNum                               {apexUdpMapBlade5Entry 5}
--                apexUdpMapBlade5ConfInputInterface                            {apexUdpMapBlade5Entry 6}
--          apexUdpMapBlade5MulticastTable                                      {apexUdpMapBlade5 3}
--             apexUdpMapBlade5MulticastEntry                                   {apexUdpMapBlade5MulticastTable 1}
--                apexUdpMapBlade5MulticastIndex                                {apexUdpMapBlade5MulticastEntry 1}
--                apexUdpMapBlade5MulticastEnable                               {apexUdpMapBlade5MulticastEntry 2}
--                apexUdpMapBlade5MulticastVirtualIpIndex                       {apexUdpMapBlade5MulticastEntry 3}
--                apexUdpMapBlade5MulticastUdp                                  {apexUdpMapBlade5MulticastEntry 4}
--                apexUdpMapBlade5MulticastMcastIp                              {apexUdpMapBlade5MulticastEntry 5}
--                apexUdpMapBlade5MulticastSourceIp                             {apexUdpMapBlade5MulticastEntry 6}
--          apexUdpMapBlade5MulticastApplyTable                                 {apexUdpMapBlade5 4}
--             apexUdpMapBlade5MulticastApplyEntry                              {apexUdpMapBlade5MulticastApplyTable 1}
--                apexUdpMapBlade5MulticastApplyIndex                           {apexUdpMapBlade5MulticastApplyEntry 1}
--                apexUdpMapBlade5MulticastApplyChange                          {apexUdpMapBlade5MulticastApplyEntry 2}
         apexUdpMapBlade6                                 OBJECT IDENTIFIER ::= {apexUdpMapConfig 7}
--          apexUdpMapBlade6ApplyTable                                          {apexUdpMapBlade6 1}
--             apexUdpMapBlade6ApplyEntry                                       {apexUdpMapBlade6ApplyTable 1}
--                apexUdpMapBlade6ApplyOutputTsNum                              {apexUdpMapBlade6ApplyEntry 1}
--                apexUdpMapBlade6ApplyChange                                   {apexUdpMapBlade6ApplyEntry 2}
--                apexUdpMapBlade6InvalidApplyText                              {apexUdpMapBlade6ApplyEntry 3}
--          apexUdpMapBlade6Table                                               {apexUdpMapBlade6 2}
--             apexUdpMapBlade6Entry                                            {apexUdpMapBlade6Table 1}
--                apexUdpMapBlade6OutputTsNum                                   {apexUdpMapBlade6Entry 1}
--                apexUdpMapBlade6StartProgNum                                  {apexUdpMapBlade6Entry 2}
--                apexUdpMapBlade6NumberProgs                                   {apexUdpMapBlade6Entry 3}
--                apexUdpMapBlade6VirtualIpIndex                                {apexUdpMapBlade6Entry 4}
--                apexUdpMapBlade6ConfOutputTsNum                               {apexUdpMapBlade6Entry 5}
--                apexUdpMapBlade6ConfInputInterface                            {apexUdpMapBlade6Entry 6}
--          apexUdpMapBlade6MulticastTable                                      {apexUdpMapBlade6 3}
--             apexUdpMapBlade6MulticastEntry                                   {apexUdpMapBlade6MulticastTable 1}
--                apexUdpMapBlade6MulticastIndex                                {apexUdpMapBlade6MulticastEntry 1}
--                apexUdpMapBlade6MulticastEnable                               {apexUdpMapBlade6MulticastEntry 2}
--                apexUdpMapBlade6MulticastVirtualIpIndex                       {apexUdpMapBlade6MulticastEntry 3}
--                apexUdpMapBlade6MulticastUdp                                  {apexUdpMapBlade6MulticastEntry 4}
--                apexUdpMapBlade6MulticastMcastIp                              {apexUdpMapBlade6MulticastEntry 5}
--                apexUdpMapBlade6MulticastSourceIp                             {apexUdpMapBlade6MulticastEntry 6}
--          apexUdpMapBlade6MulticastApplyTable                                 {apexUdpMapBlade6 4}
--             apexUdpMapBlade6MulticastApplyEntry                              {apexUdpMapBlade6MulticastApplyTable 1}
--                apexUdpMapBlade6MulticastApplyIndex                           {apexUdpMapBlade6MulticastApplyEntry 1}
--                apexUdpMapBlade6MulticastApplyChange                          {apexUdpMapBlade6MulticastApplyEntry 2}
         apexUdpMapBlade7                                 OBJECT IDENTIFIER ::= {apexUdpMapConfig 8}
--          apexUdpMapBlade7ApplyTable                                          {apexUdpMapBlade7 1}
--             apexUdpMapBlade7ApplyEntry                                       {apexUdpMapBlade7ApplyTable 1}
--                apexUdpMapBlade7ApplyOutputTsNum                              {apexUdpMapBlade7ApplyEntry 1}
--                apexUdpMapBlade7ApplyChange                                   {apexUdpMapBlade7ApplyEntry 2}
--                apexUdpMapBlade7InvalidApplyText                              {apexUdpMapBlade7ApplyEntry 3}
--          apexUdpMapBlade7Table                                               {apexUdpMapBlade7 2}
--             apexUdpMapBlade7Entry                                            {apexUdpMapBlade7Table 1}
--                apexUdpMapBlade7OutputTsNum                                   {apexUdpMapBlade7Entry 1}
--                apexUdpMapBlade7StartProgNum                                  {apexUdpMapBlade7Entry 2}
--                apexUdpMapBlade7NumberProgs                                   {apexUdpMapBlade7Entry 3}
--                apexUdpMapBlade7VirtualIpIndex                                {apexUdpMapBlade7Entry 4}
--                apexUdpMapBlade7ConfOutputTsNum                               {apexUdpMapBlade7Entry 5}
--                apexUdpMapBlade7ConfInputInterface                            {apexUdpMapBlade7Entry 6}
--          apexUdpMapBlade7MulticastTable                                      {apexUdpMapBlade7 3}
--             apexUdpMapBlade7MulticastEntry                                   {apexUdpMapBlade7MulticastTable 1}
--                apexUdpMapBlade7MulticastIndex                                {apexUdpMapBlade7MulticastEntry 1}
--                apexUdpMapBlade7MulticastEnable                               {apexUdpMapBlade7MulticastEntry 2}
--                apexUdpMapBlade7MulticastVirtualIpIndex                       {apexUdpMapBlade7MulticastEntry 3}
--                apexUdpMapBlade7MulticastUdp                                  {apexUdpMapBlade7MulticastEntry 4}
--                apexUdpMapBlade7MulticastMcastIp                              {apexUdpMapBlade7MulticastEntry 5}
--                apexUdpMapBlade7MulticastSourceIp                             {apexUdpMapBlade7MulticastEntry 6}
--          apexUdpMapBlade7MulticastApplyTable                                 {apexUdpMapBlade7 4}
--             apexUdpMapBlade7MulticastApplyEntry                              {apexUdpMapBlade7MulticastApplyTable 1}
--                apexUdpMapBlade7MulticastApplyIndex                           {apexUdpMapBlade7MulticastApplyEntry 1}
--                apexUdpMapBlade7MulticastApplyChange                          {apexUdpMapBlade7MulticastApplyEntry 2}
         apexUdpMapBlade8                                 OBJECT IDENTIFIER ::= {apexUdpMapConfig 9}
--          apexUdpMapBlade8ApplyTable                                          {apexUdpMapBlade8 1}
--             apexUdpMapBlade8ApplyEntry                                       {apexUdpMapBlade8ApplyTable 1}
--                apexUdpMapBlade8ApplyOutputTsNum                              {apexUdpMapBlade8ApplyEntry 1}
--                apexUdpMapBlade8ApplyChange                                   {apexUdpMapBlade8ApplyEntry 2}
--                apexUdpMapBlade8InvalidApplyText                              {apexUdpMapBlade8ApplyEntry 3}
--          apexUdpMapBlade8Table                                               {apexUdpMapBlade8 2}
--             apexUdpMapBlade8Entry                                            {apexUdpMapBlade8Table 1}
--                apexUdpMapBlade8OutputTsNum                                   {apexUdpMapBlade8Entry 1}
--                apexUdpMapBlade8StartProgNum                                  {apexUdpMapBlade8Entry 2}
--                apexUdpMapBlade8NumberProgs                                   {apexUdpMapBlade8Entry 3}
--                apexUdpMapBlade8VirtualIpIndex                                {apexUdpMapBlade8Entry 4}
--                apexUdpMapBlade8ConfOutputTsNum                               {apexUdpMapBlade8Entry 5}
--                apexUdpMapBlade8ConfInputInterface                            {apexUdpMapBlade8Entry 6}
--          apexUdpMapBlade8MulticastTable                                      {apexUdpMapBlade8 3}
--             apexUdpMapBlade8MulticastEntry                                   {apexUdpMapBlade8MulticastTable 1}
--                apexUdpMapBlade8MulticastIndex                                {apexUdpMapBlade8MulticastEntry 1}
--                apexUdpMapBlade8MulticastEnable                               {apexUdpMapBlade8MulticastEntry 2}
--                apexUdpMapBlade8MulticastVirtualIpIndex                       {apexUdpMapBlade8MulticastEntry 3}
--                apexUdpMapBlade8MulticastUdp                                  {apexUdpMapBlade8MulticastEntry 4}
--                apexUdpMapBlade8MulticastMcastIp                              {apexUdpMapBlade8MulticastEntry 5}
--                apexUdpMapBlade8MulticastSourceIp                             {apexUdpMapBlade8MulticastEntry 6}
--          apexUdpMapBlade8MulticastApplyTable                                 {apexUdpMapBlade8 4}
--             apexUdpMapBlade8MulticastApplyEntry                              {apexUdpMapBlade8MulticastApplyTable 1}
--                apexUdpMapBlade8MulticastApplyIndex                           {apexUdpMapBlade8MulticastApplyEntry 1}
--                apexUdpMapBlade8MulticastApplyChange                          {apexUdpMapBlade8MulticastApplyEntry 2}
         apexUdpMapVirtualIp                              OBJECT IDENTIFIER ::= {apexUdpMapConfig 10}
--          apexUdpMapVirtualIpTable                                            {apexUdpMapVirtualIp 1}
--             apexUdpMapVirtualIpEntry                                         {apexUdpMapVirtualIpTable 1}
--                apexUdpMapVirtualIpIndex                                      {apexUdpMapVirtualIpEntry 1}
--                apexUdpMapVirtualIpInputInterface                             {apexUdpMapVirtualIpEntry 2}
--                apexUdpMapVirtualIpAddress                                    {apexUdpMapVirtualIpEntry 3}
      apexUdpMapStatus                                    OBJECT IDENTIFIER ::= {apexUdpPortMapping 2}
         apexUdpMapStatusGeneral                          OBJECT IDENTIFIER ::= {apexUdpMapStatus 1}
--          apexUdpMapVirtualIpInvalidApplyText                                 {apexUdpMapStatusGeneral 1}
--          apexUdpMapAlgorithmApplyText                                        {apexUdpMapStatusGeneral 2}
--       apexUdpMapStatusTable                                                  {apexUdpMapStatus 2}
--          apexUdpMapStatusEntry                                               {apexUdpMapStatusTable 1}
--             apexUdpMapStatusBladeNum                                         {apexUdpMapStatusEntry 1}
--             apexUdpMapStatusOutputTsIndex                                    {apexUdpMapStatusEntry 2}
--             apexUdpMapStatusStartUdpPort                                     {apexUdpMapStatusEntry 3}
--             apexUdpMapStatusAssignedOutputTsNum                              {apexUdpMapStatusEntry 4}
--             apexUdpMapStatusNumberPrograms                              	  {apexUdpMapStatusEntry 5}
--       apexUdpMapStatusMulticastTable                                         {apexUdpMapStatus 3}
--          apexUdpMapStatusMulticastEntry                                      {apexUdpMapStatusMulticastTable 1}
--             apexUdpMapMulticastBladeNum                                      {apexUdpMapStatusMulticastEntry 1}
--             apexUdpMapMulticastInvalidApplyText                              {apexUdpMapStatusMulticastEntry 2}
--       apexUdpMapVirtualIpInputTsAssignedTable                                {apexUdpMapStatus 4}
--          apexUdpMapVirtualIpInputTsAssignedEntry                             {apexUdpMapVirtualIpInputTsAssignedTable 1}
--             apexUdpMapVirtualIpInputTsIndex                                  {apexUdpMapVirtualIpInputTsAssignedEntry 1}
--             apexUdpMapVirtualIpInputTsAssignedCount                          {apexUdpMapVirtualIpInputTsAssignedEntry 2}

   apexRds                                                OBJECT IDENTIFIER ::= {apex3000 18}
      apexRdsConfig                                       OBJECT IDENTIFIER ::= {apexRds 1}
         apexRdsConfigGeneral                             OBJECT IDENTIFIER ::= {apexRdsConfig 1}
--          apexRdsIpAddr                                                       {apexRdsConfigGeneral 1}
--          apexRdsTcpPort                                                      {apexRdsConfigGeneral 2}
--          apexRdsProgramEpochDuration                                         {apexRdsConfigGeneral 3}
--          apexRdsCetPollInterval                                              {apexRdsConfigGeneral 4}
--          apexRdsCetRefresh                                                   {apexRdsConfigGeneral 5}
--          apexRdsRmdPollInterval                                              {apexRdsConfigGeneral 6}
--          apexRdsRmdRefresh                                                   {apexRdsConfigGeneral 7}
--          apexRdsPollRandomization                                            {apexRdsConfigGeneral 8}
--          apexRdsSetDefault                                                   {apexRdsConfigGeneral 9}
--          apexRdsErrorCountReset                                              {apexRdsConfigGeneral 10}
--          apexRdsConfigApplyChange                                            {apexRdsConfigGeneral 11}
      apexRdsStatus                                       OBJECT IDENTIFIER ::= {apexRds 2}
         apexRdsStatusGeneral                             OBJECT IDENTIFIER ::= {apexRdsStatus 1}
--          apexRdsConnectionStatus                                             {apexRdsStatusGeneral 1}
--          apexRdsCurrentCsn                                                   {apexRdsStatusGeneral 2}
--          apexRdsCetNextPollTime                                              {apexRdsStatusGeneral 3}
--          apexRdsRmdNextPollTime                                              {apexRdsStatusGeneral 4}
--          apexRdsEmmStatusTableSize                                           {apexRdsStatusGeneral 5}
--          apexRdsProgramMessagesReceived                                      {apexRdsStatusGeneral 6}
--          apexRdsProgramMessagesFailed                                        {apexRdsStatusGeneral 7}
--          apexRdsCommErrorCount                                               {apexRdsStatusGeneral 8}
--          apexRdsCommStatus                                                   {apexRdsStatusGeneral 9}
--          apexRdsFlashWriteCount                                              {apexRdsStatusGeneral 10}
--          apexRdsMcast16                                                      {apexRdsStatusGeneral 11}
--       apexRdsEmmStatusTable                                                  {apexRdsStatus 2}
--          apexRdsEmmStatusEntry                                               {apexRdsEmmStatusTable 1}
--             apexRdsEmmStatusIndex                                            {apexRdsEmmStatusEntry 1}
--             apexRdsEmmStatusCsn                                              {apexRdsEmmStatusEntry 2}
--             apexRdsEmmStatusState                                            {apexRdsEmmStatusEntry 3}
--             apexRdsEmmStatusGpsTime                                          {apexRdsEmmStatusEntry 4}
--             apexRdsEmmStatusServerError                                      {apexRdsEmmStatusEntry 5}
--             apexRdsEmmStatusUnitAddress                                      {apexRdsEmmStatusEntry 6}
--       apexRdsSourceLookupTable                                               {apexRdsStatus 3}
--          apexRdsSourceLookupEntry                                            {apexRdsSourceLookupTable 1}
--             apexRdsSourceLookupIndex                                         {apexRdsSourceLookupEntry 1}
--             apexRdsSourceLookupDescription                                   {apexRdsSourceLookupEntry 2}
--             apexRdsSourceLookupSourceId                                      {apexRdsSourceLookupEntry 3}
--             apexRdsSourceLookupProviderId                                    {apexRdsSourceLookupEntry 4}
   apexEncryption                                         OBJECT IDENTIFIER ::= {apex3000 19}
      apexEncryptionConfig                                OBJECT IDENTIFIER ::= {apexEncryption 1}
         apexEncryptionConfigGeneral                      OBJECT IDENTIFIER ::= {apexEncryptionConfig 1}
--       apexEncryptionConfTable                                                {apexEncryptionConfigGeneral 1}
--          apexEncryptionConfEntry                                             {apexEncryptionConfTable 1}
--             apexEncrytionConfBladeNum                                        {apexEncryptionConfEntry 1}
--             apexEncryptionConfAlgorithm                                      {apexEncryptionConfEntry 2}
         apexCteConfig                                    OBJECT IDENTIFIER ::= {apexEncryptionConfig 2}
--          apexCteEncryptionMode                                               {apexCteConfig 1}
--          apexCteCciLevel                                                     {apexCteConfig 2}
--          apexCteApsLevel                                                     {apexCteConfig 3}
--          apexCteCitEnable                                                    {apexCteConfig 4}
--          apexCteCommonTier                                                   {apexCteConfig 5}
--          apexCteApplyChange                                                  {apexCteConfig 6}
      apexEncryptionStatus                                OBJECT IDENTIFIER ::= {apexEncryption 2}
         apexEncryptionStatusGeneral                      OBJECT IDENTIFIER ::= {apexEncryptionStatus 1}
   apexHostModule                                         OBJECT IDENTIFIER ::= {apex3000 20}
      apexHostModuleConfig                                OBJECT IDENTIFIER ::= {apexHostModule 1}
         apexHostModuleConfigGeneral                      OBJECT IDENTIFIER ::= {apexHostModuleConfig 1}
--       apexHostModuleConfTable                                                {apexHostModuleConfigGeneral 2}
--          apexHostModuleConfEntry                                             {apexHostModuleConfTable 1}         
--             apexHostModuleConfResetBladeNum                                  {apexHostModuleConfEntry 1}
--             apexHostModuleConfResetModule                                    {apexHostModuleConfEntry 2}
      apexHostModuleStatus                                OBJECT IDENTIFIER ::= {apexHostModule 2}
         apexHostModuleStatusGeneral                      OBJECT IDENTIFIER ::= {apexHostModuleStatus 1}
--       apexHostModuleStatusTable                                              {apexHostModuleStatus 2}
--          apexHostModuleStatusEntry                                           {apexHostModuleStatusTable 1}         
--             apexHostModuleStatusBladeNum                                     {apexHostModuleStatusEntry 1}
--             apexHostModuleStatusFault                                        {apexHostModuleStatusEntry 2}
      apexHostModuleRedundancy                            OBJECT IDENTIFIER ::= {apexHostModule 3}
         apexHostRedundConfig                             OBJECT IDENTIFIER ::= {apexHostModuleRedundancy 1}
            apexHostRedundConfigGeneral                   OBJECT IDENTIFIER ::= {apexHostRedundConfig 1}
--             apexHostRedundConfigApplyChange                                  {apexHostRedundConfigGeneral 1}
--             apexHostRedundSuspendFailover                                    {apexHostRedundConfigGeneral 2}
--             apexHostRedundForceSwitchover                                    {apexHostRedundConfigGeneral 3}
--             apexHostRedundTriggerEnet2LinkLoss                               {apexHostRedundConfigGeneral 4}
--             apexHostRedundTriggerTemperature                                 {apexHostRedundConfigGeneral 5}
--             apexHostRedundTriggerEnet1LinkLoss                               {apexHostRedundConfigGeneral 6}
--             apexHostRedundTriggerEnetTimer                                   {apexHostRedundConfigGeneral 7}
         apexHostRedundStatus                             OBJECT IDENTIFIER ::= {apexHostModuleRedundancy 2}
            apexHostRedundStatusGeneral                   OBJECT IDENTIFIER ::= {apexHostRedundStatus 1}
--             apexHostRedundInvalidApplyText                                   {apexHostRedundStatusGeneral 1}
--             apexHostRedundSystemStatus                                       {apexHostRedundStatusGeneral 2}
--          apexHostRedundStatusTable                                           {apexHostRedundStatus 2}
--             apexHostRedundStatusEntry                                        {apexHostRedundStatusTable 1}
--                apexHostRedundStatusHostNum                                   {apexHostRedundStatusEntry 1}
--                apexHostRedundStatusState                                     {apexHostRedundStatusEntry 2}
--                apexHostRedundStatusReleaseVersion                            {apexHostRedundStatusEntry 3}
   apexQamBlade                                           OBJECT IDENTIFIER ::= {apex3000 21}
      apexQamBladeConfig                                  OBJECT IDENTIFIER ::= {apexQamBlade 1}
         apexQamBladeConfigGeneral                        OBJECT IDENTIFIER ::= {apexQamBladeConfig 1}
--       apexQamBladeConfigShutdownTable                                        {apexQamBladeConfig 2}
--          apexQamBladeConfigShutdownEntry                                     {apexQamBladeConfigShutdownTable 1}
--             apexQamBladeConfigBladeNum                                       {apexQamBladeConfigShutdownEntry 1}
--             apexQamBladeConfigShutdown                                       {apexQamBladeConfigShutdownEntry 2}
      apexQamBladeStatus                                  OBJECT IDENTIFIER ::= {apexQamBlade 2}
         apexQamBladeStatusGeneral                        OBJECT IDENTIFIER ::= {apexQamBladeStatus 1}
--       apexQamBladeStatusTable                                                {apexQamBladeStatus 2}
--          apexQamBladeStatusEntry                                             {apexQamBladeStatusTable 1}
--             apexQamBladeStatusBladeNum                                       {apexQamBladeStatusEntry 1}
--             apexQamBladeStatusFaultSummary                                   {apexQamBladeStatusEntry 2}
--             apexQamBladeStatusFaultCondition                                 {apexQamBladeStatusEntry 3}
--             apexQamBladeStatusRfAlarmSummary                                 {apexQamBladeStatusEntry 4}
--             apexQamBladeStatusNpuCommFault                                   {apexQamBladeStatusEntry 5}
--             apexQamBladeStatusInitError                                      {apexQamBladeStatusEntry 6}
--             apexQamBladeStatusServiceFault                                   {apexQamBladeStatusEntry 7}
--             apexQamBladeStatusOtsOverflowFault                               {apexQamBladeStatusEntry 8}
--             apexQamBladeStatusOtsUtilFault                                   {apexQamBladeStatusEntry 9}
--             apexQamBladeStatusLink                                           {apexQamBladeStatusEntry 10}
--             apexQamBladeStatusPacketPassCount                                {apexQamBladeStatusEntry 11}
--             apexQamBladeStatusPacketDropCount                                {apexQamBladeStatusEntry 12}
--             apexQamBladeStatusServiceInactiveFault                           {apexQamBladeStatusEntry 13}
--       apexQamBladeOverflowTable                                              {apexQamBladeStatus 3}
--          apexQamBladeOverflowEntry                                           {apexQamBladeOverflowTable 1}
--             apexQamBladeOverflowBladeNum                                     {apexQamBladeOverflowEntry 1}
--             apexQamBladeGbeSwitchOverflowError                               {apexQamBladeOverflowEntry 2}
--             apexQamBladeIngressOverflowError                                 {apexQamBladeOverflowEntry 3}
--             apexQamBladeNpuOverflowError                                     {apexQamBladeOverflowEntry 4}  
--       apexQamBladeIngressTable                                               {apexQamBladeStatus 4}
--          apexQamBladeIngressEntry                                            {apexQamBladeIngressTable 1}
--             apexQamBladeIngressBladeNum                                      {apexQamBladeIngressEntry 1}
--             apexQamBladeIngressInputUdpPackets                               {apexQamBladeIngressEntry 2}
--             apexQamBladeIngressDiscardedPackets                              {apexQamBladeIngressEntry 3}
--             apexQamBladeIngressOverflowedPackets                             {apexQamBladeIngressEntry 4}
--             apexQamBladeIngressInputCurStreamCount                           {apexQamBladeIngressEntry 5}
--             apexQamBladeIngressInputTotStreamCount                           {apexQamBladeIngressEntry 6}
--             apexQamBladeIngressOutputCurStreamCount                          {apexQamBladeIngressEntry 7}
--             apexQamBladeIngressOutputTotStreamCount                          {apexQamBladeIngressEntry 8}
--       apexQamBladeInputTsTable                                               {apexQamBladeStatus 5}
--          apexQamBladeInputTsEntry                                            {apexQamBladeInputTsTable 1}
--             apexQamBladeInputTsBladeNum                                      {apexQamBladeInputTsEntry 1}
--             apexQamBladeInputTsCount                                         {apexQamBladeInputTsEntry 2}
--       apexQamBladeRfStatusTable                                              {apexQamBladeStatus 6}
--          apexQamBladeRfStatusEntry                                           {apexQamBladeRfStatusTable 1}
--             apexQamBladeRfStatusBladeNum                                     {apexQamBladeRfStatusEntry 1}
--             apexQamBladeRfStatusPortNum                                      {apexQamBladeRfStatusEntry 2}
--             apexQamBladeRfStatusFault                                        {apexQamBladeRfStatusEntry 3}
--             apexQamBladeRfStatusServiceFault                                 {apexQamBladeRfStatusEntry 4}
--             apexQamBladeRfStatusOtsOverflowFault                             {apexQamBladeRfStatusEntry 5}
--             apexQamBladeRfStatusOtsUtilFault                                 {apexQamBladeRfStatusEntry 6}
--             apexQamBladeRfNumServicesInError                                 {apexQamBladeRfStatusEntry 7}
--             apexQamBladeRfNumOtsOverflowErrors                               {apexQamBladeRfStatusEntry 8}
--             apexQamBladeRfNumOtsUtilErrors                                   {apexQamBladeRfStatusEntry 9}
--       apexQamBladeNpuStatusTable                                             {apexQamBladeStatus 7}
--          apexQamBladeNpuStatusEntry                                          {apexQamBladeNpuStatusTable 1}
--             apexQamBladeNpuStatusBladeNum                                    {apexQamBladeNpuStatusEntry 1}
--             apexQamBladeNpuStatusInputPackets                                {apexQamBladeNpuStatusEntry 2}
--             apexQamBladeNpuStatusInputPacketRate                             {apexQamBladeNpuStatusEntry 3}
--             apexQamBladeNpuStatusInputPacketErrors                           {apexQamBladeNpuStatusEntry 4}
--             apexQamBladeNpuStatusInputPacketDrops1                           {apexQamBladeNpuStatusEntry 5}
--             apexQamBladeNpuStatusInputPacketDrops2                           {apexQamBladeNpuStatusEntry 6}
      apexQamBladeRedundancy                              OBJECT IDENTIFIER ::= {apexQamBlade 3}
         apexQamBladeRedundancyConfig                     OBJECT IDENTIFIER ::= {apexQamBladeRedundancy 1}
            apexQamBladeRedundancyConfigGeneral           OBJECT IDENTIFIER ::= {apexQamBladeRedundancyConfig 1}
--             apexQamBladeRedundConfigApplyChange                              {apexQamBladeRedundancyConfigGeneral 1}
--             apexQamBladeRedundConfigEnable                                   {apexQamBladeRedundancyConfigGeneral 2}
--             apexQamBladeRedundConfigAutoSwitchBack                           {apexQamBladeRedundancyConfigGeneral 3}
--             apexQamBladeRedundConfigSuspendFailover                          {apexQamBladeRedundancyConfigGeneral 4}
--             apexQamBladeRedundConfigForceSwitch                              {apexQamBladeRedundancyConfigGeneral 5}
--             apexQamBladeRedundConfigDefaultRfConfBlade                       {apexQamBladeRedundancyConfigGeneral 6}
         apexQamBladeRedundancyStatus                     OBJECT IDENTIFIER ::= {apexQamBladeRedundancy 2}
            apexQamBladeRedundancyStatusGeneral           OBJECT IDENTIFIER ::= {apexQamBladeRedundancyStatus 1}
--             apexQamBladeRedundStatusInvalidApplyText                         {apexQamBladeRedundancyStatusGeneral 1}
--             apexQamBladeRedundStatusMismatch                                 {apexQamBladeRedundancyStatusGeneral 2}
--             apexQamBladeRedundStatusBackupBlade                              {apexQamBladeRedundancyStatusGeneral 3}
--             apexQamBladeRedundStatusFailedBlade                              {apexQamBladeRedundancyStatusGeneral 4}
--             apexQamBladeRedundStatusFailoverForced                           {apexQamBladeRedundancyStatusGeneral 5}
--             apexQamBladeRedundStatusForceSwitchText                          {apexQamBladeRedundancyStatusGeneral 6}
   apexRfModule                                           OBJECT IDENTIFIER ::= {apex3000 22}
      apexRfModuleConfig                                  OBJECT IDENTIFIER ::= {apexRfModule 1}
         apexRfModuleConfigGeneral                        OBJECT IDENTIFIER ::= {apexRfModuleConfig 1}
      apexRfModuleStatus                                  OBJECT IDENTIFIER ::= {apexRfModule 2}
         apexRfModuleStatusGeneral                        OBJECT IDENTIFIER ::= {apexRfModuleStatus 1}
--       apexRfModuleStatusTable                                                {apexRfModuleStatus 2}
--          apexRfModuleStatusEntry                                             {apexRfModuleStatusTable 1}
--             apexRfModuleStatusBladeNum                                       {apexRfModuleStatusEntry 1}
--             apexRfModuleStatusFaultCondition                                 {apexRfModuleStatusEntry 2}
--             apexRfModuleStatusInitError                                      {apexRfModuleStatusEntry 3}
--             apexRfModuleStatusMasterClockLock                                {apexRfModuleStatusEntry 4}
--             apexRfModuleStatusRefernceClockLock                              {apexRfModuleStatusEntry 5}
--             apexRfModuleStatusInputPortError                                 {apexRfModuleStatusEntry 6}
--             apexRfModuleStatus5VoltSupplyError                               {apexRfModuleStatusEntry 7}
--             apexRfModuleStatus8VoltSupplyError                               {apexRfModuleStatusEntry 8}
--             apexRfModuleStatusInternalPowerError                             {apexRfModuleStatusEntry 9}
--             apexRfModuleStatus5VoltSupplyLevel                               {apexRfModuleStatusEntry 10}
--             apexRfModuleStatus8VoltSupplyLevel                               {apexRfModuleStatusEntry 11}
--             apexRfModuleStatusCommunicationError                             {apexRfModuleStatusEntry 12}
--             apexRfModuleStatusCodeFileDownload                               {apexRfModuleStatusEntry 13}
   apexRouting                                            OBJECT IDENTIFIER ::= {apex3000 23}
      apexRoutingConfig                                   OBJECT IDENTIFIER ::= {apexRouting 1}
         apexRoutingConfigGeneral                         OBJECT IDENTIFIER ::= {apexRoutingConfig 1}
      apexRoutingStatus                                   OBJECT IDENTIFIER ::= {apexRouting 2}
         apexRoutingStatusGeneral                         OBJECT IDENTIFIER ::= {apexRoutingStatus 1}
--          apexMaxOutputTsServiceMappings                                      {apexRoutingStatusGeneral 1}
--          apexTotalServicesMapped                                             {apexRoutingStatusGeneral 2}
--          apexTotalPassThruTsMapped                                           {apexRoutingStatusGeneral 3}
--          apexTotalPidsMapped                                                 {apexRoutingStatusGeneral 4}
--          apexTotalManualRouteServices                                        {apexRoutingStatusGeneral 5}
--          apexTotalSessionsServices                                           {apexRoutingStatusGeneral 6}
--          apexTotalUdpPortServices                                            {apexRoutingStatusGeneral 7}
--          apexTotalNumServicesInError                                         {apexRoutingStatusGeneral 8}
--          apexTotalDepiControlConnections                                     {apexRoutingStatusGeneral 9}
--          apexTotalDepiCntlMsgsDiscarded                                      {apexRoutingStatusGeneral 10}
--          apexTotalDepiDataMsgsDiscarded                                      {apexRoutingStatusGeneral 11}  
--          apexTotalNumDepiSessions                                            {apexRoutingStatusGeneral 12}
--          apexTotalNumPriDepiSessions                                         {apexRoutingStatusGeneral 13}
--       apexRoutingStatusBladeTable                                            {apexRoutingStatus 2}
--          apexRoutingStatusBladeEntry                                         {apexRoutingStatusBladeTable 1}
--             apexRoutingStatusBladeNum                                        {apexRoutingStatusBladeEntry 1}
--             apexQamBladeServicesMapped                                       {apexRoutingStatusBladeEntry 2}
--             apexQamBladePassThrusMapped                                      {apexRoutingStatusBladeEntry 3}
--             apexQamBladePidsMapped                                           {apexRoutingStatusBladeEntry 4}
--             apexQamBladeManualRouteServices                                  {apexRoutingStatusBladeEntry 5}
--             apexQamBladeSessionsServices                                     {apexRoutingStatusBladeEntry 6}
--             apexQamBladeUdpPortServices                                      {apexRoutingStatusBladeEntry 7}
--             apexQamBladeNumServicesInError                                   {apexRoutingStatusBladeEntry 8}
--             apexQamBladeActiveServicesMapped                                 {apexRoutingStatusBladeEntry 9}
--             apexQamBladeActivePassThrusMapped                                {apexRoutingStatusBladeEntry 10}
--             apexQamBladeActivePidsMapped                                     {apexRoutingStatusBladeEntry 11}
--             apexQamBladeInactiveServicesMapped                               {apexRoutingStatusBladeEntry 12}
--             apexQamBladeMultiplexedServicesMapped                            {apexRoutingStatusBladeEntry 13}
--             apexQamBladeDepiSessionsMapped                                   {apexRoutingStatusBladeEntry 14}
--             apexQamBladeDepiPriSessionsMapped                                {apexRoutingStatusBladeEntry 15}
--             apexQamBladeSimScgsProvisioned                                   {apexRoutingStatusBladeEntry 16}
--             apexQamBladeReplicatedServicesMapped                             {apexRoutingStatusBladeEntry 17}
--             apexQamBladeReplicatedPidsMapped                                 {apexRoutingStatusBladeEntry 18}
--       apexRoutingStatusOtsTable                                              {apexRoutingStatus 3}
--          apexRoutingStatusOtsEntry                                           {apexRoutingStatusOtsTable 1}
--             apexRoutingStatusOtsBladeNum                                     {apexRoutingStatusOtsEntry 1}
--             apexRoutingStatusOtsNum                                          {apexRoutingStatusOtsEntry 2}
--             apexOutputTsServicesMapped                                       {apexRoutingStatusOtsEntry 3}
--             apexOutputTsPassThrusMapped                                      {apexRoutingStatusOtsEntry 4}
--             apexOutputTsPidsMapped                                           {apexRoutingStatusOtsEntry 5}
--             apexOutputTsServicesInError                                      {apexRoutingStatusOtsEntry 6}
--             apexOutputTsDepiSessionMappings                                  {apexRoutingStatusOtsEntry 7}
--       apexRoutingStatusOtsSimTable                                           {apexRoutingStatus 4}
--          apexRoutingStatusOtsSimEntry                                        {apexRoutingStatusOtsSimTable 1}
--             apexRoutingStatusOtsSimBladeNum                                  {apexRoutingStatusOtsSimEntry 1}
--             apexRoutingStatusOtsSimOtsNum                                    {apexRoutingStatusOtsSimEntry 2}
--             apexRoutingStatusOtsSimScgsProvisioned                           {apexRoutingStatusOtsSimEntry 3}

   apexLiveUpgrade                                        OBJECT IDENTIFIER ::= {apex3000 24}
      apexLiveUpgradeConfig                               OBJECT IDENTIFIER ::= {apexLiveUpgrade 1}
         apexLiveUpgradeConfigGeneral                     OBJECT IDENTIFIER ::= {apexLiveUpgradeConfig 1}
--          apexLiveUpgradeRequest                                              {apexLiveUpgradeConfigGeneral 1}
--          apexLiveUpgradeOperation                                            {apexLiveUpgradeConfigGeneral 2}
--          apexLiveUpgradeRequestedFile                                        {apexLiveUpgradeConfigGeneral 3}
--          apexLiveUpgradeMode                                                 {apexLiveUpgradeConfigGeneral 4}
      apexLiveUpgradeStatus                               OBJECT IDENTIFIER ::= {apexLiveUpgrade 2}
         apexLiveUpgradeStatusGeneral                     OBJECT IDENTIFIER ::= {apexLiveUpgradeStatus 1}
--          apexLiveUpgradeStatusText                                           {apexLiveUpgradeStatusGeneral 1}
   apexBladeFan                                           OBJECT IDENTIFIER ::= {apex3000 25}
      apexBladeFanConfig                                  OBJECT IDENTIFIER ::= {apexBladeFan 1}
         apexBladeFanConfigGeneral                        OBJECT IDENTIFIER ::= {apexBladeFanConfig 1}
      apexBladeFanStatus                                  OBJECT IDENTIFIER ::= {apexBladeFan 2}
         apexBladeFanStatusGeneral                        OBJECT IDENTIFIER ::= {apexBladeFanStatus 1}
--       apexBladeFanStatusTable                                                {apexBladeFanStatus 2}
--          apexBladeFanStatusEntry                                             {apexBladeFanStatusTable 1}
--            apexBladeFanStatusBladeNum                                        {apexBladeFanStatusEntry 1}
--            apexBladeFanStatusFanSpeedControl                                 {apexBladeFanStatusEntry 2}
--            apexBladeFanStatusFan1Speed                                       {apexBladeFanStatusEntry 3}
--            apexBladeFanStatusFan2Speed                                       {apexBladeFanStatusEntry 4}
--            apexFanSpeed1FaultCondition                                       {apexBladeFanStatusEntry 5}
--            apexFanSpeed2FaultCondition                                       {apexBladeFanStatusEntry 6}
   apexDepi                                               OBJECT IDENTIFIER ::= {apex3000 26}
      apexDepiConfig                                      OBJECT IDENTIFIER ::= {apexDepi 1}
         apexDepiConfigGeneral                            OBJECT IDENTIFIER ::= {apexDepiConfig 1}
--          apexDepiDiscardedNoSessionReset                                     {apexDepiConfigGeneral 1}
            apexDepiSessionRemoveSession                  OBJECT IDENTIFIER ::= {apexDepiConfigGeneral 2}
--             apexDepiSessionRemoveSessionId                                   {apexDepiSessionRemoveSession 1}
--             apexDepiSessionRemoveSessionApply                                {apexDepiSessionRemoveSession 2}
            apexDepiRfLock                                OBJECT IDENTIFIER ::= {apexDepiConfigGeneral 3}
--             apexDepiRfLockChannelFrequency                                   {apexDepiRfLock 1}
--             apexDepiRfLockChannelModulation                                  {apexDepiRfLock 2}
--             apexDepiRfLockChannelInterleaver                                 {apexDepiRfLock 3}
--             apexDepiRfLockChannelMute                                        {apexDepiRfLock 4}
--             apexDepiRfLockApplyChange                                        {apexDepiRfLock 5}
--             apexDepiRfLockInvalidApplyText                                   {apexDepiRfLock 5}
         apexDepiSessionConfig                            OBJECT IDENTIFIER ::= {apexDepiConfig 2}
            apexDepiSessionConfigBlade1                   OBJECT IDENTIFIER ::= {apexDepiSessionConfig  1}
--             apexDepiSessionConfigBlade1ApplyTable                            {apexDepiSessionConfigBlade1  1}
--                apexDepiSessionConfigBlade1ApplyEntry                         {apexDepiSessionConfigBlade1ApplyTable 1}
--                   apexDepiSessionConfigBlade1ApplyOutputTsNum                {apexDepiSessionConfigBlade1ApplyEntry 1}
--                   apexDepiSessionConfigBlade1ApplyChange                     {apexDepiSessionConfigBlade1ApplyEntry 2}
--             apexDepiSessionConfigBlade1Table                                 {apexDepiSessionConfigBlade1  2}
--                apexDepiSessionConfigBlade1Entry                              {apexDepiSessionConfigBlade1Table 1}
--                   apexDepiSessionConfigBlade1OutputTsNum                     {apexDepiSessionConfigBlade1Entry 1}
--                   apexDepiSessionConfigBlade1Enable                          {apexDepiSessionConfigBlade1Entry 2}
--                   apexDepiSessionConfigBlade1DocsisTsid                      {apexDepiSessionConfigBlade1Entry 3}
--                   apexDepiSessionConfigBlade1InterfaceNumber                 {apexDepiSessionConfigBlade1Entry 4}
--                   apexDepiSessionConfigBlade1SourceIp                        {apexDepiSessionConfigBlade1Entry 5}
            apexDepiSessionConfigBlade2                   OBJECT IDENTIFIER ::= {apexDepiSessionConfig  2}
--             apexDepiSessionConfigBlade2ApplyTable                            {apexDepiSessionConfigBlade2  1}
--                apexDepiSessionConfigBlade2ApplyEntry                         {apexDepiSessionConfigBlade2ApplyTable 1}
--                   apexDepiSessionConfigBlade2ApplyOutputTsNum                {apexDepiSessionConfigBlade2ApplyEntry 1}
--                   apexDepiSessionConfigBlade2ApplyChange                     {apexDepiSessionConfigBlade2ApplyEntry 2}
--             apexDepiSessionConfigBlade2Table                                 {apexDepiSessionConfigBlade2 2}
--                apexDepiSessionConfigBlade2Entry                              {apexDepiSessionConfigBlade2Table 1}
--                   apexDepiSessionConfigBlade2OutputTsNum                     {apexDepiSessionConfigBlade2Entry 1}
--                   apexDepiSessionConfigBlade2Enable                          {apexDepiSessionConfigBlade2Entry 2}
--                   apexDepiSessionConfigBlade2DocsisTsid                      {apexDepiSessionConfigBlade2Entry 3}
--                   apexDepiSessionConfigBlade2InterfaceNumber                 {apexDepiSessionConfigBlade2Entry 4}
--                   apexDepiSessionConfigBlade2SourceIp                        {apexDepiSessionConfigBlade2Entry 5}
            apexDepiSessionConfigBlade3                   OBJECT IDENTIFIER ::= {apexDepiSessionConfig  3}
--             apexDepiSessionConfigBlade3ApplyTable                            {apexDepiSessionConfigBlade3  1}
--                apexDepiSessionConfigBlade3ApplyEntry                         {apexDepiSessionConfigBlade3ApplyTable 1}
--                   apexDepiSessionConfigBlade3ApplyOutputTsNum                {apexDepiSessionConfigBlade3ApplyEntry 1}
--                   apexDepiSessionConfigBlade3ApplyChange                     {apexDepiSessionConfigBlade3ApplyEntry 2}
--             apexDepiSessionConfigBlade3Table                                 {apexDepiSessionConfigBlade3 2}
--                apexDepiSessionConfigBlade3Entry                              {apexDepiSessionConfigBlade3Table 1}
--                   apexDepiSessionConfigBlade3OutputTsNum                     {apexDepiSessionConfigBlade3Entry 1}
--                   apexDepiSessionConfigBlade3Enable                          {apexDepiSessionConfigBlade3Entry 2}
--                   apexDepiSessionConfigBlade3DocsisTsid                      {apexDepiSessionConfigBlade3Entry 3}
--                   apexDepiSessionConfigBlade3InterfaceNumber                 {apexDepiSessionConfigBlade3Entry 4}
--                   apexDepiSessionConfigBlade3SourceIp                        {apexDepiSessionConfigBlade3Entry 5}
            apexDepiSessionConfigBlade4                   OBJECT IDENTIFIER ::= {apexDepiSessionConfig  4}
--             apexDepiSessionConfigBlade4ApplyTable                            {apexDepiSessionConfigBlade4  1}
--                apexDepiSessionConfigBlade4ApplyEntry                         {apexDepiSessionConfigBlade4ApplyTable 1}
--                   apexDepiSessionConfigBlade4ApplyOutputTsNum                {apexDepiSessionConfigBlade4ApplyEntry 1}
--                   apexDepiSessionConfigBlade4ApplyChange                     {apexDepiSessionConfigBlade4ApplyEntry 2}
--             apexDepiSessionConfigBlade4Table                                 {apexDepiSessionConfigBlade4 2}
--                apexDepiSessionConfigBlade4Entry                              {apexDepiSessionConfigBlade4Table 1}
--                   apexDepiSessionConfigBlade4OutputTsNum                     {apexDepiSessionConfigBlade4Entry 1}
--                   apexDepiSessionConfigBlade4Enable                          {apexDepiSessionConfigBlade4Entry 2}
--                   apexDepiSessionConfigBlade4DocsisTsid                      {apexDepiSessionConfigBlade4Entry 3}
--                   apexDepiSessionConfigBlade4InterfaceNumber                 {apexDepiSessionConfigBlade4Entry 4}
--                   apexDepiSessionConfigBlade4SourceIp                        {apexDepiSessionConfigBlade4Entry 5}
            apexDepiSessionConfigBlade5                   OBJECT IDENTIFIER ::= {apexDepiSessionConfig  5}
--             apexDepiSessionConfigBlade5ApplyTable                            {apexDepiSessionConfigBlade5  1}
--                apexDepiSessionConfigBlade5ApplyEntry                         {apexDepiSessionConfigBlade5ApplyTable 1}
--                   apexDepiSessionConfigBlade5ApplyOutputTsNum                {apexDepiSessionConfigBlade5ApplyEntry 1}
--                   apexDepiSessionConfigBlade5ApplyChange                     {apexDepiSessionConfigBlade5ApplyEntry 2}
--             apexDepiSessionConfigBlade5Table                                 {apexDepiSessionConfigBlade5 2}
--                apexDepiSessionConfigBlade5Entry                              {apexDepiSessionConfigBlade5Table 1}
--                   apexDepiSessionConfigBlade5OutputTsNum                     {apexDepiSessionConfigBlade5Entry 1}
--                   apexDepiSessionConfigBlade5Enable                          {apexDepiSessionConfigBlade5Entry 2}
--                   apexDepiSessionConfigBlade5DocsisTsid                      {apexDepiSessionConfigBlade5Entry 3}
--                   apexDepiSessionConfigBlade51InterfaceNumber                {apexDepiSessionConfigBlade5Entry 4}
--                   apexDepiSessionConfigBlade5SourceIp                        {apexDepiSessionConfigBlade5Entry 5}
            apexDepiSessionConfigBlade6                   OBJECT IDENTIFIER ::= {apexDepiSessionConfig  6}
--             apexDepiSessionConfigBlade6ApplyTable                            {apexDepiSessionConfigBlade6  1}
--                apexDepiSessionConfigBlade6ApplyEntry                         {apexDepiSessionConfigBlade6ApplyTable 1}
--                   apexDepiSessionConfigBlade6ApplyOutputTsNum                {apexDepiSessionConfigBlade6ApplyEntry 1}
--                   apexDepiSessionConfigBlade6ApplyChange                     {apexDepiSessionConfigBlade6ApplyEntry 2}
--             apexDepiSessionConfigBlade6Table                                 {apexDepiSessionConfigBlade6 2}
--                apexDepiSessionConfigBlade6Entry                              {apexDepiSessionConfigBlade6Table 1}
--                   apexDepiSessionConfigBlade6OutputTsNum                     {apexDepiSessionConfigBlade6Entry 1}
--                   apexDepiSessionConfigBlade6Enable                          {apexDepiSessionConfigBlade6Entry 2}
--                   apexDepiSessionConfigBlade6DocsisTsid                      {apexDepiSessionConfigBlade6Entry 3}
--                   apexDepiSessionConfigBlade6InterfaceNumber                 {apexDepiSessionConfigBlade6Entry 4}
--                   apexDepiSessionConfigBlade6SourceIp                        {apexDepiSessionConfigBlade6Entry 5}
            apexDepiSessionConfigBlade7                   OBJECT IDENTIFIER ::= {apexDepiSessionConfig  7}
--             apexDepiSessionConfigBlade7ApplyTable                            {apexDepiSessionConfigBlade7  1}
--                apexDepiSessionConfigBlade7ApplyEntry                         {apexDepiSessionConfigBlade7ApplyTable 1}
--                   apexDepiSessionConfigBlade7ApplyOutputTsNum                {apexDepiSessionConfigBlade7ApplyEntry 1}
--                   apexDepiSessionConfigBlade7ApplyChange                     {apexDepiSessionConfigBlade7ApplyEntry 2}
--             apexDepiSessionConfigBlade7Table                                 {apexDepiSessionConfigBlade7 2}
--                apexDepiSessionConfigBlade7Entry                              {apexDepiSessionConfigBlade7Table 1}
--                   apexDepiSessionConfigBlade7OutputTsNum                     {apexDepiSessionConfigBlade7Entry 1}
--                   apexDepiSessionConfigBlade7Enable                          {apexDepiSessionConfigBlade7Entry 2}
--                   apexDepiSessionConfigBlade7DocsisTsid                      {apexDepiSessionConfigBlade7Entry 3}
--                   apexDepiSessionConfigBlade7InterfaceNumber                 {apexDepiSessionConfigBlade7Entry 4}
--                   apexDepiSessionConfigBlade7SourceIp                        {apexDepiSessionConfigBlade7Entry 5}
            apexDepiSessionConfigBlade8                   OBJECT IDENTIFIER ::= {apexDepiSessionConfig  8}
--             apexDepiSessionConfigBlade8ApplyTable                            {apexDepiSessionConfigBlade8  1}
--                apexDepiSessionConfigBlade8ApplyEntry                         {apexDepiSessionConfigBlade8ApplyTable 1}
--                   apexDepiSessionConfigBlade8ApplyOutputTsNum                {apexDepiSessionConfigBlade8ApplyEntry 1}
--                   apexDepiSessionConfigBlade8ApplyChange                     {apexDepiSessionConfigBlade8ApplyEntry 2}
--             apexDepiSessionConfigBlade8Table                                 {apexDepiSessionConfigBlade8 2}
--                apexDepiSessionConfigBlade8Entry                              {apexDepiSessionConfigBlade8Table 1}
--                   apexDepiSessionConfigBlade8OutputTsNum                     {apexDepiSessionConfigBlade8Entry 1}
--                   apexDepiSessionConfigBlade8Enable                          {apexDepiSessionConfigBlade8Entry 2}
--                   apexDepiSessionConfigBlade8DocsisTsid                      {apexDepiSessionConfigBlade8Entry 3}
--                   apexDepiSessionConfigBlade8InterfaceNumber                 {apexDepiSessionConfigBlade8Entry 4}
--                   apexDepiSessionConfigBlade8SourceIp                        {apexDepiSessionConfigBlade8Entry 5}
--          apexDepiSessionEnableDisableApply                                   {apexDepiSessionConfig  9}
         apexDepiControlConfig                            OBJECT IDENTIFIER ::= {apexDepiConfig 3}
            apexDepiControlConfigGeneral                  OBJECT IDENTIFIER ::= {apexDepiControlConfig 1}
--             apexDepiAllowUnsupportedMandatoryAvps                            {apexDepiControlConfigGeneral 1}
--             apexDepiKeepaliveTimeout                                         {apexDepiControlConfigGeneral 2}
--             apexDepiKeepalive                                                {apexDepiControlConfigGeneral 3}
--             apexDepiNumberRetransmissions                                    {apexDepiControlConfigGeneral 4}
--             apexDepiControlPlaneConfigApplyChange                            {apexDepiControlConfigGeneral 5}
--             apexDepiControlPlaneConfigInvalidApplyText                       {apexDepiControlConfigGeneral 6}
--          apexDepiControlConfigApplyTable                                     {apexDepiControlConfig 2}
--             apexDepiControlConfigApplyEntry                                  {apexDepiControlConfigApplyTable 1}
--                apexDepiControlConfigApplyIndex                               {apexDepiControlConfigApplyEntry 1}
--                apexDepiControlConfigApplyChange                              {apexDepiControlConfigApplyEntry 2}
--          apexDepiControlConfigTable                                          {apexDepiControlConfig 3}
--             apexDepiControlConfigEntry                                       {apexDepiControlConfigTable 1}
--                apexDepiControlConfigIndex                                    {apexDepiControlConfigEntry 1}
--                apexDepiControlConfigEnable                                   {apexDepiControlConfigEntry 2}
--                apexDepiControlConfigInterfaceNumber                          {apexDepiControlConfigEntry 3}
--                apexDepiControlConfigSrcIpAddr                                {apexDepiControlConfigEntry 4}
     apexDepiStatus                                       OBJECT IDENTIFIER ::= {apexDepi 2}
         apexDepiStatusGeneral                            OBJECT IDENTIFIER ::= {apexDepiStatus 1}  
--          apexDtiPort1LinkActive                                              {apexDepiStatusGeneral 1} 
--          apexDtiPort2LinkActive                                              {apexDepiStatusGeneral 2}
--          apexDtiClientStatusMode                                             {apexDepiStatusGeneral 3}
--          apexDtiClientPhaseError                                             {apexDepiStatusGeneral 4}
--          apexDtiCurrentTimestamp                                             {apexDepiStatusGeneral 5}
--          apexDtiPort1CableAdvanceValue                                       {apexDepiStatusGeneral 6}
--          apexDtiPort2CableAdvanceValue                                       {apexDepiStatusGeneral 7}
         apexDepiSessionStatus                            OBJECT IDENTIFIER ::= {apexDepiStatus 2}
            apexDepiSessionStatusGeneral                  OBJECT IDENTIFIER ::= {apexDepiSessionStatus 1}
--             apexDepiSessionStatusGeneralInvalidApplyText                     {apexDepiSessionStatusGeneral 1}
--             apexDepiSessionStatusGeneralTotalSessions             [obsolete] {apexDepiSessionStatusGeneral 2}
--             apexDepiSessionStatusGeneralDiscardedNoSession        [obsolete] {apexDepiSessionStatusGeneral 3}
            apexDepiSessionStatusBlade1                   OBJECT IDENTIFIER ::= {apexDepiSessionStatus 2}
--             apexDepiSessionStatusBlade1Table                      [obsolete] {apexDepiSessionStatusBlade1 1}
--                apexDepiSessionStatusBlade1Entry                   [obsolete] {apexDepiSessionStatusBlade1Table 1}
--                   apexDepiSessionStatusBlade1Index                [obsolete] {apexDepiSessionStatusBlade1Entry 1}
--                   apexDepiSessionStatusBlade1OutputQAMChannel     [obsolete] {apexDepiSessionStatusBlade1Entry 2}
--                   apexDepiSessionStatusBlade1Status               [obsolete] {apexDepiSessionStatusBlade1Entry 3}
--                   apexDepiSessionStatusBlade1InDataPackets        [obsolete] {apexDepiSessionStatusBlade1Entry 4}
--                   apexDepiSessionStatusBlade1InSequenceDiscards   [obsolete] {apexDepiSessionStatusBlade1Entry 5}
--                   apexDepiSessionStatusBlade1InDataPacketDiscards [obsolete] {apexDepiSessionStatusBlade1Entry 6}
--                   apexDepiSessionStatusBlade1SessionID            [obsolete] {apexDepiSessionStatusBlade1Entry 7}
--                   apexDepiSessionStatusBlade1InputIf              [obsolete] {apexDepiSessionStatusBlade1Entry 8}
--                   apexDepiSessionStatusBlade1DataRate             [obsolete] {apexDepiSessionStatusBlade1Entry 9}
--                   apexDepiSessionStatusBlade1SourceIp             [obsolete] {apexDepiSessionStatusBlade1Entry 10}
--             apexDepiSessionStatusBlade1TotalSessions              [obsolete] {apexDepiSessionStatusBlade1 2}
--             apexDepiSessionBlade1StatusTable                                 {apexDepiSessionStatusBlade1 3}
--                apexDepiSessionBlade1StatusEntry                              {apexDepiSessionBlade1StatusTable 1}
--                   apexDepiSessionBlade1StatusOutputOtsNum                    {apexDepiSessionBlade1StatusEntry 1}
--                   apexDepiSessionBlade1StatusIndex                           {apexDepiSessionBlade1StatusEntry 2}
--                   apexDepiSessionBlade1StatusStatus                          {apexDepiSessionBlade1StatusEntry 3}
--                   apexDepiSessionBlade1StatusInDataPackets                   {apexDepiSessionBlade1StatusEntry 4}
--                   apexDepiSessionBlade1StatusInSequenceDiscards              {apexDepiSessionBlade1StatusEntry 5}
--                   apexDepiSessionBlade1StatusInDataPacketDiscards            {apexDepiSessionBlade1StatusEntry 6}
--                   apexDepiSessionBlade1StatusSessionID                       {apexDepiSessionBlade1StatusEntry 7}
--                   apexDepiSessionBlade1StatusInputIf                         {apexDepiSessionBlade1StatusEntry 8}
--                   apexDepiSessionBlade1StatusDataRate                        {apexDepiSessionBlade1StatusEntry 9}
--                   apexDepiSessionBlade1StatusSourceIp                        {apexDepiSessionBlade1StatusEntry 10}
--                   apexDepiSessionBlade1StatusActivationMode                  {apexDepiSessionBlade1StatusEntry 11}
--                   apexDepiSessionBlade1StatusCCid                            {apexDepiSessionBlade1StatusEntry 12}
--                   apexDepiSessionBlade1StatusSessionType                     {apexDepiSessionBlade1StatusEntry 13}
--                   apexDepiSessionBlade1StatusSyncRequired                    {apexDepiSessionBlade1StatusEntry 14}
--                   apexDepiSessionBlade1StatusRemoteSessionId                 {apexDepiSessionBlade1StatusEntry 15}
--                   apexDepiSessionBlade1StatusInputTsIndex                    {apexDepiSessionBlade1StatusEntry 16}
            apexDepiSessionStatusBlade2                   OBJECT IDENTIFIER ::= {apexDepiSessionStatus 3}
--             apexDepiSessionStatusBlade2Table                      [obsolete] {apexDepiSessionStatusBlade2 1}
--                apexDepiSessionStatusBlade2Entry                   [obsolete] {apexDepiSessionStatusBlade2Table 1}
--                   apexDepiSessionStatusBlade2Index                [obsolete] {apexDepiSessionStatusBlade2Entry 1}
--                   apexDepiSessionStatusBlade2OutputQAMChannel     [obsolete] {apexDepiSessionStatusBlade2Entry 2}
--                   apexDepiSessionStatusBlade2Status               [obsolete] {apexDepiSessionStatusBlade2Entry 3}
--                   apexDepiSessionStatusBlade2InDataPackets        [obsolete] {apexDepiSessionStatusBlade2Entry 4}
--                   apexDepiSessionStatusBlade2InSequenceDiscards   [obsolete] {apexDepiSessionStatusBlade2Entry 5}
--                   apexDepiSessionStatusBlade2InDataPacketDiscards [obsolete] {apexDepiSessionStatusBlade2Entry 6}
--                   apexDepiSessionStatusBlade2SessionID            [obsolete] {apexDepiSessionStatusBlade2Entry 7}
--                   apexDepiSessionStatusBlade2InputIf              [obsolete] {apexDepiSessionStatusBlade2Entry 8}
--                   apexDepiSessionStatusBlade2DataRate             [obsolete] {apexDepiSessionStatusBlade2Entry 9}
--                   apexDepiSessionStatusBlade2SourceIp             [obsolete] {apexDepiSessionStatusBlade2Entry 10}
--             apexDepiSessionStatusBlade2TotalSessions              [obsolete] {apexDepiSessionStatusBlade2 2}
--             apexDepiSessionBlade2StatusTable                                 {apexDepiSessionStatusBlade2 3}
--                apexDepiSessionBlade2StatusEntry                              {apexDepiSessionBlade2StatusTable 1}
--                   apexDepiSessionBlade2StatusOutputOtsNum                    {apexDepiSessionBlade2StatusEntry 1}
--                   apexDepiSessionBlade2StatusIndex                           {apexDepiSessionBlade2StatusEntry 2}
--                   apexDepiSessionBlade2StatusStatus                          {apexDepiSessionBlade2StatusEntry 3}
--                   apexDepiSessionBlade2StatusInDataPackets                   {apexDepiSessionBlade2StatusEntry 4}
--                   apexDepiSessionBlade2StatusInSequenceDiscards              {apexDepiSessionBlade2StatusEntry 5}
--                   apexDepiSessionBlade2StatusInDataPacketDiscards            {apexDepiSessionBlade2StatusEntry 6}
--                   apexDepiSessionBlade2StatusSessionID                       {apexDepiSessionBlade2StatusEntry 7}
--                   apexDepiSessionBlade2StatusInputIf                         {apexDepiSessionBlade2StatusEntry 8}
--                   apexDepiSessionBlade2StatusDataRate                        {apexDepiSessionBlade2StatusEntry 9}
--                   apexDepiSessionBlade2StatusSourceIp                        {apexDepiSessionBlade2StatusEntry 10}
--                   apexDepiSessionBlade2StatusActivationMode                  {apexDepiSessionBlade2StatusEntry 11}
--                   apexDepiSessionBlade2StatusCCid                            {apexDepiSessionBlade2StatusEntry 12}
--                   apexDepiSessionBlade2StatusSessionType                     {apexDepiSessionBlade2StatusEntry 13}
--                   apexDepiSessionBlade2StatusSyncRequired                    {apexDepiSessionBlade2StatusEntry 14}
--                   apexDepiSessionBlade2StatusRemoteSessionId                 {apexDepiSessionBlade2StatusEntry 15}
--                   apexDepiSessionBlade2StatusInputTsIndex                    {apexDepiSessionBlade2StatusEntry 16}
            apexDepiSessionStatusBlade3                   OBJECT IDENTIFIER ::= {apexDepiSessionStatus 4}
--             apexDepiSessionStatusBlade3Table                      [obsolete] {apexDepiSessionStatusBlade3 1}
--                apexDepiSessionStatusBlade3Entry                   [obsolete] {apexDepiSessionStatusBlade3Table 1}
--                   apexDepiSessionStatusBlade3Index                [obsolete] {apexDepiSessionStatusBlade3Entry 1}
--                   apexDepiSessionStatusBlade3OutputQAMChannel     [obsolete] {apexDepiSessionStatusBlade3Entry 2}
--                   apexDepiSessionStatusBlade3Status               [obsolete] {apexDepiSessionStatusBlade3Entry 3}
--                   apexDepiSessionStatusBlade3InDataPackets        [obsolete] {apexDepiSessionStatusBlade3Entry 4}
--                   apexDepiSessionStatusBlade3InSequenceDiscards   [obsolete] {apexDepiSessionStatusBlade3Entry 5}
--                   apexDepiSessionStatusBlade3InDataPacketDiscards [obsolete] {apexDepiSessionStatusBlade3Entry 6}
--                   apexDepiSessionStatusBlade3SessionID            [obsolete] {apexDepiSessionStatusBlade3Entry 7}
--                   apexDepiSessionStatusBlade3InputIf              [obsolete] {apexDepiSessionStatusBlade3Entry 8}
--                   apexDepiSessionStatusBlade3DataRate             [obsolete] {apexDepiSessionStatusBlade3Entry 9}
--                   apexDepiSessionStatusBlade3SourceIp             [obsolete] {apexDepiSessionStatusBlade3Entry 10}
--             apexDepiSessionStatusBlade3TotalSessions              [obsolete] {apexDepiSessionStatusBlade3 2}
--             apexDepiSessionBlade3StatusTable                                 {apexDepiSessionStatusBlade3 3}
--                apexDepiSessionBlade3StatusEntry                              {apexDepiSessionBlade3StatusTable 1}
--                   apexDepiSessionBlade3StatusOutputOtsNum                    {apexDepiSessionBlade3StatusEntry 1}
--                   apexDepiSessionBlade3StatusIndex                           {apexDepiSessionBlade3StatusEntry 2}
--                   apexDepiSessionBlade3StatusStatus                          {apexDepiSessionBlade3StatusEntry 3}
--                   apexDepiSessionBlade3StatusInDataPackets                   {apexDepiSessionBlade3StatusEntry 4}
--                   apexDepiSessionBlade3StatusInSequenceDiscards              {apexDepiSessionBlade3StatusEntry 5}
--                   apexDepiSessionBlade3StatusInDataPacketDiscards            {apexDepiSessionBlade3StatusEntry 6}
--                   apexDepiSessionBlade3StatusSessionID                       {apexDepiSessionBlade3StatusEntry 7}
--                   apexDepiSessionBlade3StatusInputIf                         {apexDepiSessionBlade3StatusEntry 8}
--                   apexDepiSessionBlade3StatusDataRate                        {apexDepiSessionBlade3StatusEntry 9}
--                   apexDepiSessionBlade3StatusSourceIp                        {apexDepiSessionBlade3StatusEntry 10}
--                   apexDepiSessionBlade3StatusActivationMode                  {apexDepiSessionBlade3StatusEntry 11}
--                   apexDepiSessionBlade3StatusCCid                            {apexDepiSessionBlade3StatusEntry 12}
--                   apexDepiSessionBlade3StatusSessionType                     {apexDepiSessionBlade3StatusEntry 13}
--                   apexDepiSessionBlade3StatusSyncRequired                    {apexDepiSessionBlade3StatusEntry 14}
--                   apexDepiSessionBlade3StatusRemoteSessionId                 {apexDepiSessionBlade3StatusEntry 15}
--                   apexDepiSessionBlade3StatusInputTsIndex                    {apexDepiSessionBlade3StatusEntry 16}
            apexDepiSessionStatusBlade4                   OBJECT IDENTIFIER ::= {apexDepiSessionStatus 5}
--             apexDepiSessionStatusBlade4Table                      [obsolete] {apexDepiSessionStatusBlade4 1}
--                apexDepiSessionStatusBlade4Entry                   [obsolete] {apexDepiSessionStatusBlade4Table 1}
--                   apexDepiSessionStatusBlade4Index                [obsolete] {apexDepiSessionStatusBlade4Entry 1}
--                   apexDepiSessionStatusBlade4OutputQAMChannel     [obsolete] {apexDepiSessionStatusBlade4Entry 2}
--                   apexDepiSessionStatusBlade4Status               [obsolete] {apexDepiSessionStatusBlade4Entry 3}
--                   apexDepiSessionStatusBlade4InDataPackets        [obsolete] {apexDepiSessionStatusBlade4Entry 4}
--                   apexDepiSessionStatusBlade4InSequenceDiscards   [obsolete] {apexDepiSessionStatusBlade4Entry 5}
--                   apexDepiSessionStatusBlade4InDataPacketDiscards [obsolete] {apexDepiSessionStatusBlade4Entry 6}
--                   apexDepiSessionStatusBlade4SessionID            [obsolete] {apexDepiSessionStatusBlade4Entry 7}
--                   apexDepiSessionStatusBlade4InputIf              [obsolete] {apexDepiSessionStatusBlade4Entry 8}
--                   apexDepiSessionStatusBlade4DataRate             [obsolete] {apexDepiSessionStatusBlade4Entry 9}
--                   apexDepiSessionStatusBlade4SourceIp             [obsolete] {apexDepiSessionStatusBlade4Entry 10}
--             apexDepiSessionStatusBlade4TotalSessions              [obsolete] {apexDepiSessionStatusBlade4 2}
--             apexDepiSessionBlade4StatusTable                                 {apexDepiSessionStatusBlade4 3}
--                apexDepiSessionBlade4StatusEntry                              {apexDepiSessionBlade4StatusTable 1}
--                   apexDepiSessionBlade4StatusOutputOtsNum                    {apexDepiSessionBlade4StatusEntry 1}
--                   apexDepiSessionBlade4StatusIndex                           {apexDepiSessionBlade4StatusEntry 2}
--                   apexDepiSessionBlade4StatusStatus                          {apexDepiSessionBlade4StatusEntry 3}
--                   apexDepiSessionBlade4StatusInDataPackets                   {apexDepiSessionBlade4StatusEntry 4}
--                   apexDepiSessionBlade4StatusInSequenceDiscards              {apexDepiSessionBlade4StatusEntry 5}
--                   apexDepiSessionBlade4StatusInDataPacketDiscards            {apexDepiSessionBlade4StatusEntry 6}
--                   apexDepiSessionBlade4StatusSessionID                       {apexDepiSessionBlade4StatusEntry 7}
--                   apexDepiSessionBlade4StatusInputIf                         {apexDepiSessionBlade4StatusEntry 8}
--                   apexDepiSessionBlade4StatusDataRate                        {apexDepiSessionBlade4StatusEntry 9}
--                   apexDepiSessionBlade4StatusSourceIp                        {apexDepiSessionBlade4StatusEntry 10}
--                   apexDepiSessionBlade4StatusActivationMode                  {apexDepiSessionBlade4StatusEntry 11}
--                   apexDepiSessionBlade4StatusCCid                            {apexDepiSessionBlade4StatusEntry 12}
--                   apexDepiSessionBlade4StatusSessionType                     {apexDepiSessionBlade4StatusEntry 13}
--                   apexDepiSessionBlade4StatusSyncRequired                    {apexDepiSessionBlade4StatusEntry 14}
--                   apexDepiSessionBlade4StatusRemoteSessionId                 {apexDepiSessionBlade4StatusEntry 15}
--                   apexDepiSessionBlade4StatusInputTsIndex                    {apexDepiSessionBlade4StatusEntry 16}
            apexDepiSessionStatusBlade5                   OBJECT IDENTIFIER ::= {apexDepiSessionStatus 6}
--             apexDepiSessionStatusBlade5Table                      [obsolete] {apexDepiSessionStatusBlade5 1}
--                apexDepiSessionStatusBlade5Entry                   [obsolete] {apexDepiSessionStatusBlade5Table 1}
--                   apexDepiSessionStatusBlade5Index                [obsolete] {apexDepiSessionStatusBlade5Entry 1}
--                   apexDepiSessionStatusBlade5OutputQAMChannel     [obsolete] {apexDepiSessionStatusBlade5Entry 2}
--                   apexDepiSessionStatusBlade5Status               [obsolete] {apexDepiSessionStatusBlade5Entry 3}
--                   apexDepiSessionStatusBlade5InDataPackets        [obsolete] {apexDepiSessionStatusBlade5Entry 4}
--                   apexDepiSessionStatusBlade5InSequenceDiscards   [obsolete] {apexDepiSessionStatusBlade5Entry 5}
--                   apexDepiSessionStatusBlade5InDataPacketDiscards [obsolete] {apexDepiSessionStatusBlade5Entry 6}
--                   apexDepiSessionStatusBlade5SessionID            [obsolete] {apexDepiSessionStatusBlade5Entry 7}
--                   apexDepiSessionStatusBlade5InputIf              [obsolete] {apexDepiSessionStatusBlade5Entry 8}
--                   apexDepiSessionStatusBlade5DataRate             [obsolete] {apexDepiSessionStatusBlade5Entry 9}
--                   apexDepiSessionStatusBlade5SourceIp             [obsolete] {apexDepiSessionStatusBlade5Entry 10}
--             apexDepiSessionStatusBlade5TotalSessions              [obsolete] {apexDepiSessionStatusBlade5 2}
--             apexDepiSessionBlade5StatusTable                                 {apexDepiSessionStatusBlade5 3}
--                apexDepiSessionBlade5StatusEntry                              {apexDepiSessionBlade5StatusTable 1}
--                   apexDepiSessionBlade5StatusOutputOtsNum                    {apexDepiSessionBlade5StatusEntry 1}
--                   apexDepiSessionBlade5StatusIndex                           {apexDepiSessionBlade5StatusEntry 2}
--                   apexDepiSessionBlade5StatusStatus                          {apexDepiSessionBlade5StatusEntry 3}
--                   apexDepiSessionBlade5StatusInDataPackets                   {apexDepiSessionBlade5StatusEntry 4}
--                   apexDepiSessionBlade5StatusInSequenceDiscards              {apexDepiSessionBlade5StatusEntry 5}
--                   apexDepiSessionBlade5StatusInDataPacketDiscards            {apexDepiSessionBlade5StatusEntry 6}
--                   apexDepiSessionBlade5StatusSessionID                       {apexDepiSessionBlade5StatusEntry 7}
--                   apexDepiSessionBlade5StatusInputIf                         {apexDepiSessionBlade5StatusEntry 8}
--                   apexDepiSessionBlade5StatusDataRate                        {apexDepiSessionBlade5StatusEntry 9}
--                   apexDepiSessionBlade5StatusSourceIp                        {apexDepiSessionBlade5StatusEntry 10}
--                   apexDepiSessionBlade5StatusActivationMode                  {apexDepiSessionBlade5StatusEntry 11}
--                   apexDepiSessionBlade5StatusCCid                            {apexDepiSessionBlade5StatusEntry 12}
--                   apexDepiSessionBlade5StatusSessionType                     {apexDepiSessionBlade5StatusEntry 13}
--                   apexDepiSessionBlade5StatusSyncRequired                    {apexDepiSessionBlade5StatusEntry 14}
--                   apexDepiSessionBlade5StatusRemoteSessionId                 {apexDepiSessionBlade5StatusEntry 15}
--                   apexDepiSessionBlade5StatusInputTsIndex                    {apexDepiSessionBlade5StatusEntry 16}
            apexDepiSessionStatusBlade6                   OBJECT IDENTIFIER ::= {apexDepiSessionStatus 7}
--             apexDepiSessionStatusBlade6Table                      [obsolete] {apexDepiSessionStatusBlade6 1}
--                apexDepiSessionStatusBlade6Entry                   [obsolete] {apexDepiSessionStatusBlade6Table 1}
--                   apexDepiSessionStatusBlade6Index                [obsolete] {apexDepiSessionStatusBlade6Entry 1}
--                   apexDepiSessionStatusBlade6OutputQAMChannel     [obsolete] {apexDepiSessionStatusBlade6Entry 2}
--                   apexDepiSessionStatusBlade6Status               [obsolete] {apexDepiSessionStatusBlade6Entry 3}
--                   apexDepiSessionStatusBlade6InDataPackets        [obsolete] {apexDepiSessionStatusBlade6Entry 4}
--                   apexDepiSessionStatusBlade6InSequenceDiscards   [obsolete] {apexDepiSessionStatusBlade6Entry 5}
--                   apexDepiSessionStatusBlade6InDataPacketDiscards [obsolete] {apexDepiSessionStatusBlade6Entry 6}
--                   apexDepiSessionStatusBlade6SessionID            [obsolete] {apexDepiSessionStatusBlade6Entry 7}
--                   apexDepiSessionStatusBlade6InputIf              [obsolete] {apexDepiSessionStatusBlade6Entry 8}
--                   apexDepiSessionStatusBlade6DataRate             [obsolete] {apexDepiSessionStatusBlade6Entry 9}
--                   apexDepiSessionStatusBlade6SourceIp             [obsolete] {apexDepiSessionStatusBlade6Entry 10}
--             apexDepiSessionStatusBlade6TotalSessions              [obsolete] {apexDepiSessionStatusBlade6 2}
--             apexDepiSessionBlade6StatusTable                                 {apexDepiSessionStatusBlade6 3}
--                apexDepiSessionBlade6StatusEntry                              {apexDepiSessionBlade6StatusTable 1}
--                   apexDepiSessionBlade6StatusOutputOtsNum                    {apexDepiSessionBlade6StatusEntry 1}
--                   apexDepiSessionBlade6StatusIndex                           {apexDepiSessionBlade6StatusEntry 2}
--                   apexDepiSessionBlade6StatusStatus                          {apexDepiSessionBlade6StatusEntry 3}
--                   apexDepiSessionBlade6StatusInDataPackets                   {apexDepiSessionBlade6StatusEntry 4}
--                   apexDepiSessionBlade6StatusInSequenceDiscards              {apexDepiSessionBlade6StatusEntry 5}
--                   apexDepiSessionBlade6StatusInDataPacketDiscards            {apexDepiSessionBlade6StatusEntry 6}
--                   apexDepiSessionBlade6StatusSessionID                       {apexDepiSessionBlade6StatusEntry 7}
--                   apexDepiSessionBlade6StatusInputIf                         {apexDepiSessionBlade6StatusEntry 8}
--                   apexDepiSessionBlade6StatusDataRate                        {apexDepiSessionBlade6StatusEntry 9}
--                   apexDepiSessionBlade6StatusSourceIp                        {apexDepiSessionBlade6StatusEntry 10}
--                   apexDepiSessionBlade6StatusActivationMode                  {apexDepiSessionBlade6StatusEntry 11}
--                   apexDepiSessionBlade6StatusCCid                            {apexDepiSessionBlade6StatusEntry 12}
--                   apexDepiSessionBlade6StatusSessionType                     {apexDepiSessionBlade6StatusEntry 13}
--                   apexDepiSessionBlade6StatusSyncRequired                    {apexDepiSessionBlade6StatusEntry 14}
--                   apexDepiSessionBlade6StatusRemoteSessionId                 {apexDepiSessionBlade6StatusEntry 15}
--                   apexDepiSessionBlade6StatusInputTsIndex                    {apexDepiSessionBlade6StatusEntry 16}
            apexDepiSessionStatusBlade7                   OBJECT IDENTIFIER ::= {apexDepiSessionStatus 8}
--             apexDepiSessionStatusBlade7Table                      [obsolete] {apexDepiSessionStatusBlade7 1}
--                apexDepiSessionStatusBlade7Entry                   [obsolete] {apexDepiSessionStatusBlade7Table 1}
--                   apexDepiSessionStatusBlade7Index                [obsolete] {apexDepiSessionStatusBlade7Entry 1}
--                   apexDepiSessionStatusBlade7OutputQAMChannel     [obsolete] {apexDepiSessionStatusBlade7Entry 2}
--                   apexDepiSessionStatusBlade7Status               [obsolete] {apexDepiSessionStatusBlade7Entry 3}
--                   apexDepiSessionStatusBlade7InDataPackets        [obsolete] {apexDepiSessionStatusBlade7Entry 4}
--                   apexDepiSessionStatusBlade7InSequenceDiscards   [obsolete] {apexDepiSessionStatusBlade7Entry 5}
--                   apexDepiSessionStatusBlade7InDataPacketDiscards [obsolete] {apexDepiSessionStatusBlade7Entry 6}
--                   apexDepiSessionStatusBlade7SessionID            [obsolete] {apexDepiSessionStatusBlade7Entry 7}
--                   apexDepiSessionStatusBlade7InputIf              [obsolete] {apexDepiSessionStatusBlade7Entry 8}
--                   apexDepiSessionStatusBlade7DataRate             [obsolete] {apexDepiSessionStatusBlade7Entry 9}
--                   apexDepiSessionStatusBlade7SourceIp             [obsolete] {apexDepiSessionStatusBlade7Entry 10}
--             apexDepiSessionStatusBlade7TotalSessions              [obsolete] {apexDepiSessionStatusBlade7 2}
--             apexDepiSessionBlade7StatusTable                                 {apexDepiSessionStatusBlade7 3}
--                apexDepiSessionBlade7StatusEntry                              {apexDepiSessionBlade7StatusTable 1}
--                   apexDepiSessionBlade7StatusOutputOtsNum                    {apexDepiSessionBlade7StatusEntry 1}
--                   apexDepiSessionBlade7StatusIndex                           {apexDepiSessionBlade7StatusEntry 2}
--                   apexDepiSessionBlade7StatusStatus                          {apexDepiSessionBlade7StatusEntry 3}
--                   apexDepiSessionBlade7StatusInDataPackets                   {apexDepiSessionBlade7StatusEntry 4}
--                   apexDepiSessionBlade7StatusInSequenceDiscards              {apexDepiSessionBlade7StatusEntry 5}
--                   apexDepiSessionBlade7StatusInDataPacketDiscards            {apexDepiSessionBlade7StatusEntry 6}
--                   apexDepiSessionBlade7StatusSessionID                       {apexDepiSessionBlade7StatusEntry 7}
--                   apexDepiSessionBlade7StatusInputIf                         {apexDepiSessionBlade7StatusEntry 8}
--                   apexDepiSessionBlade7StatusDataRate                        {apexDepiSessionBlade7StatusEntry 9}
--                   apexDepiSessionBlade7StatusSourceIp                        {apexDepiSessionBlade7StatusEntry 10}
--                   apexDepiSessionBlade7StatusActivationMode                  {apexDepiSessionBlade7StatusEntry 11}
--                   apexDepiSessionBlade7StatusCCid                            {apexDepiSessionBlade7StatusEntry 12}
--                   apexDepiSessionBlade7StatusSessionType                     {apexDepiSessionBlade7StatusEntry 13}
--                   apexDepiSessionBlade7StatusSyncRequired                    {apexDepiSessionBlade7StatusEntry 14}
--                   apexDepiSessionBlade7StatusRemoteSessionId                 {apexDepiSessionBlade7StatusEntry 15}
--                   apexDepiSessionBlade7StatusInputTsIndex                    {apexDepiSessionBlade7StatusEntry 16}
            apexDepiSessionStatusBlade8                   OBJECT IDENTIFIER ::= {apexDepiSessionStatus 9}
--             apexDepiSessionStatusBlade8Table                      [obsolete] {apexDepiSessionStatusBlade8 1}
--                apexDepiSessionStatusBlade8Entry                   [obsolete] {apexDepiSessionStatusBlade8Table 1}
--                   apexDepiSessionStatusBlade8Index                [obsolete] {apexDepiSessionStatusBlade8Entry 1}
--                   apexDepiSessionStatusBlade8OutputQAMChannel     [obsolete] {apexDepiSessionStatusBlade8Entry 2}
--                   apexDepiSessionStatusBlade8Status               [obsolete] {apexDepiSessionStatusBlade8Entry 3}
--                   apexDepiSessionStatusBlade8InDataPackets        [obsolete] {apexDepiSessionStatusBlade8Entry 4}
--                   apexDepiSessionStatusBlade8InSequenceDiscards   [obsolete] {apexDepiSessionStatusBlade8Entry 5}
--                   apexDepiSessionStatusBlade8InDataPacketDiscards [obsolete] {apexDepiSessionStatusBlade8Entry 6}
--                   apexDepiSessionStatusBlade8SessionID            [obsolete] {apexDepiSessionStatusBlade8Entry 7}
--                   apexDepiSessionStatusBlade8InputIf              [obsolete] {apexDepiSessionStatusBlade8Entry 8}
--                   apexDepiSessionStatusBlade8DataRate             [obsolete] {apexDepiSessionStatusBlade8Entry 9}
--                   apexDepiSessionStatusBlade8SourceIp             [obsolete] {apexDepiSessionStatusBlade8Entry 10}
--             apexDepiSessionStatusBlade8TotalSessions              [obsolete] {apexDepiSessionStatusBlade8 2}
--             apexDepiSessionBlade8StatusTable                                 {apexDepiSessionStatusBlade8 3}
--                apexDepiSessionBlade8StatusEntry                              {apexDepiSessionBlade8StatusTable 1}
--                   apexDepiSessionBlade8StatusOutputOtsNum                    {apexDepiSessionBlade8StatusEntry 1}
--                   apexDepiSessionBlade8StatusIndex                           {apexDepiSessionBlade8StatusEntry 2}
--                   apexDepiSessionBlade8StatusStatus                          {apexDepiSessionBlade8StatusEntry 3}
--                   apexDepiSessionBlade8StatusInDataPackets                   {apexDepiSessionBlade8StatusEntry 4}
--                   apexDepiSessionBlade8StatusInSequenceDiscards              {apexDepiSessionBlade8StatusEntry 5}
--                   apexDepiSessionBlade8StatusInDataPacketDiscards            {apexDepiSessionBlade8StatusEntry 6}
--                   apexDepiSessionBlade8StatusSessionID                       {apexDepiSessionBlade8StatusEntry 7}
--                   apexDepiSessionBlade8StatusInputIf                         {apexDepiSessionBlade8StatusEntry 8}
--                   apexDepiSessionBlade8StatusDataRate                        {apexDepiSessionBlade8StatusEntry 9}
--                   apexDepiSessionBlade8StatusSourceIp                        {apexDepiSessionBlade8StatusEntry 10}
--                   apexDepiSessionBlade8StatusActivationMode                  {apexDepiSessionBlade8StatusEntry 11}
--                   apexDepiSessionBlade8StatusCCid                            {apexDepiSessionBlade8StatusEntry 12}
--                   apexDepiSessionBlade8StatusSessionType                     {apexDepiSessionBlade8StatusEntry 13}
--                   apexDepiSessionBlade8StatusSyncRequired                    {apexDepiSessionBlade8StatusEntry 14}
--                   apexDepiSessionBlade8StatusRemoteSessionId                 {apexDepiSessionBlade8StatusEntry 15}
--                   apexDepiSessionBlade8StatusInputTsIndex                    {apexDepiSessionBlade8StatusEntry 16}
         apexDepiControlStatus                            OBJECT IDENTIFIER ::= {apexDepiStatus 3}
            apexDepiControlStatusGeneral                  OBJECT IDENTIFIER ::= {apexDepiControlStatus 1}
--             apexDepiControlStatusGeneralInvalidApplyText                     {apexDepiControlStatusGeneral 6}
--          apexDepiControlStatusTable                                          {apexDepiControlStatus 2}
--             apexDepiControlStatusEntry                                       {apexDepiControlStatusTable 1}
--                apexDepiControlStatusIndex                                    {apexDepiControlStatusEntry 1}
--                apexDepiControlStatusConnectionStatus                         {apexDepiControlStatusEntry 2}
--                apexDepiControlStatusTotalSessions                            {apexDepiControlStatusEntry 3}
--                apexDepiControlStatusInterfaceNumber                          {apexDepiControlStatusEntry 4}
--                apexDepiControlStatusSrcIpAddr                                {apexDepiControlStatusEntry 5}
--                apexDepiControlStatusLocalConnId                              {apexDepiControlStatusEntry 6}
--                apexDepiControlStatusRemoteConnId                             {apexDepiControlStatusEntry 7}
--                apexDepiControlStatusRelatedConfigIndex                       {apexDepiControlStatusEntry 8}
   apexUls                                                OBJECT IDENTIFIER ::= {apex3000 27}
      apexUlsConfig                                       OBJECT IDENTIFIER ::= {apexUls 1}
         apexUlsConfigGeneral                             OBJECT IDENTIFIER ::= {apexUlsConfig 1}          
--          apexUlsConfigGenerateRequest                                        {apexUlsConfigGeneral 1}
--          apexUlsConfigValidateResponse                                       {apexUlsConfigGeneral 2}
--          apexUlsConfigCommitNewFeatures                                      {apexUlsConfigGeneral 3}
         apexUlsConfigDocsisFeatures                      OBJECT IDENTIFIER ::= {apexUlsConfig 2}
--          apexUlsConfigDocsisChannelsRequest                                  {apexUlsConfigDocsisFeatures 1}
         apexUlsConfigQamAnnexAChannels                   OBJECT IDENTIFIER ::= {apexUlsConfig 3}
--          apexUlsConfigQamAnnexAChannelsRequest                               {apexUlsConfigQamAnnexAChannels 1}
         apexUlsConfigQamAnnexBChannels                   OBJECT IDENTIFIER ::= {apexUlsConfig 4}
--          apexUlsConfigQamAnnexBChannelsRequest                               {apexUlsConfigQamAnnexBChannels 1}
      apexUlsStatus                                       OBJECT IDENTIFIER ::= {apexUls 2}
         apexUlsStatusGeneral                             OBJECT IDENTIFIER ::= {apexUlsStatus 1}          
--          apexUlsStatusGenerateRequestText                                    {apexUlsStatusGeneral 1}
--          apexUlsStatusValidateResponseText                                   {apexUlsStatusGeneral 2}
--          apexUlsStatusCommitNewFeaturesText                                  {apexUlsStatusGeneral 3}
         apexUlsStatusDocsisFeatures                      OBJECT IDENTIFIER ::= {apexUlsStatus 2}          
--          apexUlsStatusDocsisChannelsCurrent                                  {apexUlsStatusDocsisFeatures 1}
--          apexUlsStatusDocsisChannelsInUse                                    {apexUlsStatusDocsisFeatures 2}
         apexUlsStatusQamAnnexAChannels                   OBJECT IDENTIFIER ::= {apexUlsStatus 3}         
--          apexUlsStatusQamAnnexAChannelsCurrent                               {apexUlsStatusQamAnnexAChannels 1}
--          apexUlsStatusQamAnnexAChannelsInUse                                 {apexUlsStatusQamAnnexAChannels 2}
         apexUlsStatusQamAnnexBChannels                   OBJECT IDENTIFIER ::= {apexUlsStatus 4}         
--          apexUlsStatusQamAnnexBChannelsCurrent                               {apexUlsStatusQamAnnexBChannels 1}
--          apexUlsStatusQamAnnexBChannelsInUse                                 {apexUlsStatusQamAnnexBChannels 2}
   apexQamEntitlement                                     OBJECT IDENTIFIER ::= {apex3000 28}
      apexQamEntConfig                                    OBJECT IDENTIFIER ::= {apexQamEntitlement 1}
         apexQamEntConfigGeneral                          OBJECT IDENTIFIER ::= {apexQamEntConfig 1}
--          apexQamEntConfigApplyChange                                         {apexQamEntConfigGeneral 1}
--       apexQamEntConfigAssignTable                                            {apexQamEntConfig 3}
--          apexQamEntConfigAssignEntry                                         {apexQamEntConfigAssignTable 1}
--             apexQamEntConfigAssignBladeNum                                   {apexQamEntConfigAssignEntry 1}
--             apexQamEntConfigAssignRfNum                                      {apexQamEntConfigAssignEntry 2}
--             apexQamEntConfigAssignChannels                                   {apexQamEntConfigAssignEntry 3}
      apexQamEntStatus                                    OBJECT IDENTIFIER ::= {apexQamEntitlement 2}
         apexQamEntStatusGeneral                          OBJECT IDENTIFIER ::= {apexQamEntStatus 1}
--          apexQamEntStatusInvalidApplyText                                    {apexQamEntStatusGeneral 1}
--       apexQamEntStatusTable                                                  {apexQamEntStatus 2}
--          apexQamEntStatusEntry                                               {apexQamEntStatusTable 1}
--             apexQamEntStatusBladeNum                                         {apexQamEntStatusEntry 1}
--             apexQamEntStatusRfNum                                            {apexQamEntStatusEntry 2}
--             apexQamEntStatusHwSupport                                        {apexQamEntStatusEntry 3}
--             apexQamEntStatusMinChannels                                      {apexQamEntStatusEntry 4}
--             apexQamEntStatusMaxChannels                                      {apexQamEntStatusEntry 5}
--             apexQamEntStatusTotalChannels                                    {apexQamEntStatusEntry 6}
   apexImportFile                                         OBJECT IDENTIFIER ::= {apex3000 29}
      apexImportFileConfig                                OBJECT IDENTIFIER ::= {apexImportFile 1}
         apexImportFileConfigGeneral                      OBJECT IDENTIFIER ::= {apexImportFileConfig 1}
--          apexImportFileRequest                                               {apexImportFileConfigGeneral 1}
--          apexImportFileOperation                                             {apexImportFileConfigGeneral 2}
--          apexImportFileRequestedFile                                         {apexImportFileConfigGeneral 3}
      apexImportFileStatus                                OBJECT IDENTIFIER ::= {apexImportFile 2}
         apexImportFileStatusGeneral                      OBJECT IDENTIFIER ::= {apexImportFileStatus 1}
--          apexImportFileStatusText                                            {apexImportFileStatusGeneral 1}
--          apexImportFileOperationalState                                      {apexImportFileStatusGeneral 2}
   apexAlarms                                             OBJECT IDENTIFIER ::= {apex3000 100}
--    apexAlarmHardwareFault                                                    {apexAlarms 8000}
--    apexAlarmInvalidConfigData                                                {apexAlarms 8001}
--    apexAlarmTemperatureFault                                                 {apexAlarms 8002}
--    apexAlarmFanFault                                                         {apexAlarms 8003}
--    apexAlarmPowerSupplyFault                                                 {apexAlarms 8004}
--    apexAlarmFanModuleFault                                                   {apexAlarms 8005}
--    apexAlarmHostModuleFault                                                  {apexAlarms 8006}
--    apexAlarmFrontPanelModuleFault                                            {apexAlarms 8007}
--    apexAlarmRfSwitchModuleFault                                              {apexAlarms 8008}
--    apexAlarm10GbeModuleFault                                                 {apexAlarms 8009}
--    apexAlarmDtiModuleFault                                                   {apexAlarms 8010}
--
--    apexAlarmGbeLossOfPhysicalInput                                           {apexAlarms 8020}
--    apexAlarmGbeBufferFullness                                                {apexAlarms 8021}
--    apexAlarmGbeInputStreamHighBitRate                                        {apexAlarms 8022}
--    apexAlarmGbeInputTsRedundFailover                                         {apexAlarms 8023}
--    apexAlarmServiceInError                                                   {apexAlarms 8024}
--    apexAlarmGbeLossOfInputStream                                             {apexAlarms 8025}
--    apexAlarmNpuToHostCommFault                                               {apexAlarms 8026}
--    apexAlarmGbeInterfaceRedundFailover                                       {apexAlarms 8027}
--    apexAlarmServiceInactiveError                                             {apexAlarms 8028}
--
--    apexAlarmOutputUtilizationFault                                           {apexAlarms 8040}
--    apexAlarmOutputOverflow                                                   {apexAlarms 8041}
--    apexAlarmQamBladeFault                                                    {apexAlarms 8042}
--    apexAlarmQamRfPortFault                                                   {apexAlarms 8043}
--    apexAlarmQamChannelFault                                                  {apexAlarms 8044}
--    apexAlarmQamBladeRedundFailover                                           {apexAlarms 8045}
--    apexAlarmQamBladeRedundMismatch                                           {apexAlarms 8046}
--    apexAlarmQamBladePhysicalLatchFault                                       {apexAlarms 8047}
--
--    apexAlarmRtspControllerCommFault                                          {apexAlarms 8060}
--
--    apexAlarmRdsCommFault                                                     {apexAlarms 8070}
--
--    apexAlarmHostModuleRedundFailover                                         {apexAlarms 8080}
--    apexAlarmHostModuleRedundFault                                            {apexAlarms 8081}
--
--    apexAlarmDtiSyncLossFault                                                 {apexAlarms 8090}
--    apexAlarmDepiControlConnectionFault                                       {apexAlarms 8091}
   apexEvents                                             OBJECT IDENTIFIER ::= {apex3000 101}
--    apexEventEmUserLoginFailed                                                {apexEvents 8500}
   apexConfigAlarms                                       OBJECT IDENTIFIER ::= {apex3000 102}
      apexConfAlarmEnable                                 OBJECT IDENTIFIER ::= {apexConfigAlarms 1}
--       apexEnableInvalidConfigData                                            {apexConfAlarmEnable 8001}
--       apexEnableGbeLossOfPhysicalInput                                       {apexConfAlarmEnable 8020}
--       apexEnableGbeBufferFullness                                            {apexConfAlarmEnable 8021}
--       apexEnableGbeInputStreamHighBitRate                                    {apexConfAlarmEnable 8022}
--       apexEnableGbeInputTsRedundFailover                                     {apexConfAlarmEnable 8023}
--       apexEnableServiceInError                                               {apexConfAlarmEnable 8024}
--       apexEnableGbeLossOfInputStream                                         {apexConfAlarmEnable 8025}
--       apexEnableGbeInterfaceRedundFailover                                   {apexConfAlarmEnable 8027}
--       apexEnableServiceInactiveError                                         {apexConfAlarmEnable 8028}
--       apexEnableOutputUtilizationFault                                       {apexConfAlarmEnable 8040}
--       apexEnableOutputOverflow                                               {apexConfAlarmEnable 8041}
--       apexEnableQamRfPortFault                                               {apexConfAlarmEnable 8043}
--       apexEnableQamChannelFault                                              {apexConfAlarmEnable 8044}
--       apexEnableQamBladeRedundFailover                                       {apexConfAlarmEnable 8045}
--       apexEnableQamBladeRedundMismatch                                       {apexConfAlarmEnable 8046}
--       apexEnableRtspControllerCommFault                                      {apexConfAlarmEnable 8060}
--       apexEnableRdsCommFault                                                 {apexConfAlarmEnable 8070}
--       apexEnableHostModuleRedundFailover                                     {apexConfAlarmEnable 8080}
--       apexEnableHostModuleRedundFault                                        {apexConfAlarmEnable 8081}
--       apexEnableDtiSyncLossFault                                             {apexConfAlarmEnable 8090}
--       apexEnableDepiControlConnectionFault                                   {apexConfAlarmEnable 8091}
      apexConfAlarmClear                                  OBJECT IDENTIFIER ::= {apexConfigAlarms 2}
--       apexClearInvalidConfigData                                             {apexConfAlarmClear 8001}
--       apexClearDepiControlConnectionFault                                    {apexConfAlarmClear 8002}
   apexLogs                                               OBJECT IDENTIFIER ::= {apex3000 200}
--    apexHwEventTable                                                          {apexLogs 1}
--       apexHwEventEntry                                                       {apexHwEventTable 1}
--          apexHwEventIndex                                                    {apexHwEventEntry 1}
--          apexHwEventTimeLogged                                               {apexHwEventEntry 2}
--          apexHwEventAlarmCode                                                {apexHwEventEntry 3}
--          apexHwEventAlarmSeverity                                            {apexHwEventEntry 4}
--          apexHwEventDescription                                              {apexHwEventEntry 5}
--    apexInvalidConfigDataTable                                                {apexLogs 2}
--       apexInvalidConfigDataEntry                                             {apexInvalidConfigDataTable 1}
--          apexInvalidConfigDataIndex                                          {apexInvalidConfigDataEntry 1}
--          apexInvalidConfigDataTimeLogged                                     {apexInvalidConfigDataEntry 2}
--          apexInvalidConfigDataDescription                                    {apexInvalidConfigDataEntry 3}
--    apexOutputTsEventTable                                                    {apexLogs 3}
--       apexOutputTsEventEntry                                                 {apexOutputTsEventTable 1}
--          apexOutputTsEventBladeNum                                           {apexOutputTsEventEntry 1}
--          apexOutputTsEventIndex                                              {apexOutputTsEventEntry 2}
--          apexOutputTsEventTimeLogged                                         {apexOutputTsEventEntry 3}
--          apexOutputTsEventAlarmCode                                          {apexOutputTsEventEntry 4}
--          apexOutputTsEventAlarmSeverity                                      {apexOutputTsEventEntry 5}
--          apexOutputTsEventOutputTsNum                                        {apexOutputTsEventEntry 6}
--          apexOutputTsEventCurRate                                            {apexOutputTsEventEntry 7}
--          apexOutputTsEventAvgRate                                            {apexOutputTsEventEntry 8}
--          apexOutputTsEventMinRate                                            {apexOutputTsEventEntry 9}
--          apexOutputTsEventPeakRate                                           {apexOutputTsEventEntry 10}
--          apexOutputTsEventDescription                                        {apexOutputTsEventEntry 11}
--    apexGbeInputTsEventTable                                                  {apexLogs 4}
--       apexGbeInputTsEventEntry                                               {apexGbeInputTsEventTable 1}
--          apexGbeInputTsEventIndex                                            {apexGbeInputTsEventEntry 1}
--          apexGbeInputTsEventTimeLogged                                       {apexGbeInputTsEventEntry 2}
--          apexGbeInputTsEventAlarmCode                                        {apexGbeInputTsEventEntry 3}
--          apexGbeInputTsEventAlarmSeverity                                    {apexGbeInputTsEventEntry 4}
--          apexGbeInputTsEventRedundantConfig                                  {apexGbeInputTsEventEntry 5}
--          apexGbeInputTsEventGbeInterface                                     {apexGbeInputTsEventEntry 6}
--          apexGbeInputTsEventUdpPort                                          {apexGbeInputTsEventEntry 7}
--          apexGbeInputTsEventDestinationIp                                    {apexGbeInputTsEventEntry 8}
--          apexGbeInputTsEventSourceIp                                         {apexGbeInputTsEventEntry 9}
--          apexGbeInputTsEventInputTsState                                     {apexGbeInputTsEventEntry 10}
--          apexGbeInputTsEventCurStreamCount                                   {apexGbeInputTsEventEntry 11}
--          apexGbeInputTsEventCurDataCount                                     {apexGbeInputTsEventEntry 12}
--          apexGbeInputTsEventDescription                                      {apexGbeInputTsEventEntry 13}
--    apexRtspEventTable                                                        {apexLogs 5}
--       apexRtspEventEntry                                                     {apexRtspEventTable 1}
--          apexRtspEventIndex                                                  {apexRtspEventEntry 1}
--          apexRtspEventTimeLogged                                             {apexRtspEventEntry 2}
--          apexRtspEventControllerIp                                           {apexRtspEventEntry 3}
--          apexRtspEventSessionCount                                           {apexRtspEventEntry 4}
--          apexRtspEventSourceDescription                                      {apexRtspEventEntry 5}
--          apexRtspEventDescription                                            {apexRtspEventEntry 6}
--    apexMappingErrorTable                                                     {apexLogs 6}
--       apexMappingErrorEntry                                                  {apexMappingErrorTable 1}
--          apexMappingErrorIndex                                               {apexMappingErrorEntry 1}
--          apexMappingErrorTimeLogged                                          {apexMappingErrorEntry 2}
--          apexMappingErrorCode                                                {apexMappingErrorEntry 3}
--          apexMappingErrorMappingType                                         {apexMappingErrorEntry 4}
--          apexMappingErrorInputInterface                                      {apexMappingErrorEntry 5}
--          apexMappingErrorUdpPort                                             {apexMappingErrorEntry 6}
--          apexMappingErrorMulticastIp                                         {apexMappingErrorEntry 7}
--          apexMappingErrorSourceIp                                            {apexMappingErrorEntry 8}
--          apexMappingErrorInputProgramPid                                     {apexMappingErrorEntry 9}
--          apexMappingErrorOutputProgramPid                                    {apexMappingErrorEntry 10}
--          apexMappingErrorOutputOpMode                                        {apexMappingErrorEntry 11}
--          apexMappingErrorOutputTsNum                                         {apexMappingErrorEntry 12}
--          apexMappingErrorBladeNum                                            {apexMappingErrorEntry 13}
--          apexMappingErrorSecInputInterface                                   {apexMappingErrorEntry 14}
--          apexMappingErrorSecUdpPort                                          {apexMappingErrorEntry 15}
--          apexMappingErrorSecMulticastIp                                      {apexMappingErrorEntry 16}
--          apexMappingErrorSecSourceIp                                         {apexMappingErrorEntry 17}
--    apexHostModuleRedundEventTable                                            {apexLogs 7}
--       apexHostModuleRedundEventEntry                                         {apexHostModuleRedundEventTable 1}
--          apexHostModuleRedundEventIndex                                      {apexHostModuleRedundEventEntry 1}
--          apexHostModuleRedundEventTimeLogged                                 {apexHostModuleRedundEventEntry 2}
--          apexHostModuleRedundEventSeverity                                   {apexHostModuleRedundEventEntry 3}
--          apexHostModuleRedundEventCode                                       {apexHostModuleRedundEventEntry 4}
--          apexHostModuleRedundEventData                                       {apexHostModuleRedundEventEntry 5}
--          apexHostModuleRedundEventDescription                                {apexHostModuleRedundEventEntry 6}
--    apexDepiEventTable                                                        {apexLogs 8}
--       apexDepiEventEntry                                                     {apexDepiEventTable 1}
--          apexDepiEventIndex                                                  {apexDepiEventEntry 1}
--          apexDepiEventTimeLogged                                             {apexDepiEventEntry 2}
--          apexDepiEventCode                                                   {apexDepiEventEntry 3}
--          apexDepiEventConnId                                                 {apexDepiEventEntry 4}
--          apexDepiEventSessionId                                              {apexDepiEventEntry 5}
--          apexDepiEventDescription                                            {apexDepiEventEntry 6}
   apexTraps                                              OBJECT IDENTIFIER ::= {apex3000 0}
--    not used for APEX                                                         {apexTraps    1}
--    not used for APEX                                                         {apexTraps    2}
--    trapConfigurationChangeInteger                                            {apexTraps    3}
--    trapConfigurationChangeDisplayString                                      {apexTraps    4}
--    trapConfigurationChangeOID                                                {apexTraps    5}
--    trapConfigurationChangeIpAddress                                          {apexTraps    6}
--    trapConditionNotInList                                                    {apexTraps   20}
--    trapConditionAlreadyInList                                                {apexTraps   21}
--    trapConditionListFull                                                     {apexTraps   22}
--    trapInvalidCaseInSwitch                                                   {apexTraps   23}
--    trapCannotCreateSemaphore                                                 {apexTraps   24}
--    trapCannotOpenSocket                                                      {apexTraps   25}
--    trapUnknownMessageReceived                                                {apexTraps   26}
--    trapInvalidMessageReceived                                                {apexTraps   27}
--
--    trapHardwareFault                                                         {apexTraps 8000}
--    trapInvalidConfigData                                                     {apexTraps 8001}
--    trapTemperatureFault                                                      {apexTraps 8002}
--    trapFanFault                                                              {apexTraps 8003}
--    trapPowerSupplyFault                                                      {apexTraps 8004}
--    trapFanModuleFault                                                        {apexTraps 8005}
--    trapHostModuleFault                                                       {apexTraps 8006}
--    trapFrontPanelModuleFault                                                 {apexTraps 8007}
--    trapRfSwitchModuleFault                                                   {apexTraps 8008}
--    trap10GbeModuleFault                                                      {apexTraps 8009}
--    trapDtiModuleFault                                                        {apexTraps 8010}
--    trapGbeLossOfPhysicalInput                                                {apexTraps 8020}
--    trapGbeBufferFullness                                                     {apexTraps 8021}
--    trapGbeInputStreamHighBitRate                                             {apexTraps 8022}
--    trapGbeInputTsRedundFailover                                              {apexTraps 8023}
--    trapServiceInError                                                        {apexTraps 8024}
--    trapGbeLossOfInputStream                                                  {apexTraps 8025}
--    trapNpuToHostCommFault                                                    {apexTraps 8026}
--    trapGbeInterfaceRedundFailover                                            {apexTraps 8027}
--    trapServiceInactiveError                                                  {apexTraps 8028}
--    trapOutputUtilizationFault                                                {apexTraps 8040}
--    trapOutputOverflow                                                        {apexTraps 8041}
--    trapQamBladeFault                                                         {apexTraps 8042}
--    trapQamRfPortFault                                                        {apexTraps 8043}
--    trapQamChannelFault                                                       {apexTraps 8044}
--    trapQamBladeRedundFailover                                                {apexTraps 8045}
--    trapQamBladeRedundMismatch                                                {apexTraps 8046}
--    trapQamBladePhysicalLatchFault                                            {apexTraps 8047}
--    trapRtspControllerCommFault                                               {apexTraps 8060}
--    trapRdsCommFault                                                          {apexTraps 8070}
--    trapHostModuleRedundFailover                                              {apexTraps 8080}
--    trapHostModuleRedundFault                                                 {apexTraps 8081}
--    trapDitSyncLossFault                                                      {apexTraps 8090}
--    trapDepiControlConnectionFault                                            {apexTraps 8091}
--
--    trapEmUserLoginFailed                                                     {apexTraps 8500}
   apexDebug                                              OBJECT IDENTIFIER ::= {apex3000 5000}


-- ------------------------------------------------------------------------------
--
-- APEX MIB
--
-- ------------------------------------------------------------------------------


-- ------------------------------------------------------------------------------
--
-- apexSys
--
-- apexSysConfig
--
-- apexSysConfigGeneral
--

apexSaveConfig OBJECT-TYPE
    SYNTAX INTEGER
        {
         notApplicable       (0),
         saveNotInProgress   (1),
         startSaveToFlash    (2),
         savingConfigToFlash (3)
        }
    MAX-ACCESS read-write
    STATUS current
    DESCRIPTION
        "Writing this object will commit the current
         configuration to Flash.  While a read returns the
         value savingConfigToFlash, the flash is being saved;
         the save may not have been initiated by an SNMP set.

         Once written, the change to this parameter will take immediate effect.

         @Config(config=no, reboot=no)
        "
        --MOT-MIBCOMP-BE-EXT <DbHint map="SCALAR" dbc_fmt="1"></DbHint>
::= { apexSysConfigGeneral 1 }

apexProductName OBJECT-TYPE
    SYNTAX DisplayString (SIZE (0..31))
    MAX-ACCESS read-write
    STATUS current
    DESCRIPTION
        "This is the Product Name of the APEX loaded at initialization from
         the config.ini file.  Specific configurations of the APEX have
         specific purposes and are identified by their product name.

         Once written, the change to this parameter will take immediate effect.
         However, in order for the change to persist through subsequent reboots
         or power cycles, the change must be saved via the apexSaveConfig parameter.

         @Config(config=yes, reboot=no)
         @Save(apexSaveConfig, value=2, default=yes)
         @File(config.ini, type='ini')
        "
::= { apexSysConfigGeneral 2 }

apexBootMethod OBJECT-TYPE
    SYNTAX INTEGER
        {
         notApplicable (0),
         noBootp       (1),
         bootpOnly     (2)
        }
    MAX-ACCESS read-write
    STATUS current
    DESCRIPTION
        "This parameter is used to set the boot method for the APEX.
         Selection of noBootp means the APEX will not use BOOTP
         - this will result in about a 10 second savings in boot time.

         Once written, the change to this parameter will take immediate effect.
         However, in order for the change to persist through subsequent reboots
         or power cycles, the change must be saved via the apexSaveConfig parameter.

         @Config(config=yes, reboot=no)
         @Save(apexSaveConfig, value=2)
         @File(config.ini, type='ini')
        "
::= { apexSysConfigGeneral 3 }


-- ------------------------------------------------------------------------------
--
-- apexSysConfigMcEmmInsertion
--

apexMcEmmInsertionMode OBJECT-TYPE
    SYNTAX INTEGER
        {
         outOfBand(1),
         fullInBand(2)
        }
    MAX-ACCESS read-write
    STATUS current
    DESCRIPTION
        "Specify the mode in which MediaCipher EMMs are inserted, out of band 
         or full in band.

         Once written, the change to this parameter will only take immediate
         effect after apexMcEmmInsertionApplyChange is set to 'apply'.  In
         order for the change to persist through subsequent reboots or power
         cycles, the change must be saved via the apexSaveConfig parameter.

         @Config(config=yes, reboot=no)
         @Commit(param=apexMcEmmInsertionApplyChange , value=2)
         @Save(apexSaveConfig, value=2)
         @File(config.ini, type='ini')
        "
::= { apexSysConfigMcEmmInsertion 1 }

apexMcEmmInsertionPid1Enable OBJECT-TYPE
    SYNTAX EnableDisableTYPE
    MAX-ACCESS read-write
    STATUS current
    DESCRIPTION
        "Enable/disable first EMM PID to include in the CAT for MediaCipher Full In Band mode.
         Default value is enabled.

         Once written, the change to this parameter will only take immediate
         effect after apexMcEmmInsertionApplyChange is set to 'apply'.  In
         order for the change to persist through subsequent reboots or power
         cycles, the change must be saved via the apexSaveConfig parameter.

         @Config(config=yes, reboot=no)
         @Commit(param=apexMcEmmInsertionApplyChange , value=2)
         @Save(apexSaveConfig, value=2)
         @File(config.ini, type='ini')
        "
::= { apexSysConfigMcEmmInsertion 2 }

apexMcEmmInsertionPid1 OBJECT-TYPE
    SYNTAX Unsigned32(7168..8190)
    MAX-ACCESS read-write
    STATUS current
    DESCRIPTION
        "First EMM PID to include in the CAT for MediaCipher Full In Band mode.
         Allowed values: from 0x1C00 to 0x1FFE.
         Default value is 0x1C02.

         Once written, the change to this parameter will only take immediate
         effect after apexMcEmmInsertionApplyChange is set to 'apply'.  In
         order for the change to persist through subsequent reboots or power
         cycles, the change must be saved via the apexSaveConfig parameter.

         @Config(config=yes, reboot=no)
         @Commit(param=apexMcEmmInsertionApplyChange , value=2)
         @Save(apexSaveConfig, value=2)
         @File(config.ini, type='ini')
        "
::= { apexSysConfigMcEmmInsertion 3 }

apexMcEmmInsertionPid2Enable OBJECT-TYPE
    SYNTAX EnableDisableTYPE
    MAX-ACCESS read-write
    STATUS current
    DESCRIPTION
        "Enable/disable first EMM PID to include in the CAT for MediaCipher Full In Band mode.
         Default value is disabled.

         Once written, the change to this parameter will only take immediate
         effect after apexMcEmmInsertionApplyChange is set to 'apply'.  In
         order for the change to persist through subsequent reboots or power
         cycles, the change must be saved via the apexSaveConfig parameter.

         @Config(config=yes, reboot=no)
         @Commit(param=apexMcEmmInsertionApplyChange , value=2)
         @Save(apexSaveConfig, value=2)
         @File(config.ini, type='ini')
        "
::= { apexSysConfigMcEmmInsertion 4 }

apexMcEmmInsertionPid2 OBJECT-TYPE
    SYNTAX Unsigned32(7168..8190)
    MAX-ACCESS read-write
    STATUS current
    DESCRIPTION
        "Second EMM PID to include in the CAT for MediaCipher Full In Band mode.
         Allowed values: from 0x1C00 to 0x1FFE.
         Default value is 0x1C03.

         Once written, the change to this parameter will only take immediate
         effect after apexMcEmmInsertionApplyChange is set to 'apply'.  In
         order for the change to persist through subsequent reboots or power
         cycles, the change must be saved via the apexSaveConfig parameter.

         @Config(config=yes, reboot=no)
         @Commit(param=apexMcEmmInsertionApplyChange , value=2)
         @Save(apexSaveConfig, value=2)
         @File(config.ini, type='ini')
        "
::= { apexSysConfigMcEmmInsertion 5 }

apexMcEmmInsertionApplyChange OBJECT-TYPE
    SYNTAX ApplyDataToDeviceTYPE
    MAX-ACCESS read-write
    STATUS current
    DESCRIPTION
        "The Apply for the MediaCipher EMM Insertion group.

         This parameter MUST be set to 'apply' in order for any of the data
         in the MC EMM Insertion group to take effect in the device.  This
         parameter MUST be set LAST after all other data in the MC Emm Insertion
         group has been configured.

         @Config(config=no, reboot=no)
        "
::= { apexSysConfigMcEmmInsertion 6 }


-- ------------------------------------------------------------------------------
--
-- apexSysStatus
--
-- apexSysStatusGeneral
--

apexBootReason OBJECT-TYPE
    SYNTAX INTEGER
        {
         powerCycle       (0),
         operatorReboot   (1),
         hwFault          (2)
        }
    MAX-ACCESS read-only
    STATUS current
    DESCRIPTION
        "Indicates reason for APEX boot:
            'powerCycle'       - Power-up or power cycled.
            'operatorReboot'   - Operator commanded reboot (refer to manual).
            'hwFault'          - Automatic reboot occurred as per apexAutoRebootEnable.
        "
::= { apexSysStatusGeneral 1 }

apexMaxServiceMappings OBJECT-TYPE
    SYNTAX Integer32
    MAX-ACCESS read-only
    STATUS current
    DESCRIPTION
        "Maximum number of service mappings supported by the APEX.
        "
::= { apexSysStatusGeneral 2 }


-- ------------------------------------------------------------------------------
--
-- apexSysStatusVersions
--

apexProductType OBJECT-TYPE
    SYNTAX INTEGER
        {
         invalid         (0),
         apex3000        (1)
        }
    MAX-ACCESS read-only
    STATUS current
    DESCRIPTION
        "APEX Product Type.  The corresponding product name
         text setting can be found in identUnitModel."
::= { apexSysStatusVersions 1 }


-- ------------------------------------------------------------------------------
--
-- apexSysStatusModules
--
-- apexSysStatFrontPanelModule                   
--

apexSysStatFrontPanelModulePresent OBJECT-TYPE
    SYNTAX ModulePresentTYPE
    MAX-ACCESS read-only
    STATUS current
    DESCRIPTION
        "Indicates whether the module is Present or Missing."
::= { apexSysStatFrontPanelModule 1 }

apexSysStatFrontPanelModuleType OBJECT-TYPE
    SYNTAX INTEGER
        {
         unknown         (0),
         frontPanelType1 (1)
        }
    MAX-ACCESS read-only
    STATUS current
    DESCRIPTION
        "Indicates type of module."
::= { apexSysStatFrontPanelModule 2 }

apexSysStatFrontPanelModuleAvailable OBJECT-TYPE
    SYNTAX ModuleAvailableTYPE
    MAX-ACCESS read-only
    STATUS current
    DESCRIPTION
        "Indicates whether the module is Available for use."
::= { apexSysStatFrontPanelModule 3 }

apexSysStatFrontPanelModuleSerialNumber OBJECT-TYPE
    SYNTAX DisplayString (SIZE (0..31))
    MAX-ACCESS read-only
    STATUS current
    DESCRIPTION
        "Serial Number."
::= { apexSysStatFrontPanelModule 4 }

apexSysStatFrontPanelModuleHardwareVersion OBJECT-TYPE
    SYNTAX DisplayString (SIZE (0..31))
    MAX-ACCESS read-only
    STATUS current
    DESCRIPTION
        "Hardware Revision."
::= { apexSysStatFrontPanelModule 5 }

apexSysStatFrontPanelModuleMicroCtrlVersion OBJECT-TYPE
    SYNTAX DisplayString (SIZE (0..31))
    MAX-ACCESS read-only
    STATUS current
    DESCRIPTION
        "Microcontroller Firmware Version."
::= { apexSysStatFrontPanelModule 6 }

apexSysStatFrontPanelModuleGoodStatusPollCounts OBJECT-TYPE
    SYNTAX Counter32
    MAX-ACCESS read-only
    STATUS current
    DESCRIPTION
        "The number of good status polls to the module."
::= { apexSysStatFrontPanelModule 7 }

apexSysStatFrontPanelModuleBadStatusPollCounts OBJECT-TYPE
    SYNTAX Counter32
    MAX-ACCESS read-only
    STATUS current
    DESCRIPTION
        "The number of failed status polls to the module."
::= { apexSysStatFrontPanelModule 8 }


-- ------------------------------------------------------------------------------
--
-- apexSysStatDtiModule
--

apexSysStatDtiModulePresent OBJECT-TYPE
    SYNTAX ModulePresentTYPE
    MAX-ACCESS read-only
    STATUS current
    DESCRIPTION
        "Indicates whether the module is Present or Missing."
::= { apexSysStatDtiModule 1 }

apexSysStatDtiModuleType OBJECT-TYPE
    SYNTAX INTEGER
        {
         unknown  (0),
         dtiType1 (1)
        }
    MAX-ACCESS read-only
    STATUS current
    DESCRIPTION
        "Indicates type of module."
::= { apexSysStatDtiModule 2 }

apexSysStatDtiModuleAvailable OBJECT-TYPE
    SYNTAX ModuleAvailableTYPE
    MAX-ACCESS read-only
    STATUS current
    DESCRIPTION
        "Indicates whether the module is Available for use."
::= { apexSysStatDtiModule 3 }

apexSysStatDtiModuleSerialNumber OBJECT-TYPE
    SYNTAX DisplayString (SIZE (0..31))
    MAX-ACCESS read-only
    STATUS current
    DESCRIPTION
        "Serial Number."
::= { apexSysStatDtiModule 4 }

apexSysStatDtiModuleHardwareVersion OBJECT-TYPE
    SYNTAX DisplayString (SIZE (0..31))
    MAX-ACCESS read-only
    STATUS current
    DESCRIPTION
        "Hardware Revision."
::= { apexSysStatDtiModule 5 }

apexSysStatDtiModuleMicroCtrlVersion OBJECT-TYPE
    SYNTAX DisplayString (SIZE (0..31))
    MAX-ACCESS read-only
    STATUS current
    DESCRIPTION
        "Microcontroller Firmware Version."
::= { apexSysStatDtiModule 6 }

apexSysStatDtiModuleGoodStatusPollCounts OBJECT-TYPE
    SYNTAX Counter32
    MAX-ACCESS read-only
    STATUS current
    DESCRIPTION
        "The number of good status polls to the module."
::= { apexSysStatDtiModule 7 }

apexSysStatDtiModuleBadStatusPollCounts OBJECT-TYPE
    SYNTAX Counter32
    MAX-ACCESS read-only
    STATUS current
    DESCRIPTION
        "The number of failed status polls to the module."
::= { apexSysStatDtiModule 8 }

apexSysStatDtiModuleFpgaVersion OBJECT-TYPE
    SYNTAX DisplayString (SIZE (0..31))
    MAX-ACCESS read-only
    STATUS current
    DESCRIPTION
        "FPGA Version."
::= { apexSysStatDtiModule 9 }


-- ------------------------------------------------------------------------------
--
-- apexSysStatHostModuleTable
--

apexSysStatHostModuleTable OBJECT-TYPE
    SYNTAX SEQUENCE OF ApexSysStatHostModuleEntry
    MAX-ACCESS not-accessible
    STATUS current
    DESCRIPTION
        "Table of Host Module Status."
::= { apexSysStatusModules 3 }

apexSysStatHostModuleEntry OBJECT-TYPE
    SYNTAX ApexSysStatHostModuleEntry
    MAX-ACCESS not-accessible
    STATUS current
    DESCRIPTION
        "Host Module Status Table Entry."
    INDEX { apexSysStatHostModuleNum }
::= { apexSysStatHostModuleTable 1 }

ApexSysStatHostModuleEntry ::= SEQUENCE
    {
     apexSysStatHostModuleNum                  Integer32,
     apexSysStatHostModulePresent              ModulePresentTYPE,
     apexSysStatHostModuleType                 INTEGER,
     apexSysStatHostModuleAvailable            ModuleAvailableTYPE,
     apexSysStatHostModuleSerialNumber         DisplayString,
     apexSysStatHostModuleHardwareVersion      DisplayString,
     apexSysStatHostModuleMicroCtrlVersion     DisplayString,
     apexSysStatHostModuleBootCodeVersion      DisplayString,
     apexSysStatHostModuleApplicationDate      DisplayString,
     apexSysStatHostModuleGlueFpgaVersion      DisplayString,
     apexSysStatHostModuleAppVersion           DisplayString,
     apexSysStatHostModuleAmpAppDate           DisplayString,
     apexSysStatHostModuleAmpAppVersion        DisplayString,
     apexSysStatHostModuleGoodStatusPollCounts Counter32,
     apexSysStatHostModuleBadStatusPollCounts  Counter32
    }

apexSysStatHostModuleNum OBJECT-TYPE
    SYNTAX Integer32(1..2)
    MAX-ACCESS not-accessible
    STATUS current
    DESCRIPTION
        "Host Module Number."
::= { apexSysStatHostModuleEntry 1 }
                      
apexSysStatHostModulePresent OBJECT-TYPE
    SYNTAX ModulePresentTYPE
    MAX-ACCESS read-only
    STATUS current
    DESCRIPTION
        "Indicates whether the module is Present or Missing."
::= { apexSysStatHostModuleEntry 2 }

apexSysStatHostModuleType OBJECT-TYPE
    SYNTAX INTEGER
        {
         unknown   (0),
         hostType1 (1)
        }
    MAX-ACCESS read-only
    STATUS current
    DESCRIPTION
        "Indicates type of module."
::= { apexSysStatHostModuleEntry 3 }

apexSysStatHostModuleAvailable OBJECT-TYPE
    SYNTAX ModuleAvailableTYPE
    MAX-ACCESS read-only
    STATUS current
    DESCRIPTION
        "Indicates whether the module is Available for use."
::= { apexSysStatHostModuleEntry 4 }

apexSysStatHostModuleSerialNumber OBJECT-TYPE
    SYNTAX DisplayString (SIZE (0..31))
    MAX-ACCESS read-only
    STATUS current
    DESCRIPTION
        "Serial Number."
::= { apexSysStatHostModuleEntry 5 }

apexSysStatHostModuleHardwareVersion OBJECT-TYPE
    SYNTAX DisplayString (SIZE (0..31))
    MAX-ACCESS read-only
    STATUS current
    DESCRIPTION
        "Hardware Revision."
::= { apexSysStatHostModuleEntry 6 }

apexSysStatHostModuleMicroCtrlVersion OBJECT-TYPE
    SYNTAX DisplayString (SIZE (0..31))
    MAX-ACCESS read-only
    STATUS current
    DESCRIPTION
        "Microcontroller Firmware Version."
::= { apexSysStatHostModuleEntry 7 }
                      
apexSysStatHostModuleBootCodeVersion OBJECT-TYPE
    SYNTAX DisplayString (SIZE (0..31))
    MAX-ACCESS read-only
    STATUS current
    DESCRIPTION
        "Host Processor Boot Code Version."
::= { apexSysStatHostModuleEntry 8 }

apexSysStatHostModuleApplicationDate OBJECT-TYPE
    SYNTAX DisplayString (SIZE (0..31))
    MAX-ACCESS read-only
    STATUS current
    DESCRIPTION
        "Host Processor Application Creation Date."
::= { apexSysStatHostModuleEntry 9 }

apexSysStatHostModuleGlueFpgaVersion OBJECT-TYPE
    SYNTAX DisplayString (SIZE (0..31))
    MAX-ACCESS read-only
    STATUS current
    DESCRIPTION
        "Glue FPGA Version."
::= { apexSysStatHostModuleEntry 10 }

apexSysStatHostModuleAppVersion OBJECT-TYPE
    SYNTAX DisplayString (SIZE (0..31))
    MAX-ACCESS read-only
    STATUS current
    DESCRIPTION
        "Host Processor Main application SW Version."
::= { apexSysStatHostModuleEntry 11 }

apexSysStatHostModuleAmpAppDate OBJECT-TYPE
    SYNTAX DisplayString (SIZE (0..31))
    MAX-ACCESS read-only
    STATUS current
    DESCRIPTION
        "Host Processor AMP core application SW creation Date."
::= { apexSysStatHostModuleEntry 12 }

apexSysStatHostModuleAmpAppVersion OBJECT-TYPE
    SYNTAX DisplayString (SIZE (0..31))
    MAX-ACCESS read-only
    STATUS current
    DESCRIPTION
        "Host Processor AMP core application SW Version."
::= { apexSysStatHostModuleEntry 13 }

apexSysStatHostModuleGoodStatusPollCounts OBJECT-TYPE
    SYNTAX Counter32
    MAX-ACCESS read-only
    STATUS current
    DESCRIPTION
        "The number of good status polls to the module."
::= { apexSysStatHostModuleEntry 14 }

apexSysStatHostModuleBadStatusPollCounts OBJECT-TYPE
    SYNTAX Counter32
    MAX-ACCESS read-only
    STATUS current
    DESCRIPTION
        "The number of failed status polls to the module."
::= { apexSysStatHostModuleEntry 15 }


-- ------------------------------------------------------------------------------
--
-- apexSysStat10GbeModuleTable
--

apexSysStat10GbeModuleTable OBJECT-TYPE
    SYNTAX SEQUENCE OF ApexSysStat10GbeModuleEntry
    MAX-ACCESS not-accessible
    STATUS current
    DESCRIPTION
        "Table of 10Gbe Module Status."
::= { apexSysStatusModules 4 }

apexSysStat10GbeModuleEntry OBJECT-TYPE
    SYNTAX ApexSysStat10GbeModuleEntry
    MAX-ACCESS not-accessible
    STATUS current
    DESCRIPTION
        "10Gbe Module Status Table Entry."
    INDEX { apexSysStat10GbeModuleNum }
::= { apexSysStat10GbeModuleTable 1 }

ApexSysStat10GbeModuleEntry ::= SEQUENCE
    {
     apexSysStat10GbeModuleNum                  Integer32,
     apexSysStat10GbeModuleType                 INTEGER,
     apexSysStat10GbeModulePresent              ModulePresentTYPE,
     apexSysStat10GbeModuleAvailable            ModuleAvailableTYPE,
     apexSysStat10GbeModuleSerialNumber         DisplayString,
     apexSysStat10GbeModuleHardwareVersion      DisplayString,
     apexSysStat10GbeModuleMicroCtrlVersion     DisplayString,
     apexSysStat10GbeModuleGoodStatusPollCounts Counter32,
     apexSysStat10GbeModuleBadStatusPollCounts  Counter32
    }

apexSysStat10GbeModuleNum OBJECT-TYPE
    SYNTAX Integer32(1..3)
    MAX-ACCESS not-accessible
    STATUS current
    DESCRIPTION
        "10Gbe Module Number."
::= { apexSysStat10GbeModuleEntry 1 }
                      
apexSysStat10GbeModulePresent OBJECT-TYPE
    SYNTAX ModulePresentTYPE
    MAX-ACCESS read-only
    STATUS current
    DESCRIPTION
        "Indicates whether the module is Present or Missing."
::= { apexSysStat10GbeModuleEntry 2 }

apexSysStat10GbeModuleType OBJECT-TYPE
    SYNTAX INTEGER
        {
         unknown     (0),
         tenGbeType1 (1)
        }
    MAX-ACCESS read-only
    STATUS current
    DESCRIPTION
        "Indicates type of module."
::= { apexSysStat10GbeModuleEntry 3 }

apexSysStat10GbeModuleAvailable OBJECT-TYPE
    SYNTAX ModuleAvailableTYPE
    MAX-ACCESS read-only
    STATUS current
    DESCRIPTION
        "Indicates whether the module is Available for use."
::= { apexSysStat10GbeModuleEntry 4 }

apexSysStat10GbeModuleSerialNumber OBJECT-TYPE
    SYNTAX DisplayString (SIZE (0..31))
    MAX-ACCESS read-only
    STATUS current
    DESCRIPTION
        "Serial Number."
::= { apexSysStat10GbeModuleEntry 5 }

apexSysStat10GbeModuleHardwareVersion OBJECT-TYPE
    SYNTAX DisplayString (SIZE (0..31))
    MAX-ACCESS read-only
    STATUS current
    DESCRIPTION
        "Hardware Revision."
::= { apexSysStat10GbeModuleEntry 6 }

apexSysStat10GbeModuleMicroCtrlVersion OBJECT-TYPE
    SYNTAX DisplayString (SIZE (0..31))
    MAX-ACCESS read-only
    STATUS current
    DESCRIPTION
        "Microcontroller Firmware Version."
::= { apexSysStat10GbeModuleEntry 7 }

apexSysStat10GbeModuleGoodStatusPollCounts OBJECT-TYPE
    SYNTAX Counter32
    MAX-ACCESS read-only
    STATUS current
    DESCRIPTION
        "The number of good status polls to the module."
::= { apexSysStat10GbeModuleEntry 8 }

apexSysStat10GbeModuleBadStatusPollCounts OBJECT-TYPE
    SYNTAX Counter32
    MAX-ACCESS read-only
    STATUS current
    DESCRIPTION
        "The number of failed status polls to the module."
::= { apexSysStat10GbeModuleEntry 9 }


-- ------------------------------------------------------------------------------
--
-- apexSysStatQamBladeTable
--

apexSysStatQamBladeTable OBJECT-TYPE
    SYNTAX SEQUENCE OF ApexSysStatQamBladeEntry
    MAX-ACCESS not-accessible
    STATUS current
    DESCRIPTION
        "Table of QAM Blade Status."
::= { apexSysStatusModules 5 }

apexSysStatQamBladeEntry OBJECT-TYPE
    SYNTAX ApexSysStatQamBladeEntry
    MAX-ACCESS not-accessible
    STATUS current
    DESCRIPTION
        "QAM Blade Status Table Entry."
    INDEX { apexSysStatQamBladeNum }
::= { apexSysStatQamBladeTable 1 }

ApexSysStatQamBladeEntry ::= SEQUENCE
    {
     apexSysStatQamBladeNum                    Integer32,
     apexSysStatQamBladePresent                ModulePresentTYPE,
     apexSysStatQamBladeType                   INTEGER,
     apexSysStatQamBladeAvailable              ModuleAvailableTYPE,
     apexSysStatQamBladeSerialNumber           DisplayString,
     apexSysStatQamBladeHardwareVersion        DisplayString,
     apexSysStatQamBladeMicroCtrlVersion       DisplayString,
     apexSysStatQamBladeNpuBootCodeVersion     DisplayString,
     apexSysStatQamBladeNpuApplicationVersion  DisplayString,
     apexSysStatQamBladeMuxFpgaVersion         DisplayString,
     apexSysStatQamBladeIngressFpgaVersion     DisplayString,
     apexSysStatQamBladeLatched                ModuleLatchedTYPE,
     apexSysStatQamBladeClockSource            INTEGER,
     apexSysStatQamBladeGoodStatusPollCounts   Counter32,
     apexSysStatQamBladeBadStatusPollCounts    Counter32
    }

apexSysStatQamBladeNum OBJECT-TYPE
    SYNTAX Integer32(1..8)
    MAX-ACCESS not-accessible
    STATUS current
    DESCRIPTION
        "QAM Blade Number."
::= { apexSysStatQamBladeEntry 1 }
                      
apexSysStatQamBladePresent OBJECT-TYPE
    SYNTAX ModulePresentTYPE
    MAX-ACCESS read-only
    STATUS current
    DESCRIPTION
        "Indicates whether the QAM Blade is Present or Missing."
::= { apexSysStatQamBladeEntry 2 }

apexSysStatQamBladeType OBJECT-TYPE
    SYNTAX INTEGER
        {
         unknown       (0),
         qamBladeType1 (1)
        }
    MAX-ACCESS read-only
    STATUS current
    DESCRIPTION
        "Indicates type of module."
::= { apexSysStatQamBladeEntry 3 }

apexSysStatQamBladeAvailable OBJECT-TYPE
    SYNTAX ModuleAvailableTYPE
    MAX-ACCESS read-only
    STATUS current
    DESCRIPTION
        "Indicates whether the QAM Blade is Available for use."
::= { apexSysStatQamBladeEntry 4 }

apexSysStatQamBladeSerialNumber OBJECT-TYPE
    SYNTAX DisplayString (SIZE (0..31))
    MAX-ACCESS read-only
    STATUS current
    DESCRIPTION
        "Serial Number."
::= { apexSysStatQamBladeEntry 5 }

apexSysStatQamBladeHardwareVersion OBJECT-TYPE
    SYNTAX DisplayString (SIZE (0..31))
    MAX-ACCESS read-only
    STATUS current
    DESCRIPTION
        "Hardware Revision."
::= { apexSysStatQamBladeEntry 6 }

apexSysStatQamBladeMicroCtrlVersion OBJECT-TYPE
    SYNTAX DisplayString (SIZE (0..31))
    MAX-ACCESS read-only
    STATUS current
    DESCRIPTION
        "Microcontroller Firmware Version."
::= { apexSysStatQamBladeEntry 7 }

apexSysStatQamBladeNpuBootCodeVersion OBJECT-TYPE
    SYNTAX DisplayString (SIZE (0..31))
    MAX-ACCESS read-only
    STATUS current
    DESCRIPTION
        "NPU Boot Code Version"
::= { apexSysStatQamBladeEntry 8 }

apexSysStatQamBladeNpuApplicationVersion OBJECT-TYPE
    SYNTAX DisplayString (SIZE (0..31))
    MAX-ACCESS read-only
    STATUS current
    DESCRIPTION
        "NPU Application Firmware Version."
::= { apexSysStatQamBladeEntry 9 }

apexSysStatQamBladeMuxFpgaVersion OBJECT-TYPE
    SYNTAX DisplayString (SIZE (0..31))
    MAX-ACCESS read-only
    STATUS current
    DESCRIPTION
        "MUX/Encryption FPGA Version."
::= { apexSysStatQamBladeEntry 10 }

apexSysStatQamBladeIngressFpgaVersion OBJECT-TYPE
    SYNTAX DisplayString (SIZE (0..31))
    MAX-ACCESS read-only
    STATUS current
    DESCRIPTION
        "Ingress/Glue FPGA Version."
::= { apexSysStatQamBladeEntry 11 }

apexSysStatQamBladeLatched OBJECT-TYPE
    SYNTAX ModuleLatchedTYPE
    MAX-ACCESS read-only
    STATUS current
    DESCRIPTION
        "Indicates whether the QAM Blade's physical latch is closed or opened."
::= { apexSysStatQamBladeEntry 12 }

apexSysStatQamBladeClockSource OBJECT-TYPE
    SYNTAX INTEGER
        {
          notApplicable(0),
          internal(1),
          external(2)
        }
    MAX-ACCESS read-only
    STATUS current
    DESCRIPTION
        "Indicates clock source for the QAM Blade."
::= { apexSysStatQamBladeEntry 13 }

apexSysStatQamBladeGoodStatusPollCounts OBJECT-TYPE
    SYNTAX Counter32
    MAX-ACCESS read-only
    STATUS current
    DESCRIPTION
        "The number of good status polls to the QAM blade."
::= { apexSysStatQamBladeEntry 14 }

apexSysStatQamBladeBadStatusPollCounts OBJECT-TYPE
    SYNTAX Counter32
    MAX-ACCESS read-only
    STATUS current
    DESCRIPTION
        "The number of failed status polls to the QAM blade."
::= { apexSysStatQamBladeEntry 15 }


-- ------------------------------------------------------------------------------
--
-- apexSysStatRfModuleTable
--

apexSysStatRfModuleTable OBJECT-TYPE
    SYNTAX SEQUENCE OF ApexSysStatRfModuleEntry
    MAX-ACCESS not-accessible
    STATUS current
    DESCRIPTION
        "Table of RF Module Status."
::= { apexSysStatusModules 6 }

apexSysStatRfModuleEntry OBJECT-TYPE
    SYNTAX ApexSysStatRfModuleEntry
    MAX-ACCESS not-accessible
    STATUS current
    DESCRIPTION
        "RF Module Status Table Entry."
    INDEX { apexSysStatRfModuleNum }
::= { apexSysStatRfModuleTable 1 }

ApexSysStatRfModuleEntry ::= SEQUENCE
    {
     apexSysStatRfModuleNum                   Integer32,
     apexSysStatRfModulePresent               ModulePresentTYPE,
     apexSysStatRfModuleType                  INTEGER,
     apexSysStatRfModuleSerialNumber          DisplayString,
     apexSysStatRfModuleHardwareVersion       DisplayString,
     apexSysStatRfModuleFwBootCodeVersion     DisplayString,
     apexSysStatRfModuleFwApplicationVersion  DisplayString,
     apexSysStatRfModuleFwAppBuildNumber      DisplayString,
     apexSysStatRfModuleFpgaVersion           DisplayString,
     apexSysStatRfModuleCodeFileVersion       DisplayString,
     apexSysStatRfModuleCalibrationVersion    DisplayString,
     apexSysStatRfModuleTestVersion           DisplayString
    }

apexSysStatRfModuleNum OBJECT-TYPE
    SYNTAX Integer32(1..8)
    MAX-ACCESS not-accessible
    STATUS current
    DESCRIPTION
        "RF Module Number."
::= { apexSysStatRfModuleEntry 1 }
                      
apexSysStatRfModulePresent OBJECT-TYPE
    SYNTAX ModulePresentTYPE
    MAX-ACCESS read-only
    STATUS current
    DESCRIPTION
        "Indicates whether the module is Present or Missing."
::= { apexSysStatRfModuleEntry 2 }

apexSysStatRfModuleType OBJECT-TYPE
    SYNTAX INTEGER
        {
         unknown       (0),
         rfModuleType1 (1)
        }
    MAX-ACCESS read-only
    STATUS current
    DESCRIPTION
        "Indicates type of module."
::= { apexSysStatRfModuleEntry 3 }

apexSysStatRfModuleSerialNumber OBJECT-TYPE
    SYNTAX DisplayString (SIZE (0..31))
    MAX-ACCESS read-only
    STATUS current
    DESCRIPTION
        "Serial Number.
         
         20-byte, ASCII encoded as follows:
            PPPPMMYDDDSSSSSCAABB
         Where:
            PPPP:  Product code (3000)
            MM:    Manufacturing location code
            Y:     Year code
            DDD:   Day code
            SSSSS: Serial number
            C:     Mod 10 checksum of previous bytes
            AA:    Assembly revision (alphanumeric)
            BB:    SMT revision (alphanumeric)
        "
::= { apexSysStatRfModuleEntry 4 }

apexSysStatRfModuleHardwareVersion OBJECT-TYPE
    SYNTAX DisplayString (SIZE (0..31))
    MAX-ACCESS read-only
    STATUS current
    DESCRIPTION
        "Hardware Revision."
::= { apexSysStatRfModuleEntry 5 }

apexSysStatRfModuleFwBootCodeVersion OBJECT-TYPE
    SYNTAX DisplayString (SIZE (0..31))
    MAX-ACCESS read-only
    STATUS current
    DESCRIPTION
        "Firmware Bootloader Version."
::= { apexSysStatRfModuleEntry 6 }
                      
apexSysStatRfModuleFwApplicationVersion OBJECT-TYPE
    SYNTAX DisplayString (SIZE (0..31))
    MAX-ACCESS read-only
    STATUS current
    DESCRIPTION
        "Firmware Application Version."
::= { apexSysStatRfModuleEntry 7 }
                      
apexSysStatRfModuleFwAppBuildNumber OBJECT-TYPE
    SYNTAX DisplayString (SIZE (0..31))
    MAX-ACCESS read-only
    STATUS current
    DESCRIPTION
        "Firmware Application Build Number."
::= { apexSysStatRfModuleEntry 8 }
                      
apexSysStatRfModuleFpgaVersion OBJECT-TYPE
    SYNTAX DisplayString (SIZE (0..31))
    MAX-ACCESS read-only
    STATUS current
    DESCRIPTION
        "FPGA Version."
::= { apexSysStatRfModuleEntry 9 }
                      
apexSysStatRfModuleCodeFileVersion OBJECT-TYPE
    SYNTAX DisplayString (SIZE (0..31))
    MAX-ACCESS read-only
    STATUS current
    DESCRIPTION
        "Code File Version."
::= { apexSysStatRfModuleEntry 10 }
                      
apexSysStatRfModuleCalibrationVersion OBJECT-TYPE
    SYNTAX DisplayString (SIZE (0..31))
    MAX-ACCESS read-only
    STATUS current
    DESCRIPTION
        "Calibration Version.
         Firmware Application Version at calibration."
::= { apexSysStatRfModuleEntry 11 }
                      
apexSysStatRfModuleTestVersion OBJECT-TYPE
    SYNTAX DisplayString (SIZE (0..31))
    MAX-ACCESS read-only
    STATUS current
    DESCRIPTION
        "Test Version.  Factory Test Revision."
::= { apexSysStatRfModuleEntry 12 }
                      

-- ------------------------------------------------------------------------------
--
-- apexSysStatRfSwitchModuleTable
--

apexSysStatRfSwitchModuleTable OBJECT-TYPE
    SYNTAX SEQUENCE OF ApexSysStatRfSwitchModuleEntry
    MAX-ACCESS not-accessible
    STATUS current
    DESCRIPTION
        "Table of RF Switch Module Status."
::= { apexSysStatusModules 7 }

apexSysStatRfSwitchModuleEntry OBJECT-TYPE
    SYNTAX ApexSysStatRfSwitchModuleEntry
    MAX-ACCESS not-accessible
    STATUS current
    DESCRIPTION
        "RF Switch Module Status Table Entry."
    INDEX { apexSysStatRfSwitchModuleNum }
::= { apexSysStatRfSwitchModuleTable 1 }

ApexSysStatRfSwitchModuleEntry ::= SEQUENCE
    {
     apexSysStatRfSwitchModuleNum                  Integer32,
     apexSysStatRfSwitchModulePresent              ModulePresentTYPE,
     apexSysStatRfSwitchModuleType                 INTEGER,
     apexSysStatRfSwitchModuleAvailable            ModuleAvailableTYPE,
     apexSysStatRfSwitchModuleSerialNumber         DisplayString,
     apexSysStatRfSwitchModuleHardwareVersion      DisplayString,
     apexSysStatRfSwitchModuleMicroCtrlVersion     DisplayString,
     apexSysStatRfSwitchModuleGoodStatusPollCounts Counter32,
     apexSysStatRfSwitchModuleBadStatusPollCounts  Counter32
    }

apexSysStatRfSwitchModuleNum OBJECT-TYPE
    SYNTAX Integer32(1..4)
    MAX-ACCESS not-accessible
    STATUS current
    DESCRIPTION
        "RF Switch Module Number."
::= { apexSysStatRfSwitchModuleEntry 1 }
                      
apexSysStatRfSwitchModulePresent OBJECT-TYPE
    SYNTAX ModulePresentTYPE
    MAX-ACCESS read-only
    STATUS current
    DESCRIPTION
        "Indicates whether the module is Present or Missing."
::= { apexSysStatRfSwitchModuleEntry 2 }

apexSysStatRfSwitchModuleType OBJECT-TYPE
    SYNTAX INTEGER
        {
         unknown       (0),
         rfSwitchType1 (1)
        }
    MAX-ACCESS read-only
    STATUS current
    DESCRIPTION
        "Indicates type of module."
::= { apexSysStatRfSwitchModuleEntry 3 }

apexSysStatRfSwitchModuleAvailable OBJECT-TYPE
    SYNTAX ModuleAvailableTYPE
    MAX-ACCESS read-only
    STATUS current
    DESCRIPTION
        "Indicates whether the module is Available for use."
::= { apexSysStatRfSwitchModuleEntry 4 }

apexSysStatRfSwitchModuleSerialNumber OBJECT-TYPE
    SYNTAX DisplayString (SIZE (0..31))
    MAX-ACCESS read-only
    STATUS current
    DESCRIPTION
        "Serial Number."
::= { apexSysStatRfSwitchModuleEntry 5 }

apexSysStatRfSwitchModuleHardwareVersion OBJECT-TYPE
    SYNTAX DisplayString (SIZE (0..31))
    MAX-ACCESS read-only
    STATUS current
    DESCRIPTION
        "Hardware Revision."
::= { apexSysStatRfSwitchModuleEntry 6 }

apexSysStatRfSwitchModuleMicroCtrlVersion OBJECT-TYPE
    SYNTAX DisplayString (SIZE (0..31))
    MAX-ACCESS read-only
    STATUS current
    DESCRIPTION
        "Microcontroller Firmware Version."
::= { apexSysStatRfSwitchModuleEntry 7 }
                      
apexSysStatRfSwitchModuleGoodStatusPollCounts OBJECT-TYPE
    SYNTAX Counter32
    MAX-ACCESS read-only
    STATUS current
    DESCRIPTION
        "The number of good status polls to the module."
::= { apexSysStatRfSwitchModuleEntry 8 }

apexSysStatRfSwitchModuleBadStatusPollCounts OBJECT-TYPE
    SYNTAX Counter32
    MAX-ACCESS read-only
    STATUS current
    DESCRIPTION
        "The number of failed status polls to the module."
::= { apexSysStatRfSwitchModuleEntry 9 }


-- ------------------------------------------------------------------------------
--
-- apexSysStatFanFillerModuleTable
--

apexSysStatFanFillerModuleTable OBJECT-TYPE
    SYNTAX SEQUENCE OF ApexSysStatFanFillerModuleEntry
    MAX-ACCESS not-accessible
    STATUS current
    DESCRIPTION
        "Table of QAM Blade Slot Fan Filler Module Status."
::= { apexSysStatusModules 8 }

apexSysStatFanFillerModuleEntry OBJECT-TYPE
    SYNTAX ApexSysStatFanFillerModuleEntry
    MAX-ACCESS not-accessible
    STATUS current
    DESCRIPTION
        "QAM Blade Slot Fan Filler Module Status Table Entry."
    INDEX { apexSysStatFanFillerModuleNum }
::= { apexSysStatFanFillerModuleTable 1 }

ApexSysStatFanFillerModuleEntry ::= SEQUENCE
    {
     apexSysStatFanFillerModuleNum                  Integer32,
     apexSysStatFanFillerModulePresent              ModulePresentTYPE,
     apexSysStatFanFillerModuleType                 INTEGER,
     apexSysStatFanFillerModuleAvailable            ModuleAvailableTYPE,
     apexSysStatFanFillerModuleSerialNumber         DisplayString,
     apexSysStatFanFillerModuleHardwareVersion      DisplayString,
     apexSysStatFanFillerModuleMicroCtrlVersion     DisplayString,
     apexSysStatFanFillerModuleGoodStatusPollCounts Counter32,
     apexSysStatFanFillerModuleBadStatusPollCounts  Counter32
    }

apexSysStatFanFillerModuleNum OBJECT-TYPE
    SYNTAX Integer32(1..8)
    MAX-ACCESS not-accessible
    STATUS current
    DESCRIPTION
        "QAM Blade Slot Number."
::= { apexSysStatFanFillerModuleEntry 1 }
                      
apexSysStatFanFillerModulePresent OBJECT-TYPE
    SYNTAX ModulePresentTYPE
    MAX-ACCESS read-only
    STATUS current
    DESCRIPTION
        "Indicates whether the module is Present or Missing."
::= { apexSysStatFanFillerModuleEntry 2 }

apexSysStatFanFillerModuleType OBJECT-TYPE
    SYNTAX INTEGER
        {
         unknown        (0),
         fanFillerType1 (1)
        }
    MAX-ACCESS read-only
    STATUS current
    DESCRIPTION
        "Indicates type of module."
::= { apexSysStatFanFillerModuleEntry 3 }

apexSysStatFanFillerModuleAvailable OBJECT-TYPE
    SYNTAX ModuleAvailableTYPE
    MAX-ACCESS read-only
    STATUS current
    DESCRIPTION
        "Indicates whether the module is Available for use."
::= { apexSysStatFanFillerModuleEntry 4 }

apexSysStatFanFillerModuleSerialNumber OBJECT-TYPE
    SYNTAX DisplayString (SIZE (0..31))
    MAX-ACCESS read-only
    STATUS current
    DESCRIPTION
        "Serial Number."
::= { apexSysStatFanFillerModuleEntry 5 }

apexSysStatFanFillerModuleHardwareVersion OBJECT-TYPE
    SYNTAX DisplayString (SIZE (0..31))
    MAX-ACCESS read-only
    STATUS current
    DESCRIPTION
        "Hardware Revision."
::= { apexSysStatFanFillerModuleEntry 6 }

apexSysStatFanFillerModuleMicroCtrlVersion OBJECT-TYPE
    SYNTAX DisplayString (SIZE (0..31))
    MAX-ACCESS read-only
    STATUS current
    DESCRIPTION
        "Microcontroller Firmware Version."
::= { apexSysStatFanFillerModuleEntry 7 }

apexSysStatFanFillerModuleGoodStatusPollCounts OBJECT-TYPE
    SYNTAX Counter32
    MAX-ACCESS read-only
    STATUS current
    DESCRIPTION
        "The number of good status polls to the module."
::= { apexSysStatFanFillerModuleEntry 8 }

apexSysStatFanFillerModuleBadStatusPollCounts OBJECT-TYPE
    SYNTAX Counter32
    MAX-ACCESS read-only
    STATUS current
    DESCRIPTION
        "The number of failed status polls to the module."
::= { apexSysStatFanFillerModuleEntry 9 }


-- ------------------------------------------------------------------------------
--
-- apexSysStatPowerSupplyModuleTable
--

apexSysStatPowerSupplyModuleTable OBJECT-TYPE
    SYNTAX SEQUENCE OF ApexSysStatPowerSupplyModuleEntry
    MAX-ACCESS not-accessible
    STATUS current
    DESCRIPTION
        "Table of Power Supply Module Status."
::= { apexSysStatusModules 9 }

apexSysStatPowerSupplyModuleEntry OBJECT-TYPE
    SYNTAX ApexSysStatPowerSupplyModuleEntry
    MAX-ACCESS not-accessible
    STATUS current
    DESCRIPTION
        "Power Supply Module Status Table Entry."
    INDEX { apexSysStatPowerSupplyModuleNum }
::= { apexSysStatPowerSupplyModuleTable 1 }

ApexSysStatPowerSupplyModuleEntry ::= SEQUENCE
    {
     apexSysStatPowerSupplyModuleNum           Integer32,
     apexSysStatPowerSupplyModulePresent       ModulePresentTYPE,
     apexSysStatPowerSupplyModuleType          INTEGER,
     apexSysStatPowerSupplyModuleAvailable     ModuleAvailableTYPE,
     apexSysStatPowerSupplyModuleSerialNumber  DisplayString
    }

apexSysStatPowerSupplyModuleNum OBJECT-TYPE
    SYNTAX Integer32(1..2)
    MAX-ACCESS not-accessible
    STATUS current
    DESCRIPTION
        "Power Supply Module Number."
::= { apexSysStatPowerSupplyModuleEntry 1 }
                      
apexSysStatPowerSupplyModulePresent OBJECT-TYPE
    SYNTAX ModulePresentTYPE
    MAX-ACCESS read-only
    STATUS current
    DESCRIPTION
        "Indicates whether the module is Present or Missing."
::= { apexSysStatPowerSupplyModuleEntry 2 }

apexSysStatPowerSupplyModuleType OBJECT-TYPE
    SYNTAX INTEGER
        {
         unknown          (0),
         powerSupplyType1 (1)
        }
    MAX-ACCESS read-only
    STATUS current
    DESCRIPTION
        "Indicates type of module."
::= { apexSysStatPowerSupplyModuleEntry 3 }

apexSysStatPowerSupplyModuleAvailable OBJECT-TYPE
    SYNTAX ModuleAvailableTYPE
    MAX-ACCESS read-only
    STATUS current
    DESCRIPTION
        "Indicates whether the module is Available for use."
::= { apexSysStatPowerSupplyModuleEntry 4 }

apexSysStatPowerSupplyModuleSerialNumber OBJECT-TYPE
    SYNTAX DisplayString (SIZE (0..31))
    MAX-ACCESS read-only
    STATUS current
    DESCRIPTION
        "Serial Number."
::= { apexSysStatPowerSupplyModuleEntry 5 }


-- ------------------------------------------------------------------------------
--
-- apexSysStatPowerTransitionModule                   
--

apexSysStatPowerTransitionModulePresent OBJECT-TYPE
    SYNTAX ModulePresentTYPE
    MAX-ACCESS read-only
    STATUS current
    DESCRIPTION
        "Indicates whether the module is Present or Missing."
::= { apexSysStatPowerTransitionModule 1 }

apexSysStatPowerTransitionModuleType OBJECT-TYPE
    SYNTAX INTEGER
        {
         unknown              (0),
         powerTransitionType1 (1)
        }
    MAX-ACCESS read-only
    STATUS current
    DESCRIPTION
        "Indicates type of module."
::= { apexSysStatPowerTransitionModule 2 }

apexSysStatPowerTransitionModuleAvailable OBJECT-TYPE
    SYNTAX ModuleAvailableTYPE
    MAX-ACCESS read-only
    STATUS current
    DESCRIPTION
        "Indicates whether the module is Available for use."
::= { apexSysStatPowerTransitionModule 3 }

apexSysStatPowerTransitionModuleSerialNumber OBJECT-TYPE
    SYNTAX DisplayString (SIZE (0..31))
    MAX-ACCESS read-only
    STATUS current
    DESCRIPTION
        "Serial Number."
::= { apexSysStatPowerTransitionModule 4 }

apexSysStatPowerTransitionModuleHardwareVersion OBJECT-TYPE
    SYNTAX DisplayString (SIZE (0..31))
    MAX-ACCESS read-only
    STATUS current
    DESCRIPTION
        "Hardware Revision."
::= { apexSysStatPowerTransitionModule 5 }


-- ------------------------------------------------------------------------------
--
-- apexSysStatBladeSlotTable                   
--

apexSysStatBladeSlotTable OBJECT-TYPE
    SYNTAX SEQUENCE OF ApexSysStatBladeSlotEntry
    MAX-ACCESS not-accessible
    STATUS current
    DESCRIPTION
        "Table of Blade Slot Status."
::= { apexSysStatusModules 11 }

apexSysStatBladeSlotEntry OBJECT-TYPE
    SYNTAX ApexSysStatBladeSlotEntry
    MAX-ACCESS not-accessible
    STATUS current
    DESCRIPTION
        "Blade Slot Status Table Entry."
    INDEX { apexSysStatBladeSlotNum }
::= { apexSysStatBladeSlotTable 1 }

ApexSysStatBladeSlotEntry ::= SEQUENCE
    {
     apexSysStatBladeSlotNum         Integer32,
     apexSysStatBladeSlotModuleType  INTEGER
    }

apexSysStatBladeSlotNum OBJECT-TYPE
    SYNTAX Integer32(1..8)
    MAX-ACCESS not-accessible
    STATUS current
    DESCRIPTION
        "Blade Slot Number."
::= { apexSysStatBladeSlotEntry 1 }
                      
apexSysStatBladeSlotModuleType OBJECT-TYPE
    SYNTAX INTEGER
        {
         unknown   (0),
         qamBlade  (1),
         fanFiller (2)
        }
    MAX-ACCESS read-only
    STATUS current
    DESCRIPTION
        "Indicates type of module in the blade slot."
::= { apexSysStatBladeSlotEntry 3 }


-- ------------------------------------------------------------------------------
--
-- apexTime
--
-- apexTimeConfig
--
-- apexTimeConfigGeneral
--

apexTimeSource OBJECT-TYPE
    SYNTAX INTEGER
        {
         none     (0),
         sntp     (1),
         internal (2)
        }
    MAX-ACCESS read-write
    STATUS current
    DESCRIPTION
        "The source for system time.
         The time source can be configured to come from
         an SNTP time source, or be generated internally.

         When configured as internal:
            - The APEX will internally keep time starting at GPS time 0.
              A user can set the time to a valid GPS time in this mode.
            - The system time and UTC offset in internal mode are
              not updated and therefore are not valid.

         When configured to receive time via SNTP the
         SntpServerSpecified object and SntpServiceIP objects
         can be used to optionally define the SNTP server.

         Once written, the change to this parameter will take immediate effect.
         However, in order for the change to persist through subsequent reboots
         or power cycles, the change must be saved via the apexSaveConfig parameter.

         @Config(config=yes, reboot=no)
         @Save(apexSaveConfig, value=2)
         @File(config.ini, type='ini')
        "
::= { apexTimeConfigGeneral 1 }

apexSntpUtcOffset OBJECT-TYPE
    SYNTAX Integer32(0..1000)
    MAX-ACCESS read-write
    STATUS current
    DESCRIPTION
        "The value of this object is the Universal Time
         Coordinated (UTC) offset from GPS time.  Subtract
         this from GPS time to convert from GPS to UTC.
         Units are seconds.

         When time source is SNTP, this object can be set
         to specify the UTC offset that the APEX will use
         in calculating GPS time.

         Once written, the change to this parameter will take immediate effect.
         However, in order for the change to persist through subsequent reboots
         or power cycles, the change must be saved via the apexSaveConfig parameter.

         @Config(config=yes, reboot=no)
         @Save(apexSaveConfig, value=2)
         @File(config.ini, type='ini')
        "
::= { apexTimeConfigGeneral 2 }

apexSntpServerSpecified OBJECT-TYPE
    SYNTAX INTEGER
        {
         notSpecified  (1),
         specified     (2)
        }
    MAX-ACCESS read-write
    STATUS current
    DESCRIPTION
        "When the TimeSource is SNTP, this object specifies whether
         the APEX will only accept time for a single SNTP server or
         from any server that broadcasts time.
         When notSpecified, the APEX will accept time from any SNTP
         server.

         When specified, the APEX will poll for time from the address
         of the SNTP server specified by the SntpServerIP address object.

         Once written, the change to this parameter will take immediate effect.
         However, in order for the change to persist through subsequent reboots
         or power cycles, the change must be saved via the apexSaveConfig parameter.

         @Config(config=yes, reboot=no)
         @Save(apexSaveConfig, value=2)
         @File(config.ini, type='ini')
        "
::= { apexTimeConfigGeneral 3 }

apexSntpServerIpAddr OBJECT-TYPE
    SYNTAX IpAddress
    MAX-ACCESS read-write
    STATUS current
    DESCRIPTION
        "This contains the IP address of the specified SNTP server.
         If apexTimeSource is SNTP and apexSntpServerSpecified
         is set to specified, then the apex will poll for time from
         this IP address.

         Once written, the change to this parameter will take immediate effect.
         However, in order for the change to persist through subsequent reboots
         or power cycles, the change must be saved via the apexSaveConfig parameter.

         @Config(config=yes, reboot=no)
         @Save(apexSaveConfig, value=2)
         @File(config.ini, type='ini')
        "
::= { apexTimeConfigGeneral 4 }

apexUserSuppliedTime OBJECT-TYPE
    SYNTAX Unsigned32
    MAX-ACCESS read-write
    STATUS current
    DESCRIPTION
        "The value of this object is the GPS Time the APEX is given
         via user entry.  The time is reported in GPS seconds.
         This time is ONLY used when the APEX is set to Internal time mode.

         Once written, the change to this parameter will take immediate effect.

         @Config(config=no, reboot=no)
        "
::= { apexTimeConfigGeneral 5 }


-- ------------------------------------------------------------------------------
--
-- apexTimeStatus
--
-- apexTimeStatusGeneral
--

apexSystemTime OBJECT-TYPE
    SYNTAX Integer32
    MAX-ACCESS read-only
    STATUS current
    DESCRIPTION
        "The value of this object is the current System Time of the APEX.
         The system time is reported in GPS seconds.  To determine the
         APEXs system time in UTC the apexSntpUtcOffset object must also
         be read and used in the calculation."
::= { apexTimeStatusGeneral 1 }

apexOperationalTime OBJECT-TYPE
    SYNTAX Integer32
    MAX-ACCESS read-only
    STATUS current
    DESCRIPTION
        "The Operational Time is the time in seconds since the APEX completed
         the boot sequence.  It is the time that the APEX has been operational."
::= { apexTimeStatusGeneral 8 }


-- ------------------------------------------------------------------------------
--
-- apexTemperature
--
-- apexTemperatureConfig
--
-- apexTemperatureConfigGeneral
--

-- none


-- ------------------------------------------------------------------------------
--
-- apexTemperatureStatus
--
-- apexTemperatureStatusGeneral
--

-- none


-- ------------------------------------------------------------------------------
--
-- apexModuleTemperatures
--
-- apexTempsFrontPanel
--

apexTempsFrontPanelFaultCondition OBJECT-TYPE
    SYNTAX INTEGER
        {
         ok(1),
         indeterminate(2),
         warning(3),
         minor(4),
         major(5),
         critical(6)
        }
    MAX-ACCESS read-only
    STATUS current
    DESCRIPTION
        "Temperature alarm condition for the Front Panel module.
        
         Reflected in apexAlarmTemperatureFault.
        "
::= { apexTempsFrontPanel 1 }

apexTempsFrontPanelMicroCtrl OBJECT-TYPE
    SYNTAX Integer32
    MAX-ACCESS read-only
    STATUS current
    DESCRIPTION
        "Temperature for the sensor in degrees Celsius.
        "
::= { apexTempsFrontPanel 2 }


-- ------------------------------------------------------------------------------
--
-- apexTempsDti
--

apexTempsDtiFaultCondition OBJECT-TYPE
    SYNTAX INTEGER
        {
         ok(1),
         indeterminate(2),
         warning(3),
         minor(4),
         major(5),
         critical(6)
        }
    MAX-ACCESS read-only
    STATUS current
    DESCRIPTION
        "Temperature alarm condition for the DTI module.
        
         Reflected in apexAlarmTemperatureFault.
        "
::= { apexTempsDti 1 }

apexTempsDtiMicroCtrl OBJECT-TYPE
    SYNTAX Integer32
    MAX-ACCESS read-only
    STATUS current
    DESCRIPTION
        "Temperature for the sensor in degrees Celsius.
        "
::= { apexTempsDti 2 }


-- ------------------------------------------------------------------------------
--
-- apexTempsHost
--
-- apexTempsHostGeneral
--

-- none


-- ------------------------------------------------------------------------------
--
-- apexTempsHostTable
--

apexTempsHostTable OBJECT-TYPE
    SYNTAX SEQUENCE OF ApexTempsHostEntry
    MAX-ACCESS not-accessible
    STATUS current
    DESCRIPTION
        "Table of Host Module Temperature Status."
::= { apexTempsHost 2 }

apexTempsHostEntry OBJECT-TYPE
    SYNTAX ApexTempsHostEntry
    MAX-ACCESS not-accessible
    STATUS current
    DESCRIPTION
        "Host Module Temperature Status Table Entry."
    INDEX { apexTempsHostModuleNum }
::= { apexTempsHostTable 1 }

ApexTempsHostEntry ::= SEQUENCE
    {
     apexTempsHostModuleNum       Integer32,
     apexTempsHostFaultCondition  INTEGER,
     apexTempsHostMicroCtrl       Integer32,
     apexTempsHostSensor1         Integer32,
     apexTempsHostSensor2         Integer32,
     apexTempsHostSensor3         Integer32,
     apexTempsHostSensor4         Integer32,
     apexTempsHostSensor5         Integer32
    }

apexTempsHostModuleNum OBJECT-TYPE
    SYNTAX Integer32(1..2)
    MAX-ACCESS not-accessible
    STATUS current
    DESCRIPTION
        "Host Module Number."
::= { apexTempsHostEntry 1 }
                      
apexTempsHostFaultCondition OBJECT-TYPE
    SYNTAX INTEGER
        {
         ok(1),
         indeterminate(2),
         warning(3),
         minor(4),
         major(5),
         critical(6)
        }
    MAX-ACCESS read-only
    STATUS current
    DESCRIPTION
        "Temperature alarm condition for this Host module.
        
         Reflected in apexAlarmTemperatureFault.
        "
::= { apexTempsHostEntry 2 }

apexTempsHostMicroCtrl OBJECT-TYPE
    SYNTAX Integer32
    MAX-ACCESS read-only
    STATUS current
    DESCRIPTION
        "Temperature for the sensor in degrees Celsius.
        "
::= { apexTempsHostEntry 3 }

apexTempsHostSensor1 OBJECT-TYPE
    SYNTAX Integer32
    MAX-ACCESS read-only
    STATUS current
    DESCRIPTION
        "Temperature for the sensor in degrees Celsius.
        "
::= { apexTempsHostEntry 4 }

apexTempsHostSensor2 OBJECT-TYPE
    SYNTAX Integer32
    MAX-ACCESS read-only
    STATUS current
    DESCRIPTION
        "Temperature for the sensor in degrees Celsius.
        "
::= { apexTempsHostEntry 5 }

apexTempsHostSensor3 OBJECT-TYPE
    SYNTAX Integer32
    MAX-ACCESS read-only
    STATUS current
    DESCRIPTION
        "Temperature for the sensor in degrees Celsius.
        "
::= { apexTempsHostEntry 6 }

apexTempsHostSensor4 OBJECT-TYPE
    SYNTAX Integer32
    MAX-ACCESS read-only
    STATUS current
    DESCRIPTION
        "Temperature for the sensor in degrees Celsius.
        "
::= { apexTempsHostEntry 7 }

apexTempsHostSensor5 OBJECT-TYPE
    SYNTAX Integer32
    MAX-ACCESS read-only
    STATUS current
    DESCRIPTION
        "Temperature for the sensor in degrees Celsius.
        "
::= { apexTempsHostEntry 8 }


-- ------------------------------------------------------------------------------
--
-- apexTemps10Gbe
--
-- apexTemps10GbeGeneral
--

-- none


-- ------------------------------------------------------------------------------
--
-- apexTemps10GbeTable
--

apexTemps10GbeTable OBJECT-TYPE
    SYNTAX SEQUENCE OF ApexTemps10GbeEntry
    MAX-ACCESS not-accessible
    STATUS current
    DESCRIPTION
        "Table of 10Gbe Module Temperature Status."
::= { apexTemps10Gbe 2 }

apexTemps10GbeEntry OBJECT-TYPE
    SYNTAX ApexTemps10GbeEntry
    MAX-ACCESS not-accessible
    STATUS current
    DESCRIPTION
        "10Gbe Module Temperature Status Table Entry."
    INDEX { apexTemps10GbeModuleNum }
::= { apexTemps10GbeTable 1 }

ApexTemps10GbeEntry ::= SEQUENCE
    {
     apexTemps10GbeModuleNum       Integer32,
     apexTemps10GbeFaultCondition  INTEGER,
     apexTemps10GbeMicroCtrl       Integer32
    }

apexTemps10GbeModuleNum OBJECT-TYPE
    SYNTAX Integer32(1..3)
    MAX-ACCESS not-accessible
    STATUS current
    DESCRIPTION
        "10Gbe Module Number."
::= { apexTemps10GbeEntry 1 }
                      
apexTemps10GbeFaultCondition OBJECT-TYPE
    SYNTAX INTEGER
        {
         ok(1),
         indeterminate(2),
         warning(3),
         minor(4),
         major(5),
         critical(6)
        }
    MAX-ACCESS read-only
    STATUS current
    DESCRIPTION
        "Temperature alarm condition for this 10Gbe module.
        
         Reflected in apexAlarmTemperatureFault.
        "
::= { apexTemps10GbeEntry 2 }

apexTemps10GbeMicroCtrl OBJECT-TYPE
    SYNTAX Integer32
    MAX-ACCESS read-only
    STATUS current
    DESCRIPTION
        "Temperature for the sensor in degrees Celsius.
        "
::= { apexTemps10GbeEntry 3 }


-- ------------------------------------------------------------------------------
--
-- apexTempsQamBlade
--
-- apexTempsQamBladeGeneral
--

-- none


-- ------------------------------------------------------------------------------
--
-- apexTempsQamBladeTable
--

apexTempsQamBladeTable OBJECT-TYPE
    SYNTAX SEQUENCE OF ApexTempsQamBladeEntry
    MAX-ACCESS not-accessible
    STATUS current
    DESCRIPTION
        "Table of QAM Blade Temperature Status."
::= { apexTempsQamBlade 2 }

apexTempsQamBladeEntry OBJECT-TYPE
    SYNTAX ApexTempsQamBladeEntry
    MAX-ACCESS not-accessible
    STATUS current
    DESCRIPTION
        "QAM Blade Temperature Status Table Entry."
    INDEX { apexTempsQamBladeNum }
::= { apexTempsQamBladeTable 1 }

ApexTempsQamBladeEntry ::= SEQUENCE
    {
     apexTempsQamBladeNum             Integer32,
     apexTempsQamBladeFaultCondition  INTEGER,
     apexTempsQamBladeMicroCtrl       Integer32,
     apexTempsQamBladeSensor1         Integer32,
     apexTempsQamBladeSensor2         Integer32,
     apexTempsQamBladeSensor3         Integer32,
     apexTempsQamBladeSensor4         Integer32,
     apexTempsQamBladeSensor5         Integer32,
     apexTempsQamBladeSensor6         Integer32
    }

apexTempsQamBladeNum OBJECT-TYPE
    SYNTAX Integer32(1..8)
    MAX-ACCESS not-accessible
    STATUS current
    DESCRIPTION
        "QAM Blade Number."
::= { apexTempsQamBladeEntry 1 }
                      
apexTempsQamBladeFaultCondition OBJECT-TYPE
    SYNTAX INTEGER
        {
         ok(1),
         indeterminate(2),
         warning(3),
         minor(4),
         major(5),
         critical(6)
        }
    MAX-ACCESS read-only
    STATUS current
    DESCRIPTION
        "Temperature alarm condition for this QAM Blade.
        
         Reflected in apexAlarmTemperatureFault.
        "
::= { apexTempsQamBladeEntry 2 }

apexTempsQamBladeMicroCtrl OBJECT-TYPE
    SYNTAX Integer32
    MAX-ACCESS read-only
    STATUS current
    DESCRIPTION
        "Temperature for the sensor in degrees Celsius.
        "
::= { apexTempsQamBladeEntry 3 }

apexTempsQamBladeSensor1 OBJECT-TYPE
    SYNTAX Integer32
    MAX-ACCESS read-only
    STATUS current
    DESCRIPTION
        "Temperature for the sensor in degrees Celsius.
        "
::= { apexTempsQamBladeEntry 4 }

apexTempsQamBladeSensor2 OBJECT-TYPE
    SYNTAX Integer32
    MAX-ACCESS read-only
    STATUS current
    DESCRIPTION
        "Temperature for the sensor in degrees Celsius.
        "
::= { apexTempsQamBladeEntry 5 }

apexTempsQamBladeSensor3 OBJECT-TYPE
    SYNTAX Integer32
    MAX-ACCESS read-only
    STATUS current
    DESCRIPTION
        "Temperature for the sensor in degrees Celsius.
        "
::= { apexTempsQamBladeEntry 6 }

apexTempsQamBladeSensor4 OBJECT-TYPE
    SYNTAX Integer32
    MAX-ACCESS read-only
    STATUS current
    DESCRIPTION
        "Temperature for the sensor in degrees Celsius.
        "
::= { apexTempsQamBladeEntry 7 }

apexTempsQamBladeSensor5 OBJECT-TYPE
    SYNTAX Integer32
    MAX-ACCESS read-only
    STATUS current
    DESCRIPTION
        "Temperature for the sensor in degrees Celsius.
        "
::= { apexTempsQamBladeEntry 8 }

apexTempsQamBladeSensor6 OBJECT-TYPE
    SYNTAX Integer32
    MAX-ACCESS read-only
    STATUS current
    DESCRIPTION
        "Temperature for the sensor in degrees Celsius.
        "
::= { apexTempsQamBladeEntry 9 }


-- ------------------------------------------------------------------------------
--
-- apexTempsRfModule
--
-- apexTempsRfModuleGeneral
--

-- none


-- ------------------------------------------------------------------------------
--
-- apexTempsRfModuleTable
--

apexTempsRfModuleTable OBJECT-TYPE
    SYNTAX SEQUENCE OF ApexTempsRfModuleEntry
    MAX-ACCESS not-accessible
    STATUS current
    DESCRIPTION
        "Table of RF Module Temperature Status."
::= { apexTempsRfModule 2 }

apexTempsRfModuleEntry OBJECT-TYPE
    SYNTAX ApexTempsRfModuleEntry
    MAX-ACCESS not-accessible
    STATUS current
    DESCRIPTION
        "RF Module Temperature Status Table Entry."
    INDEX { apexTempsRfModuleNum }
::= { apexTempsRfModuleTable 1 }

ApexTempsRfModuleEntry ::= SEQUENCE
    {
     apexTempsRfModuleNum             Integer32,
     apexTempsRfModuleFpga            Integer32,
     apexTempsRfModuleRfHigh          Integer32
    }

apexTempsRfModuleNum OBJECT-TYPE
    SYNTAX Integer32(1..8)
    MAX-ACCESS not-accessible
    STATUS current
    DESCRIPTION
        "QAM Blade Number."
::= { apexTempsRfModuleEntry 1 }

apexTempsRfModuleFpga OBJECT-TYPE
    SYNTAX Integer32
    MAX-ACCESS read-only
    STATUS current
    DESCRIPTION
        "Temperature for the sensor in degrees Celsius.
        "
::= { apexTempsRfModuleEntry 2 }

apexTempsRfModuleRfHigh OBJECT-TYPE
    SYNTAX Integer32
    MAX-ACCESS read-only
    STATUS current
    DESCRIPTION
        "Highest RF temperature on the module in degrees Celsius.
        "
::= { apexTempsRfModuleEntry 3 }


-- ------------------------------------------------------------------------------
--
-- apexTempsRfSwitch
--
-- apexTempsRfSwitchGeneral
--

-- none


-- ------------------------------------------------------------------------------
--
-- apexTempsRfSwitchTable
--

apexTempsRfSwitchTable OBJECT-TYPE
    SYNTAX SEQUENCE OF ApexTempsRfSwitchEntry
    MAX-ACCESS not-accessible
    STATUS current
    DESCRIPTION
        "Table of RF Switch Module Temperature Status."
::= { apexTempsRfSwitch 2 }

apexTempsRfSwitchEntry OBJECT-TYPE
    SYNTAX ApexTempsRfSwitchEntry
    MAX-ACCESS not-accessible
    STATUS current
    DESCRIPTION
        "RF Switch Module Temperature Status Table Entry."
    INDEX { apexTempsRfSwitchModuleNum }
::= { apexTempsRfSwitchTable 1 }

ApexTempsRfSwitchEntry ::= SEQUENCE
    {
     apexTempsRfSwitchModuleNum       Integer32,
     apexTempsRfSwitchFaultCondition  INTEGER,
     apexTempsRfSwitchMicroCtrl       Integer32,
     apexTempsRfSwitchSensor1         Integer32
    }

apexTempsRfSwitchModuleNum OBJECT-TYPE
    SYNTAX Integer32(1..4)
    MAX-ACCESS not-accessible
    STATUS current
    DESCRIPTION
        "RF Switch Module Number."
::= { apexTempsRfSwitchEntry 1 }
                      
apexTempsRfSwitchFaultCondition OBJECT-TYPE
    SYNTAX INTEGER
        {
         ok(1),
         indeterminate(2),
         warning(3),
         minor(4),
         major(5),
         critical(6)
        }
    MAX-ACCESS read-only
    STATUS current
    DESCRIPTION
        "Temperature alarm condition for this RF Switch Module.
        
         Reflected in apexAlarmTemperatureFault.
        "
::= { apexTempsRfSwitchEntry 2 }

apexTempsRfSwitchMicroCtrl OBJECT-TYPE
    SYNTAX Integer32
    MAX-ACCESS read-only
    STATUS current
    DESCRIPTION
        "Temperature for the sensor in degrees Celsius.
        "
::= { apexTempsRfSwitchEntry 3 }

apexTempsRfSwitchSensor1 OBJECT-TYPE
    SYNTAX Integer32
    MAX-ACCESS read-only
    STATUS current
    DESCRIPTION
        "Temperature for the sensor in degrees Celsius.
        "
::= { apexTempsRfSwitchEntry 4 }


-- ------------------------------------------------------------------------------
--
-- apexTempsFanFiller
--
-- apexTempsFanFillerGeneral
--

-- none


-- ------------------------------------------------------------------------------
--
-- apexTempsFanFillerTable
--

apexTempsFanFillerTable OBJECT-TYPE
    SYNTAX SEQUENCE OF ApexTempsFanFillerEntry
    MAX-ACCESS not-accessible
    STATUS current
    DESCRIPTION
        "Table of QAM Blade Slot Fan Filler Temperature Status."
::= { apexTempsFanFiller 2 }

apexTempsFanFillerEntry OBJECT-TYPE
    SYNTAX ApexTempsFanFillerEntry
    MAX-ACCESS not-accessible
    STATUS current
    DESCRIPTION
        "QAM Blade Slot Fan Filler Module Temperature Status Table Entry."
    INDEX { apexTempsFanFillerModuleNum }
::= { apexTempsFanFillerTable 1 }

ApexTempsFanFillerEntry ::= SEQUENCE
    {
     apexTempsFanFillerModuleNum       Integer32,
     apexTempsFanFillerFaultCondition  INTEGER,
     apexTempsFanFillerMicroCtrl       Integer32,
     apexTempsFanFillerSensor1         Integer32,
     apexTempsFanFillerSensor2         Integer32,
     apexTempsFanFillerSensor3         Integer32
    }

apexTempsFanFillerModuleNum OBJECT-TYPE
    SYNTAX Integer32(1..8)
    MAX-ACCESS not-accessible
    STATUS current
    DESCRIPTION
        "QAM Blade Number."
::= { apexTempsFanFillerEntry 1 }
                      
apexTempsFanFillerFaultCondition OBJECT-TYPE
    SYNTAX INTEGER
        {
         ok(1),
         indeterminate(2),
         warning(3),
         minor(4),
         major(5),
         critical(6)
        }
    MAX-ACCESS read-only
    STATUS current
    DESCRIPTION
        "Temperature alarm condition for this QAM Blade Slot Fan Filler Module.
        
         Reflected in apexAlarmTemperatureFault.
        "
::= { apexTempsFanFillerEntry 2 }

apexTempsFanFillerMicroCtrl OBJECT-TYPE
    SYNTAX Integer32
    MAX-ACCESS read-only
    STATUS current
    DESCRIPTION
        "Temperature for the sensor in degrees Celsius.
        "
::= { apexTempsFanFillerEntry 3 }

apexTempsFanFillerSensor1 OBJECT-TYPE
    SYNTAX Integer32
    MAX-ACCESS read-only
    STATUS current
    DESCRIPTION
        "Temperature for the sensor in degrees Celsius.
        "
::= { apexTempsFanFillerEntry 4 }

apexTempsFanFillerSensor2 OBJECT-TYPE
    SYNTAX Integer32
    MAX-ACCESS read-only
    STATUS current
    DESCRIPTION
        "Temperature for the sensor in degrees Celsius.
        "
::= { apexTempsFanFillerEntry 5 }

apexTempsFanFillerSensor3 OBJECT-TYPE
    SYNTAX Integer32
    MAX-ACCESS read-only
    STATUS current
    DESCRIPTION
        "Temperature for the sensor in degrees Celsius.
        "
::= { apexTempsFanFillerEntry 6 }


-- ------------------------------------------------------------------------------
--
-- apexPowerSupply
--
-- apexPsConfig
--
-- apexPsConfigGeneral
--

-- none


-- ------------------------------------------------------------------------------
--
-- apexPsStatus
--
-- apexPsStatusGeneral
--

-- none


-- ------------------------------------------------------------------------------
--
-- apexPsStatusTable
--

apexPsStatusTable OBJECT-TYPE
    SYNTAX SEQUENCE OF ApexPsStatusEntry
    MAX-ACCESS not-accessible
    STATUS current
    DESCRIPTION
        "This is a table of status parameters for the two Power Supplies."
::= { apexPsStatus 2 }

apexPsStatusEntry OBJECT-TYPE
    SYNTAX ApexPsStatusEntry
    MAX-ACCESS not-accessible
    STATUS current
    DESCRIPTION
        "Power Supply Status Table Entry."
    INDEX { apexPsStatusPsNum }
::= { apexPsStatusTable 1 }

ApexPsStatusEntry ::= SEQUENCE
    {
     apexPsStatusPsNum             Integer32,
     apexPsStatusInstalled         INTEGER,
     apexPsStatusFirmwareVersion   DisplayString,
     apexPsStatusVoltageOut        Integer32,
     apexPsStatusCurrentOut        Integer32,
     apexPsStatusVoltageInput      Integer32,
     apexPsStatusCurrentInput      Integer32,
     apexPsStatusPowerInput        Integer32,
     apexPsStatusTemperature       Integer32,
     apexPsStatusFanSpeed          Integer32,
     apexPsStatusFan1Speed         Integer32,
     apexPsStatusFan2Speed         Integer32,
     apexPsStatusCurrentOutControl Integer32,
     apexPsStatusVoltOutControl    Integer32,
     apexPsStatusFanControl        Integer32,
     apexPsStatusFaultCondition    INTEGER,
     apexPsStatusCurrentOutFault   INTEGER,
     apexPsStatusVoltOutFault      INTEGER,
     apexPsStatusVoltInputFault    INTEGER,
     apexPsStatusTempFault         INTEGER,
     apexPsStatusFanFault          INTEGER,
     apexPsStatusMfrSpecFault      INTEGER
    }

apexPsStatusPsNum OBJECT-TYPE
    SYNTAX Integer32(1..2)
    MAX-ACCESS not-accessible
    STATUS current
    DESCRIPTION
        "PS Number."
::= { apexPsStatusEntry 1 }

apexPsStatusInstalled OBJECT-TYPE
    SYNTAX INTEGER
        {
         notApplicable      (0),
         notInstalled       (1),
         installedAcInput   (2),
         installedDcInput   (3),
         fanModuleInstalled (4),
         unsupported        (5)
        }
    MAX-ACCESS read-only
    STATUS current
    DESCRIPTION
        "This parameter indicates installed status of the PS."
::= { apexPsStatusEntry 2 }

apexPsStatusFirmwareVersion OBJECT-TYPE
    SYNTAX DisplayString (SIZE (0..31))
    MAX-ACCESS read-only
    STATUS current
    DESCRIPTION
        "Major and Minor Firmware Version of the power supply firmware."
::= { apexPsStatusEntry 3 }

apexPsStatusVoltageOut OBJECT-TYPE
    SYNTAX Integer32
    MAX-ACCESS read-only
    STATUS current
    DESCRIPTION
        "Measured output voltage of the main output of the power supply.
         The output voltage is reported in 1/512 V."
::= { apexPsStatusEntry 4 }

apexPsStatusCurrentOut OBJECT-TYPE
    SYNTAX Integer32
    MAX-ACCESS read-only
    STATUS current
    DESCRIPTION
        "Measured output current of the main output of the power supply.
         The output current is reported in 1/100 A."
::= { apexPsStatusEntry 5 }

apexPsStatusVoltageInput OBJECT-TYPE
    SYNTAX Integer32
    MAX-ACCESS read-only
    STATUS current
    DESCRIPTION
        "Input voltage to the power supply. The input voltage is reported in 1/100 V RMS."
::= { apexPsStatusEntry 6 }

apexPsStatusCurrentInput OBJECT-TYPE
    SYNTAX Integer32
    MAX-ACCESS read-only
    STATUS current
    DESCRIPTION
        "Input current to the power supply. The input current is reported in 1/100 A RMS."
::= { apexPsStatusEntry 7 }

apexPsStatusPowerInput OBJECT-TYPE
    SYNTAX Integer32
    MAX-ACCESS read-only
    STATUS current
    DESCRIPTION
        "Input power to the power supply. The input power is reported in watts (W)."
::= { apexPsStatusEntry 8 }

apexPsStatusTemperature OBJECT-TYPE
    SYNTAX Integer32
    MAX-ACCESS read-only
    STATUS current
    DESCRIPTION
        "Internal hotspot temperature of the power supply.
         The temperature sensor data is reported in degrees C."
::= { apexPsStatusEntry 9 }

apexPsStatusFanSpeed OBJECT-TYPE
    SYNTAX Integer32
    MAX-ACCESS read-only
    STATUS current
    DESCRIPTION
        "Current fan speed of the power supply in %.  100 means full speed."
::= { apexPsStatusEntry 10 }

apexPsStatusFan1Speed OBJECT-TYPE
    SYNTAX Integer32
    MAX-ACCESS read-only
    STATUS current
    DESCRIPTION
        "Measured Fan1 speed of the power supply.
         F1 speed is reported in RPM."
::= { apexPsStatusEntry 11 }

apexPsStatusFan2Speed OBJECT-TYPE
    SYNTAX Integer32
    MAX-ACCESS read-only
    STATUS current
    DESCRIPTION
        "Measured Fan2 speed of the power supply.
         F2 speed is reported in RPM."
::= { apexPsStatusEntry 12 }

apexPsStatusCurrentOutControl OBJECT-TYPE
    SYNTAX Integer32
    MAX-ACCESS read-only
    STATUS current
    DESCRIPTION
        "Current limit setting of the power supply output. Reported in 1/100 A."
::= { apexPsStatusEntry 13 }

apexPsStatusVoltOutControl OBJECT-TYPE
    SYNTAX Integer32
    MAX-ACCESS read-only
    STATUS current
    DESCRIPTION
        "Voltage setting of the power supply output. Reported in 1/512 V."
::= { apexPsStatusEntry 14 }

apexPsStatusFanControl OBJECT-TYPE
    SYNTAX Integer32
    MAX-ACCESS read-only
    STATUS current
    DESCRIPTION
        "Fan speed setting of the power supply in %. 100 means full speed."
::= { apexPsStatusEntry 15 }

apexPsStatusFaultCondition OBJECT-TYPE
    SYNTAX INTEGER
        {
         ok(1),
         commFault(2),
         tempFault(3),
         inputUnderVoltFault(4),
         outputOverCurrentFault(5),
         outputOverVoltFault(6),
         psOff(7),
         busy(8),
         unknownError(9),
         otherFault(10),
         fanFault(11),
         notApplicable(12),
         mfrFault(13),
         inputFault(14),
         outputCurrentFault(15),
         outputVoltFault(16),
         noneofbelow(17)
        }
    MAX-ACCESS read-only
    STATUS current
    DESCRIPTION
        "Summary of the power supply's fault condition."
::= { apexPsStatusEntry 16 }

apexPsStatusCurrentOutFault OBJECT-TYPE
    SYNTAX INTEGER
        {
         ok(1),
         overCurrentWarning(2),
         overCurrentFault(3)
        }
    MAX-ACCESS read-only
    STATUS current
    DESCRIPTION
        "Condition of the power supply output current."
::= { apexPsStatusEntry 17 }

apexPsStatusVoltOutFault OBJECT-TYPE
    SYNTAX INTEGER
        {
         ok(1),
         underVoltFault(2),
         underVoltWarning(3),
         overVoltWarning(4),
         overVoltFault(5)
        }
    MAX-ACCESS read-only
    STATUS current
    DESCRIPTION
        "Condition of the power supply output voltage."
::= { apexPsStatusEntry 18 }

apexPsStatusVoltInputFault OBJECT-TYPE
    SYNTAX INTEGER
        {
         ok(1),
         underVoltFault(2),
         underVoltWarning(3),
         overVoltWarning(4),
         overVoltFault(5)
        }
    MAX-ACCESS read-only
    STATUS current
    DESCRIPTION
        "Condition of the power supply input voltage."
::= { apexPsStatusEntry 19 }

apexPsStatusTempFault OBJECT-TYPE
    SYNTAX INTEGER
        {
         ok(1),
         underTempFault(2),
         underTempWarning(3),
         overTempWarning(4),
         overTempFault(5)
        }
    MAX-ACCESS read-only
    STATUS current
    DESCRIPTION
        "Thermal condition of the power supply."
::= { apexPsStatusEntry 20 }

apexPsStatusFanFault OBJECT-TYPE
    SYNTAX INTEGER
        {
         ok(1),
         fan2SpeedOverridden(2),
         fan1SpeedOverridden(3),
         fan2Fault(4),
         fan1Fault(5)
        }
    MAX-ACCESS read-only
    STATUS current
    DESCRIPTION
        "Condition of the fans inside the power supply."
::= { apexPsStatusEntry 21 }

apexPsStatusMfrSpecFault OBJECT-TYPE
    SYNTAX INTEGER
        {
         ok(1),
         acNotOk(2),
         dcNotOk(3),
         overTemp(4),
         fault(5),
         interrupt(6),
         ovsd(7),
         dcOffLimit(8)
        }
    MAX-ACCESS read-only
    STATUS current
    DESCRIPTION
        "Manufacturer specific fault/warning conditions for the power supply."
::= { apexPsStatusEntry 22 }


-- ------------------------------------------------------------------------------
--
-- apexAsiMonitorPortConfigTable
--

apexAsiMonitorPortConfigTable OBJECT-TYPE
    SYNTAX SEQUENCE OF ApexAsiMonitorPortConfigEntry
    MAX-ACCESS not-accessible
    STATUS current
    DESCRIPTION
        "Table of Configuration parameters for ASI Monitor Ports.

         Once written, the change to this parameter will take immediate effect.
         In order for the change to persist through subsequent reboots or power
         cycles, the change must be saved via the apexSaveConfig parameter.

         @Config(config=yes, reboot=no)
         @Save(apexSaveConfig, value=2)
         @File(config.ini, type='ini')
        "
::= { apexAsiConfig 2 }

apexAsiMonitorPortConfigEntry OBJECT-TYPE
    SYNTAX ApexAsiMonitorPortConfigEntry
    MAX-ACCESS not-accessible
    STATUS current
    DESCRIPTION
        "ASI Monitor Ports Configuration Table Entry."
    INDEX { apexAsiMonitorPortBladeNum }
::= { apexAsiMonitorPortConfigTable 1 }

ApexAsiMonitorPortConfigEntry ::= SEQUENCE
    {
     apexAsiMonitorPortBladeNum         Integer32,
     apexAsiMonitorPortOutputTsNum      Integer32,
     apexAsiMonitorPortEncryption       INTEGER
    }

apexAsiMonitorPortBladeNum OBJECT-TYPE
    SYNTAX Integer32(1..8)
    MAX-ACCESS not-accessible
    STATUS current
    DESCRIPTION
        "Blade Number."
::= { apexAsiMonitorPortConfigEntry 1 }

apexAsiMonitorPortOutputTsNum OBJECT-TYPE
    SYNTAX Integer32(0..256)
    MAX-ACCESS read-write
    STATUS current
    DESCRIPTION
        "The number of the output transport stream to route to the
         ASI Monitor Port.  Zero indicates that no stream is to be
         routed to the ASI Monitor port.
        "
::= { apexAsiMonitorPortConfigEntry 2 }

apexAsiMonitorPortEncryption OBJECT-TYPE
    SYNTAX INTEGER
        {
         notApplicable  (0),
         preEncryption  (1),
         postEncryption (2)
        }
    MAX-ACCESS read-write
    STATUS current
    DESCRIPTION
        "Selects pre or post encryption for the ASI monitor port. When 
         set to pre-encryption, the output of the ASI monitor will contain
         the data prior to the APEX encrypting the services. When set to
         post-encryption, the output of the ASI monitor will contain the
         data after the APEX has encrypted the services. 
         
         This setting only applies to the scrambled control bits and actual
         packet data of the MPEG packets. All ECMs and PSI messages are always
         output via the ASI monitor port.
        "
::= { apexAsiMonitorPortConfigEntry 3 }


-- ------------------------------------------------------------------------------
--
-- apexFastEnet
--
-- apexFastEnetConfig
--
-- apexFastEnetConfigGeneral
--

apexFastEnetDefaultGateway OBJECT-TYPE
    SYNTAX IpAddress
    MAX-ACCESS read-write
    STATUS current
    DESCRIPTION
        "This is the IP address of the default gateway for the Fast Ethernet
         interfaces.

         This should be zero or a valid Class A, B, or C IP address.

         Once written, the change to this parameter will only take effect 
         after apexFastEnetIpConfigApplyChange is set to 'apply'. In order
         for the change to persist through subsequent reboots or power
         cycles, the change must be saved via the apexSaveConfig parameter.

         @Commit(param=apexFastEnetIpConfigApplyChange, value=2)
         @Config(config=yes, reboot=no)
         @Save(apexSaveConfig, value=2)
         @File(ipconfig.ini, type='ini')
        "
::= { apexFastEnetConfigGeneral 1 }

apexFastEnetRoutingApplyChange OBJECT-TYPE
    SYNTAX ApplyDataToDeviceTYPE
    MAX-ACCESS read-write
    STATUS current
    DESCRIPTION
        "The Apply for the Fast Ethernet Static Routing Table.

         This parameter MUST be set to 'apply' in order for any of the data
         in the apexFastEnetRoutingTable to take effect.  This parameter
         MUST be set LAST after all other data in the apexFastEnetRoutingTable 
         has been configured.

         Once written, the change to this parameter will take immediate effect.

         @Config(config=no, reboot=no)
        "
::= { apexFastEnetConfigGeneral 2 }

apexFastEnetIpConfigApplyChange OBJECT-TYPE
    SYNTAX ApplyDataToDeviceTYPE
    MAX-ACCESS read-write
    STATUS current
    DESCRIPTION
        "The Apply for the OAMP (ENET1) and Data (ENET2) configuration 
         including the Fast Ethernet default gateway.

         This parameter MUST be set to 'apply' in order for any of the data
         in apexOampConfigGeneral or apexDataIpConfigGeneral or 
         apexFastEnetDefaultGateway to take effect. This parameter MUST be
         set LAST after all other data in the apexOampConfigGeneral, 
         apexDataIpConfigGeneral and apexFastEnetDefaultGateway has been 
         configured.

         Once written, the change to this parameter will take immediate effect.

         @Config(config=no, reboot=no)
        "
::= { apexFastEnetConfigGeneral 3 }

apexGenericQamDeviceApplyChange OBJECT-TYPE
    SYNTAX ApplyDataToDeviceTYPE
    MAX-ACCESS read-write
    STATUS current
    DESCRIPTION
        "The Apply for the Generic QAM Device configuration.

         This parameter MUST be set to 'apply' in order for any of the data
         in apexGenericQamDeviceTable to take effect. This parameter MUST be
         set LAST after all other data in the apexGenericQamDeviceTable, 
         has been configured.

         Once written, the change to this parameter will take immediate effect.

         @Config(config=no, reboot=no)
        "
::= { apexFastEnetConfigGeneral 4 }


-- ------------------------------------------------------------------------------
--
-- apexFastEnetRoutingTable
--

apexFastEnetRoutingTable OBJECT-TYPE
    SYNTAX SEQUENCE OF ApexFastEnetRoutingEntry
    MAX-ACCESS not-accessible
    STATUS current
    DESCRIPTION
        "This table is the configuration Static Routing table for the
         Fast Ethernet Interface.

         @Commit(param=apexFastEnetRoutingApplyChange, value=2)
         @Config(config=yes, reboot=no)
         @Save(apexSaveConfig, value=2)
         @File(config.ini, type='ini')
        "
::= { apexFastEnetConfig 2 }

apexFastEnetRoutingEntry OBJECT-TYPE
    SYNTAX ApexFastEnetRoutingEntry
    MAX-ACCESS not-accessible
    STATUS current
    DESCRIPTION
        "Fast Ethernet Interface Configuration Static Routing Table Entry."
    INDEX { apexFastEnetRoutingIndex }
::= { apexFastEnetRoutingTable 1 }

ApexFastEnetRoutingEntry ::= SEQUENCE
    {
     apexFastEnetRoutingIndex           Integer32,
     apexFastEnetRoutingDestinIp        IpAddress,
     apexFastEnetRoutingGatewayIp       IpAddress,
     apexFastEnetRoutingSubnetMask      IpAddress
    }

apexFastEnetRoutingIndex OBJECT-TYPE
    SYNTAX Integer32(1..16)
    MAX-ACCESS not-accessible
    STATUS current
    DESCRIPTION
        "The index of the Routing table entry.
         Currently limited to 16."
::= { apexFastEnetRoutingEntry 1 }

apexFastEnetRoutingDestinIp OBJECT-TYPE
    SYNTAX IpAddress
    MAX-ACCESS read-write
    STATUS current
    DESCRIPTION
        "The Fast Ethernet Routing Destination IP address.

         Once written, the change to this parameter will only take immediate
         effect after apexFastEnetRoutingApplyChange is set to 'apply'.  
         In order for the change to persist through subsequent reboots or power cycles, 
         the change must be saved via the apexSaveConfig parameter.
        "
::= { apexFastEnetRoutingEntry 2 }

apexFastEnetRoutingGatewayIp OBJECT-TYPE
    SYNTAX IpAddress
    MAX-ACCESS read-write
    STATUS current
    DESCRIPTION
        "The Fast Ethernet Routing Gateway IP address.

         Once written, the change to this parameter will only take immediate
         effect after apexFastEnetRoutingApplyChange is set to 'apply'.
         In order for the change to persist through subsequent reboots or power cycles, 
         the change must be saved via the apexSaveConfig parameter.
        "
::= { apexFastEnetRoutingEntry 3 }

apexFastEnetRoutingSubnetMask OBJECT-TYPE
    SYNTAX IpAddress
    MAX-ACCESS read-write
    STATUS current
    DESCRIPTION
        "The Fast Ethernet Routing Subnet Mask.

         Once written, the change to this parameter will only take immediate
         effect after apexFastEnetRoutingApplyChange is set to 'apply'.
         In order for the change to persist through subsequent reboots or power cycles, 
         the change must be saved via the apexSaveConfig parameter.
        "
::= { apexFastEnetRoutingEntry 4 }


-- ------------------------------------------------------------------------------
--
-- apexGenericQamDeviceTable
--

apexGenericQamDeviceTable OBJECT-TYPE
    SYNTAX SEQUENCE OF ApexGenericQamDeviceEntry
    MAX-ACCESS not-accessible
    STATUS current
    DESCRIPTION
        "This table contains the configuration of Generic QAM Devices.
        
         Each row contains the configuration of a Generic QAM Device (GQD). Each 
         GQD has a unique IP address bound to ENET1 or ENET2. These GQDs can be
         considered virtual sub-devices of the APEX3000. They are used to communicate
         with old devices or protocols (such as RPC) that cannot cope with the large
         number of QAMs supported by the APEX3000.
         
         Any changes to the data within this table will only take effect after
         effect after apexGenericQamDeviceApplyChange is set to 'apply'.
         In order for the change to persist through subsequent reboots or power cycles, 
         the change must be saved via the apexSaveConfig parameter.           

         @Commit(param=apexGenericQamDeviceApplyChange, value=2)
         @Config(config=yes, reboot=no)
         @Save(apexSaveConfig, value=2)
         @File(ipconfig.ini, type='ini')
        "
::= { apexFastEnetConfig 3 }

apexGenericQamDeviceEntry OBJECT-TYPE
    SYNTAX ApexGenericQamDeviceEntry
    MAX-ACCESS not-accessible
    STATUS current
    DESCRIPTION
        "Generic QAM Device Table Entry."
    INDEX { apexGenericQamDeviceIndex }
::= { apexGenericQamDeviceTable 1 }

ApexGenericQamDeviceEntry ::= SEQUENCE
    {
     apexGenericQamDeviceIndex           Integer32,
     apexGenericQamDeviceEnetInterface   Integer32,
     apexGenericQamDeviceIpAddr          IpAddress,
     apexGenericQamDeviceSubnetMask      IpAddress
    }

apexGenericQamDeviceIndex OBJECT-TYPE
    SYNTAX Integer32(1..64)
    MAX-ACCESS not-accessible
    STATUS current
    DESCRIPTION
        "The index of the Generic QAM Device table entry.
         Currently limited to 64."
::= { apexGenericQamDeviceEntry 1 }

apexGenericQamDeviceEnetInterface OBJECT-TYPE
    SYNTAX Integer32(0..2)
    MAX-ACCESS read-write
    STATUS current
    DESCRIPTION
        "Specifies which Ethernet interface the generic QAM device uses.

         0 Indicates the Generic QAM Device is not in use (disabled).
         1 = ENET1, 2 = ENET2 etc.
        "
::= { apexGenericQamDeviceEntry 2 }

apexGenericQamDeviceIpAddr OBJECT-TYPE
    SYNTAX IpAddress
    MAX-ACCESS read-write
    STATUS current
    DESCRIPTION
        "The IP address for the generic QAM device.

         The IP address will be added to the ethernet interface specified 
         by apexGenericQamDeviceEnetInterface.
        "
::= { apexGenericQamDeviceEntry 3 }

apexGenericQamDeviceSubnetMask OBJECT-TYPE
    SYNTAX IpAddress
    MAX-ACCESS read-write
    STATUS current
    DESCRIPTION
        "The subnet mask for the generic QAM device."
::= { apexGenericQamDeviceEntry 4 }


-- ------------------------------------------------------------------------------
--
-- apexFastEnetStatus
--
-- apexFastEnetStatusGeneral
--      
apexFastEnetIpConfigApplyText OBJECT-TYPE
    SYNTAX DisplayString (SIZE (0..80))
    MAX-ACCESS read-only
    STATUS current
    DESCRIPTION
        "When apexFastEnetIpConfigApplyChange is set to applyNotInProgressInvalidData,
         this entry may contain a text description of what was wrong with the data.
         This entry contains the description for the most recent apply of a related
         entry that was invalid. 
        "
::= { apexFastEnetStatusGeneral 1 }

        
-- ------------------------------------------------------------------------------
--
-- apexFastEnetStatus
--
-- apexFastEnetStatusGeneral
--      
apexGenericQamDeviceApplyText OBJECT-TYPE
    SYNTAX DisplayString (SIZE (0..80))
    MAX-ACCESS read-only
    STATUS current
    DESCRIPTION
        "When apexGenericQamDeviceApplyChange is set to applyNotInProgressInvalidData,
         this entry may contain a text description of what was wrong with the data.
         This entry contains the description for the most recent apply of a related
         entry that was invalid. 
        "
::= { apexFastEnetStatusGeneral 2 }


-- ------------------------------------------------------------------------------
--
-- apexGqdStatTable
--

apexGqdStatTable OBJECT-TYPE
    SYNTAX SEQUENCE OF ApexGqdStatEntry
    MAX-ACCESS not-accessible
    STATUS current
    DESCRIPTION
        "Table of Generic QAM Device statistics."
::= { apexFastEnetStatus 2 }

apexGqdStatEntry OBJECT-TYPE
    SYNTAX ApexGqdStatEntry
    MAX-ACCESS not-accessible
    STATUS current
    DESCRIPTION
        "Table entry for Generic QAM Device statistics."
    INDEX { apexGqdStatDeviceIndex }
::= { apexGqdStatTable 1 }

ApexGqdStatEntry ::= SEQUENCE
    {
     apexGqdStatDeviceIndex      Integer32,
     apexGqdStatNumSdvSessions   Integer32,
     apexGqdStatNumOutputTs      Integer32
    }
    
apexGqdStatDeviceIndex OBJECT-TYPE
    SYNTAX Integer32(1..64)
    MAX-ACCESS not-accessible
    STATUS current
    DESCRIPTION
        "The index of the Generic QAM Device table entry."
::= { apexGqdStatEntry 1 }
                      
apexGqdStatNumSdvSessions OBJECT-TYPE
    SYNTAX Integer32
    MAX-ACCESS read-only
    STATUS current
    DESCRIPTION
        "The Number of SDV sessions using the generic QAM device."
::= { apexGqdStatEntry 2 }

apexGqdStatNumOutputTs OBJECT-TYPE
    SYNTAX Integer32
    MAX-ACCESS read-only
    STATUS current
    DESCRIPTION
        "The Number of output transport streams using the generic QAM device."
::= { apexGqdStatEntry 3 }


-- ------------------------------------------------------------------------------
--
-- apexOamp
--
-- apexOampConfig
--
-- apexOampConfigGeneral
--

apexOampIpAddr OBJECT-TYPE
    SYNTAX IpAddress
    MAX-ACCESS read-write
    STATUS current
    DESCRIPTION
        "This is the IP address of the OAMP (ENET1) interface of the APEX.
         The IP address is bound to the ENET1 interface of the active host
         module and transferred to the standby host module during a host
         module failover.

         Once written, the change to this parameter will only take effect 
         after apexFastEnetIpConfigApplyChange is set to 'apply'. In order
         for the change to persist through subsequent reboots or power
         cycles, the change must be saved via the apexSaveConfig parameter.

         @Commit(param=apexFastEnetIpConfigApplyChange, value=2)
         @Config(config=yes, reboot=no)
         @Save(apexSaveConfig, value=2)
         @File(ipconfig.ini, type='ini')
        "
        --MOT-MIBCOMP-BE-EXT <DbHint map="SCALAR" dbc_fmt="1"></DbHint>
::= { apexOampConfigGeneral 1 }

apexOampSubnetMask OBJECT-TYPE
    SYNTAX IpAddress
    MAX-ACCESS read-write
    STATUS current
    DESCRIPTION
        "This is subnet mask corresponding to the OAMP IP address of the APEX.
         The subnet mask is bound to the ENET1 interface of the active host
         module and transferred to the standby host module during a host
         module failover.

         Once written, the change to this parameter will only take effect 
         after apexFastEnetIpConfigApplyChange is set to 'apply'. In order
         for the change to persist through subsequent reboots or power
         cycles, the change must be saved via the apexSaveConfig parameter.

         @Commit(param=apexFastEnetIpConfigApplyChange, value=2)
         @Config(config=yes, reboot=no)
         @Save(apexSaveConfig, value=2)
         @File(ipconfig.ini, type='ini')
        "
        --MOT-MIBCOMP-BE-EXT <DbHint map="SCALAR" dbc_fmt="1"></DbHint>
::= { apexOampConfigGeneral 2 }

apexOampAutoNegotiate OBJECT-TYPE
    SYNTAX EnableDisableTYPE
    MAX-ACCESS read-write
    STATUS current
    DESCRIPTION
        "OAMP IP (Enet1) Ethernet Auto-Negotiation setting.

         'disabled' is not supported.

         Once written, the change to this parameter will only take effect 
         after apexFastEnetIpConfigApplyChange is set to 'apply'. In order
         for the change to persist through subsequent reboots or power
         cycles, the change must be saved via the apexSaveConfig parameter.

         @Commit(param=apexFastEnetIpConfigApplyChange, value=2)
         @Config(config=yes, reboot=no)
         @Save(apexSaveConfig, value=2)
         @File(ipconfig.ini, type='ini')
        "
        --MOT-MIBCOMP-BE-EXT <DbHint map="SCALAR" dbc_fmt="1"></DbHint>
::= { apexOampConfigGeneral 3 }


-- ------------------------------------------------------------------------------
--
-- apexOampStatus
--
-- apexOampStatusGeneral
--

-- none


-- ------------------------------------------------------------------------------
--
-- apexOampStatusTable
--

apexOampStatusTable OBJECT-TYPE
    SYNTAX SEQUENCE OF ApexOampStatusEntry
    MAX-ACCESS not-accessible
    STATUS current
    DESCRIPTION
        "Table of OAMP Status."
::= { apexOampStatus 2 }

apexOampStatusEntry OBJECT-TYPE
    SYNTAX ApexOampStatusEntry
    MAX-ACCESS not-accessible
    STATUS current
    DESCRIPTION
        "OAMP Status Table Entry."
    INDEX { apexOampHostModuleNum }
::= { apexOampStatusTable 1 }

ApexOampStatusEntry ::= SEQUENCE
    {
     apexOampHostModuleNum      Integer32,
     apexOampMacAddr            DisplayString,
     apexOampSpeed              INTEGER,
     apexOampDuplexMode         INTEGER,
     apexOampLinkActive         ActiveTYPE,
     apexOampBootIpAddr         IpAddress,
     apexOampBootSubnetMask     IpAddress,
     apexOampBootDefaultGateway IpAddress     
    }

apexOampHostModuleNum OBJECT-TYPE
    SYNTAX Integer32(1..2)
    MAX-ACCESS not-accessible
    STATUS current
    DESCRIPTION
        "Host Module Number."
::= { apexOampStatusEntry 1 }
                      
apexOampMacAddr OBJECT-TYPE
    SYNTAX DisplayString (SIZE (0..17))
    MAX-ACCESS read-only
    STATUS current
    DESCRIPTION
        "This is the MAC address of the APEX OAMP IP (Enet1) Interface.
         It is set at the factory and cannot be changed.
         The string length is 17 characters in the format
         'hh:hh:hh:hh:hh:hh' where 'hh' is a hexadecimal number."
        --MOT-MIBCOMP-BE-EXT <DbHint map="SCALAR" dbc_fmt="1"></DbHint>
::= { apexOampStatusEntry 2 }

apexOampSpeed OBJECT-TYPE
    SYNTAX INTEGER
        {
         interfaceSpeedUnknown  (0),
         interfaceSpeed10Mbps   (1),
         interfaceSpeed100Mbps  (2),
         interfaceSpeed1000Mbps (3)
        }
    MAX-ACCESS read-only
    STATUS current
    DESCRIPTION
        "OAMP IP (Enet1) Ethernet speed (10Mbps, 100Mbps, or 1000Mbps). This is 
         determined by the results of the auto-negotiation process. "
::= { apexOampStatusEntry 3 }

apexOampDuplexMode OBJECT-TYPE
    SYNTAX INTEGER
        {
         duplexUnknown (0),
         halfDuplex    (1),
         fullDuplex    (2)
        }
    MAX-ACCESS read-only
    STATUS current
    DESCRIPTION
        "OAMP IP (Enet1) Ethernet Duplex Mode (full or half)."
::= { apexOampStatusEntry 4 }

apexOampLinkActive OBJECT-TYPE
    SYNTAX ActiveTYPE
    MAX-ACCESS read-only
    STATUS current
    DESCRIPTION
        "This indicates if the OAMP (ENET1) link is active."
::= { apexOampStatusEntry 5 }

apexOampBootIpAddr OBJECT-TYPE
    SYNTAX IpAddress
    MAX-ACCESS read-only
    STATUS current
    DESCRIPTION
        "This is the IP address that was assigned to ENET1 the last time
         BOOTP was used to boot the host."
::= { apexOampStatusEntry 6 }

apexOampBootSubnetMask OBJECT-TYPE
    SYNTAX IpAddress
    MAX-ACCESS read-only
    STATUS current
    DESCRIPTION
        "This is the subnet mask that was assigned to ENET1 the last time
         BOOTP was used to boot the host."
::= { apexOampStatusEntry 7 }

apexOampBootDefaultGateway OBJECT-TYPE
    SYNTAX IpAddress
    MAX-ACCESS read-only
    STATUS current
    DESCRIPTION
        "This is the IP address of the default gateway that was assigned to
         ENET1 the last time BOOTP was used to boot the host."
::= { apexOampStatusEntry 8 }


-- ------------------------------------------------------------------------------
--
-- apexDataIp
--
-- apexDataIpConfig
--
-- apexDataIpConfigGeneral
--

apexDataIpAddr OBJECT-TYPE
    SYNTAX IpAddress
    MAX-ACCESS read-write
    STATUS current
    DESCRIPTION
        "This is the IP address of the Data IP (Enet2) interface of this APEX.
         The data IP address may directly be changed by setting this parameter.
         The Data IP address must be configured such that the Data IP interface
         and the OAMP interface are on different networks.

         Once written, the change to this parameter will only take effect 
         after apexFastEnetIpConfigApplyChange is set to 'apply'. In order
         for the change to persist through subsequent reboots or power
         cycles, the change must be saved via the apexSaveConfig parameter.

         @Commit(param=apexFastEnetIpConfigApplyChange, value=2)
         @Config(config=yes, reboot=no)
         @Save(apexSaveConfig, value=2)
         @File(ipconfig.ini, type='ini')
        "
::= { apexDataIpConfigGeneral 1 }

apexDataIpSubnetMask OBJECT-TYPE
    SYNTAX IpAddress
    MAX-ACCESS read-write
    STATUS current
    DESCRIPTION
        "This is subnet mask of the Data IP (Enet2) interface of this APEX.
         The data IP Subnet Mask may directly be changed by setting this parameter.

         Once written, the change to this parameter will only take effect 
         after apexFastEnetIpConfigApplyChange is set to 'apply'. In order
         for the change to persist through subsequent reboots or power
         cycles, the change must be saved via the apexSaveConfig parameter.

         @Commit(param=apexFastEnetIpConfigApplyChange, value=2)
         @Config(config=yes, reboot=no)
         @Save(apexSaveConfig, value=2)
         @File(ipconfig.ini, type='ini')
        "
::= { apexDataIpConfigGeneral 2 }

apexDataIpAutoNegotiate OBJECT-TYPE
    SYNTAX EnableDisableTYPE
    MAX-ACCESS read-write
    STATUS current
    DESCRIPTION
        "Data IP (Enet2) Ethernet Auto-Negotiation setting.

         'disabled' is not supported.

         Once written, the change to this parameter will only take effect 
         after apexFastEnetIpConfigApplyChange is set to 'apply'. In order
         for the change to persist through subsequent reboots or power
         cycles, the change must be saved via the apexSaveConfig parameter.

         @Commit(param=apexFastEnetIpConfigApplyChange, value=2)
         @Config(config=yes, reboot=no)
         @Save(apexSaveConfig, value=2)
         @File(ipconfig.ini, type='ini')
        "
::= { apexDataIpConfigGeneral 3 }


-- ------------------------------------------------------------------------------
--
-- apexDataIpStatus
--
-- apexDataIpStatusGeneral
--

-- none


-- ------------------------------------------------------------------------------
--
-- apexDataIpStatusTable
--

apexDataIpStatusTable OBJECT-TYPE
    SYNTAX SEQUENCE OF ApexDataIpStatusEntry
    MAX-ACCESS not-accessible
    STATUS current
    DESCRIPTION
        "Table of Data IP Status."
::= { apexDataIpStatus 2 }

apexDataIpStatusEntry OBJECT-TYPE
    SYNTAX ApexDataIpStatusEntry
    MAX-ACCESS not-accessible
    STATUS current
    DESCRIPTION
        "Data IP Status Table Entry."
    INDEX { apexDataIpHostModuleNum }
::= { apexDataIpStatusTable 1 }

ApexDataIpStatusEntry ::= SEQUENCE
    {
     apexDataIpHostModuleNum  Integer32,
     apexDataIpMacAddr        DisplayString,
     apexDataIpSpeed          INTEGER,
     apexDataIpDuplexMode     INTEGER,
     apexDataIpLinkActive     ActiveTYPE
    }

apexDataIpHostModuleNum OBJECT-TYPE
    SYNTAX Integer32(1..2)
    MAX-ACCESS not-accessible
    STATUS current
    DESCRIPTION
        "Host Module Number."
::= { apexDataIpStatusEntry 1 }
                      
apexDataIpMacAddr OBJECT-TYPE
    SYNTAX DisplayString (SIZE (0..17))
    MAX-ACCESS read-only
    STATUS current
    DESCRIPTION
        "This is the MAC address of the APEX Data IP (ENET2) Interface.
         It is set at the factory and cannot be changed.
         The string length is 17 characters in the format
         'hh:hh:hh:hh:hh:hh' where 'hh' is a hexadecimal number."
        --MOT-MIBCOMP-BE-EXT <DbHint map="SCALAR" dbc_fmt="1"></DbHint>
::= { apexDataIpStatusEntry 2 }

apexDataIpSpeed OBJECT-TYPE
    SYNTAX INTEGER
        {
         interfaceSpeedUnknown  (0),
         interfaceSpeed10Mbps   (1),
         interfaceSpeed100Mbps  (2),
         interfaceSpeed1000Mbps (3)
        }
    MAX-ACCESS read-only
    STATUS current
    DESCRIPTION
        "Data IP (ENET2) Ethernet speed (10Mbps, 100Mbps, or 1000Mbps). This is 
         determined by the results of the auto-negotiation process."
::= { apexDataIpStatusEntry 3 }

apexDataIpDuplexMode OBJECT-TYPE
    SYNTAX INTEGER
        {
         duplexUnknown (0),
         halfDuplex    (1),
         fullDuplex    (2)
        }
    MAX-ACCESS read-only
    STATUS current
    DESCRIPTION
        "Data IP (ENET2) Ethernet Duplex Mode (full or half) This is determined by the results of the
         auto-negotiation process. "
::= { apexDataIpStatusEntry 4 }

apexDataIpLinkActive OBJECT-TYPE
    SYNTAX ActiveTYPE
    MAX-ACCESS read-only
    STATUS current
    DESCRIPTION
        "This indicates if the Data IP (ENET2) link is active."
::= { apexDataIpStatusEntry 5 }


-- ------------------------------------------------------------------------------
--
-- apexGbe
--
-- apexGbeConfig
--
-- apexGbeConfigGeneral
--

apexGbeDefaultGateway OBJECT-TYPE
    SYNTAX IpAddress
    MAX-ACCESS read-write
    STATUS current
    DESCRIPTION
        "This is the IP address of the default gateway for the 10 Gigabit 
         Ethernet interfaces.
         
         Once written, the change to this table will only take immediate
         effect after apexGbeConfigTableApplyChange is set to 'apply'.
         However, in order for the change to persist through
         subsequent reboots or power cycles, the change must be saved via
         the apexSaveConfig parameter.

         @Config(config=yes, reboot=no)
         @Commit(param=apexGbeConfigTableApplyChange, value=2)
         @Save(apexSaveConfig, value=2)
         @File(config.ini, type='ini')
        "
::= { apexGbeConfigGeneral 1 }

apexGbeGarpPeriodicity OBJECT-TYPE
    SYNTAX Integer32(20..300)
    MAX-ACCESS read-write
    STATUS current
    DESCRIPTION
        "Gratuitous ARP period in range of 20 to 300 seconds.

         Once written, the change to this parameter will take immediate
         effect.  However, in order for the change to persist through
         subsequent reboots or power cycles, the change must be saved via
         the apexSaveConfig parameter.

         @Config(config=yes, reboot=no)
         @Save(apexSaveConfig, value=2)
         @File(config.ini, type='ini')
        "
::= { apexGbeConfigGeneral 2 }

apexGbeConfigTableApplyChange OBJECT-TYPE
    SYNTAX ApplyDataToDeviceTYPE
    MAX-ACCESS read-write
    STATUS current
    DESCRIPTION
        "The Apply for the Gigabit Ethernet Configuration Table. This parameter
         MUST be set to 'apply' in order for any of the data in the
         apexGbeConfigTable to take effect.  This parameter
         MUST be set LAST after all other data in the apexGbeConfigTable
         has been configured.

         @Config(config=no, reboot=no)
        "
::= { apexGbeConfigGeneral 3 }

apexGbeNominalBufferLevel OBJECT-TYPE
    SYNTAX Integer32(50..475)
    MAX-ACCESS read-write
    STATUS current
    DESCRIPTION
        "Gigabit Ethernet Nominal Buffer Level. Range of 50 to 475 milliseconds
         in increments of 5 ms.  A change to this parameter will cause the
         Gigabit Ethernet processor to reset all of its internal Ethernet
         frame buffers. This will result in a momentary loss of data causing
         a minor glitch on all output streams.
         
         The buffer level is the normal standard starting level for an input
         stream buffer. It is highly recommended that this level not be changed
         from its default setting. The buffer level needs to be set at an 
         appropriate amount to allow for network jitter, clock skew between the
         APEX and input source, and for maximum time between PCRs (100ms). In
         addition, the level must not be set too high as the buffer needs to be
         able to grow as packets are received and PCR processing is applied. This
         buffer level is the initial level the APEX will attempt to maintain at
         all times. 

         Once written, the change to this parameter will take immediate
         effect.  However, in order for the change to persist through
         subsequent reboots or power cycles, the change must be saved via
         the apexSaveConfig parameter.

         @Config(config=yes, reboot=no)
         @Save(apexSaveConfig, value=2)
         @File(config.ini, type='ini')
        "
::= { apexGbeConfigGeneral 4 }

apexGbeConfInputUnicastTimeout OBJECT-TYPE
    SYNTAX Integer32(600..6000)
    MAX-ACCESS read-write
    STATUS current
    DESCRIPTION
        "Loss of input stream timeout value (in milliseconds) for unicast inputs. 
         This determines the amount of time a unicast input stream is missing
         before the APEX will declare the input stream lost. 
         
         Loss of unicast input is not applicable to UDP Port Mapping inputs. 
         
         Once written, the change to this parameter will take immediate effect.
         However, in order for the change to persist through subsequent reboots
         or power cycles, the change must be saved via the apexSaveConfig parameter.

         @Range(step=200)
         @Config(config=yes, reboot=no)
         @Save(apexSaveConfig, value=2)
         @File(config.ini, type='ini')
        "
::= { apexGbeConfigGeneral 5 }

apexGbeConfInputMulticastTimeout OBJECT-TYPE
    SYNTAX Integer32(600..6000)
    MAX-ACCESS read-write
    STATUS current
    DESCRIPTION
        "Loss of input stream timeout value (in milliseconds) for multicast inputs. 
         This determines the amount of time a unicast input stream is missing before 
         the APEX will declare the input stream lost. 

         Loss of multicast input is not applicable to UDP Port Mapping inputs. 

         Once written, the change to this parameter will take immediate effect.
         However, in order for the change to persist through subsequent reboots
         or power cycles, the change must be saved via the apexSaveConfig parameter.

         @Range(step=200)
         @Config(config=yes, reboot=no)
         @Save(apexSaveConfig, value=2)
         @File(config.ini, type='ini')
        "
::= { apexGbeConfigGeneral 6 }

apexGbeConfLossOfInputTsType OBJECT-TYPE
    SYNTAX RateComparisonTYPE
    MAX-ACCESS read-write
    STATUS current
    DESCRIPTION
        "Loss of input stream type. Determines if detection of loss of an input
         stream is based on data rate or stream rate. Data rate includes only 
         non-null MPEG packets (such as video and audio packets). Stream rate 
         includes all packets, including null packets. The loss of an input stream
         uses the timeout value for the specific input (unicast or multicast) and 
         the input type. If no packets are received within the specified timeout 
         value, taking into account the loss of input type checking, then the input
         stream is determined to be missing. 
         
         Data rate should be used for detecting loss of input when the input stream
         is normally null filled. When a user requires notification of a loss of
         input stream when there is no content streamed, data rate should be selected.
         
         Stream rate should be used for detecting loss of input stream when the user
         requires to be notified when there is no input stream at all being received.

         Loss of input is only applicable to inputs used for Session Control (SDV).   
         
         Once written, the change to this parameter will take immediate effect.
         However, in order for the change to persist through subsequent reboots
         or power cycles, the change must be saved via the apexSaveConfig parameter.

         @Config(config=yes, reboot=no)
         @Save(apexSaveConfig, value=2)
         @File(config.ini, type='ini')
        "
::= { apexGbeConfigGeneral 7 }

apexGbeConfFrameCounterTableResetAll OBJECT-TYPE
    SYNTAX ResetStatisticsTYPE
    MAX-ACCESS read-write
    STATUS current
    DESCRIPTION
        "Reset Ethernet Frame Counter Totals for all GigE interfaces:
            - apexGbeTotalRxSinglecastFrames
            - apexGbeTotalRxMulticastFrames
            - apexGbeTotalRxBroadcastFrames
            - apexGbeTotalRxErrorFrames
            - apexGbeTotalRxFrames
            - apexGbeTotalTxGoodFrames
            - apexGbeTotalTxErrorFrames

         Once written, the change to this parameter will take immediate effect.

         @Config(config=no, reboot=no)
        "
::= { apexGbeConfigGeneral 8 }

apexGbeConfFrameBufferAlarmThreshold OBJECT-TYPE
    SYNTAX Integer32(0..100)
    MAX-ACCESS read-write
    STATUS current
    DESCRIPTION
        "User defined threshold representing a percentage of frame buffer depth.
         The frame buffer level is monitored by the APEX and the maximum level is
         based on the actual input data rate.  The threshold percentage is used
         to determine when to issue a Gigabit Ethernet Frame Buffer Fullness
         alarm (apexAlarmGbeBufferFullness).

         @Config(config=yes, reboot=no)
         @Save(apexSaveConfig, value=2)
         @File(config.ini, type='ini')
        "
::= { apexGbeConfigGeneral 9 }


-- ------------------------------------------------------------------------------
--
-- apexGbeConfigTable
--

apexGbeConfigTable OBJECT-TYPE
    SYNTAX SEQUENCE OF ApexGbeConfigEntry
    MAX-ACCESS not-accessible
    STATUS current
    DESCRIPTION
        "This is a table of configuration parameters for the
         Gigabit Ethernet Interfaces.

         Once written, the change to this table will only take immediate
         effect after apexGbeConfigTableApplyChange is set to 'apply'.  In
         order for the change to persist through subsequent reboots or power
         cycles, the change must be saved via the apexSaveConfig parameter.

         @Config(config=yes, reboot=no)
         @Commit(param=apexGbeConfigTableApplyChange, value=2)
         @Save(apexSaveConfig, value=2)
         @File(config.ini, type='ini')
        "
::= { apexGbeConfig 2 }

apexGbeConfigEntry OBJECT-TYPE
    SYNTAX ApexGbeConfigEntry
    MAX-ACCESS not-accessible
    STATUS current
    DESCRIPTION
        "Gigabit Ethernet Interface Configuration Table Entry."
    INDEX { apexGbeConfigInterfaceNum }
::= { apexGbeConfigTable 1 }

ApexGbeConfigEntry ::= SEQUENCE
    {
     apexGbeConfigInterfaceNum          Integer32,
     apexGbeConfigOperatingMode         INTEGER,
     apexGbeConfigIpAddr                IpAddress,
     apexGbeConfigIpSubnetMask          IpAddress,
     apexGbeConfigAutoNegotiate         EnableDisableTYPE,
     apexGbeConfigBackupInterface       Integer32,
     apexGbeConfigSuspendFailover       EnableDisableTYPE,
     apexGbeConfigAutoSwitchBackEnable  EnableDisableTYPE,
     apexGbeConfigMirrorGbe             Integer32,
     apexGbeConfigMirrorQamBlade        Integer32,
     apexGbeConfigFailoverMacAddress    INTEGER
    }

apexGbeConfigInterfaceNum OBJECT-TYPE
    SYNTAX Integer32(1..12)
    MAX-ACCESS not-accessible
    STATUS current
    DESCRIPTION
        "Gigabit Ethernet Interface Number."
::= { apexGbeConfigEntry 1 }

apexGbeConfigOperatingMode OBJECT-TYPE
    SYNTAX INTEGER
        {
         notApplicable  (0),
         disabled       (1),
         primary        (2),
         backup         (3),
         mirrorGbe      (4),
         mirrorQamBlade (5)
        }
    MAX-ACCESS read-write
    STATUS current
    DESCRIPTION
        "This parameter enables the Gigabit Ethernet Interface.
        "
::= { apexGbeConfigEntry 2 }

apexGbeConfigIpAddr OBJECT-TYPE
    SYNTAX IpAddress
    MAX-ACCESS read-write
    STATUS current
    DESCRIPTION
        "This is the IP address of this Gigabit Ethernet interface.

         It is recommended that each Gigabit Ethernet interface be
         on a different subnet.  Each must be given a unique IP address.

         0.0.0.0 indicates the interface is not in use.
        "
::= { apexGbeConfigEntry 3 }

apexGbeConfigIpSubnetMask OBJECT-TYPE
    SYNTAX IpAddress
    MAX-ACCESS read-write
    STATUS current
    DESCRIPTION
        "This is subnet mask of this Gigabit Ethernet interface.
        "
::= { apexGbeConfigEntry 4 }

apexGbeConfigAutoNegotiate OBJECT-TYPE
    SYNTAX EnableDisableTYPE
    MAX-ACCESS read-write
    STATUS current
    DESCRIPTION
        "Auto negotiation enabled or disabled setting for each interface.
        "
::= { apexGbeConfigEntry 5 }

apexGbeConfigBackupInterface OBJECT-TYPE
    SYNTAX Integer32(0..12)
    MAX-ACCESS read-write
    STATUS current
    DESCRIPTION
        "Backup GigE interface for this interface.
         0 = No backup for this interface.

         Only applicable when apexGbeConfigOperatingMode is 'primary'.
        "
::= { apexGbeConfigEntry 6 }

apexGbeConfigSuspendFailover OBJECT-TYPE
    SYNTAX EnableDisableTYPE
    MAX-ACCESS read-write
    STATUS current
    DESCRIPTION
        "Enables and disables suspending of Interface failover. Prevents failovers
         to or from backup.  Force failover (apexGbeConfIfRedundForceFailover)
         overrides this setting.

         Only applicable when apexGbeConfigOperatingMode is 'primary' or 'backup'.
        "
::= { apexGbeConfigEntry 7 }

apexGbeConfigAutoSwitchBackEnable OBJECT-TYPE
    SYNTAX EnableDisableTYPE
    MAX-ACCESS read-write
    STATUS current
    DESCRIPTION
        "Enables the ability for the backup interface to switch back when
         link is re-detected on the primary interface. Auto switch back to the 
         primary interface will not occur if the user forced a failover to the
         backup. Auto switch back only occurs after a non-forced failover.

         Only applicable when apexGbeConfigOperatingMode is 'primary' or 'backup'.
        "
::= { apexGbeConfigEntry 8 }

apexGbeConfigMirrorGbe OBJECT-TYPE
    SYNTAX Integer32(0..12)
    MAX-ACCESS read-write
    STATUS current
    DESCRIPTION
        "GigE interface to mirror.
        
         Only applicable when apexGbeConfigOperatingMode is 'mirrorGbe'.
        "
::= { apexGbeConfigEntry 9 }

apexGbeConfigMirrorQamBlade OBJECT-TYPE
    SYNTAX Integer32(0..8)
    MAX-ACCESS read-write
    STATUS current
    DESCRIPTION
        "QAM blade to mirror.

         Only applicable when apexGbeConfigOperatingMode is 'mirrorQamBlade'.
        "
::= { apexGbeConfigEntry 10 }

apexGbeConfigFailoverMacAddress OBJECT-TYPE
    SYNTAX INTEGER
        {
         useBackupMacAddress  (0),
         usePrimaryMacAddress (1)
        }
    MAX-ACCESS read-write
    STATUS current
    DESCRIPTION
        "On GigE interface failover to backup interface, indicates to use either
         the backup interface MAC address or use the primary interface MAC address.
         The backup interface on a failover always uses the primary IP and subnet. 
         This setting allows the backup to also use the MAC address of the primary.
         This value can only be changed when the primary is currently not failed
         over to the backup.
        "
::= { apexGbeConfigEntry 11 }

-- ------------------------------------------------------------------------------
--
-- apexGbeFrameCounterResetTable
--

apexGbeFrameCounterResetTable OBJECT-TYPE
    SYNTAX SEQUENCE OF ApexGbeFrameCounterResetEntry
    MAX-ACCESS not-accessible
    STATUS current
    DESCRIPTION
        "Table of Gigabit Ethernet Frame Counter Reset."
::= { apexGbeConfig 3 }

apexGbeFrameCounterResetEntry OBJECT-TYPE
    SYNTAX ApexGbeFrameCounterResetEntry
    MAX-ACCESS not-accessible
    STATUS current
    DESCRIPTION
        "Gigabit Ethernet Interface Frame Counter Reset Table Entry."
    INDEX { apexGbeFrameCounterResetGbeIfNum }
::= { apexGbeFrameCounterResetTable 1 }

ApexGbeFrameCounterResetEntry ::= SEQUENCE
    {
     apexGbeFrameCounterResetGbeIfNum Integer32,
     apexGbeFrameCounterReset         ResetStatisticsTYPE
    }

apexGbeFrameCounterResetGbeIfNum OBJECT-TYPE
    SYNTAX Integer32(1..12)
    MAX-ACCESS not-accessible
    STATUS current
    DESCRIPTION
        "The index of the Gigabit Ethernet Frame Counter Table.
         Represents the Gigabit Ethernet interface number."
::= { apexGbeFrameCounterResetEntry 1 }

apexGbeFrameCounterReset OBJECT-TYPE
    SYNTAX ResetStatisticsTYPE
    MAX-ACCESS read-write
    STATUS current
    DESCRIPTION
        "Reset Ethernet Frame Counter Statistics totals for a single GigE interface:
            - apexGbeTotalRxSinglecastFrames
            - apexGbeTotalRxMulticastFrames
            - apexGbeTotalRxBroadcastFrames
            - apexGbeTotalRxErrorFrames
            - apexGbeTotalRxFrames
            - apexGbeTotalTxGoodFrames
            - apexGbeTotalTxErrorFrames

         Once written, the change to this parameter will take immediate effect.

         @Config(config=no, reboot=no)
        "
::= { apexGbeFrameCounterResetEntry 2 }


-- ------------------------------------------------------------------------------
--
-- apexGbeConfigInterfaceRedundancy
--
-- apexGbeConfigInterfaceRedundancyGeneral
--

apexGbeConfIfRedundAutoSwitchBackPeriod OBJECT-TYPE
    SYNTAX Integer32(1..30)
    MAX-ACCESS read-write
    STATUS current
    DESCRIPTION
        "Timer for determining that the primary interface is OK for auto-
         switchback.  The primary interface must have link for the configured
         amount of time.  Valid time is 1-30 seconds.

         Once written, the change to this parameter will take immediate effect.
         However, in order for the change to persist through subsequent
         reboots or power cycles, the change must be saved via apexSaveConfig.

         @Config(config=yes, reboot=no)
         @Save(apexSaveConfig, value=2)
         @File(config.ini, type='ini')
        "
::= { apexGbeConfigInterfaceRedundancyGeneral 1 }


-- ------------------------------------------------------------------------------
--
-- apexGbeConfigInterfaceRedundancyForceTable
--

apexGbeConfigInterfaceRedundancyForceTable OBJECT-TYPE
    SYNTAX SEQUENCE OF ApexGbeConfigInterfaceRedundancyForceEntry
    MAX-ACCESS not-accessible
    STATUS current
    DESCRIPTION
        "Table of Force Failover commands for the GBE Interface Redundancy feature.
        "
::= { apexGbeConfigInterfaceRedundancy 2 }

apexGbeConfigInterfaceRedundancyForceEntry OBJECT-TYPE
    SYNTAX ApexGbeConfigInterfaceRedundancyForceEntry
    MAX-ACCESS not-accessible
    STATUS current
    DESCRIPTION
        "GBE Config Interface Redundancy Table Entry."
    INDEX { apexGbeConfIfRedundForceIndex }
::= { apexGbeConfigInterfaceRedundancyForceTable 1 }

ApexGbeConfigInterfaceRedundancyForceEntry ::= SEQUENCE
    {
     apexGbeConfIfRedundForceIndex    Integer32,
     apexGbeConfIfRedundForceFailover INTEGER
    }

apexGbeConfIfRedundForceIndex OBJECT-TYPE
    SYNTAX Integer32(1..12)
    MAX-ACCESS not-accessible
    STATUS current
    DESCRIPTION
        "The index of the GBE Config Interface Redundancy Force Table."
::= { apexGbeConfigInterfaceRedundancyForceEntry 1 }

apexGbeConfIfRedundForceFailover OBJECT-TYPE
    SYNTAX INTEGER
        {
         notApplicable         (0),
         failoverNotInProgress (1),
         failover              (2)
        }
    MAX-ACCESS read-write
    STATUS current
    DESCRIPTION
        "When set to failover(2), this results in the APEX switching to 
         the interface that is currently not in use.  If the primary GbE is 
         in use and this is set to failover(2) mappings will be then 
         routed to the backup GbE.  If the secondary GbE is in use and 
         this is set to failover(2) mappings will then be routed back to 
         the primary GbE.

         Only valid when apexGbeConfigOperatingMode is 'primary' or 'backup'.

         Once written, the change to this parameter will take immediate effect.

         @Config(config=no, reboot=no)
        "
::= { apexGbeConfigInterfaceRedundancyForceEntry 2 }


-- ------------------------------------------------------------------------------
--
-- apexGbeStatus
--
-- apexGbeStatusGeneral
--

apexGbeMaxInputTs OBJECT-TYPE
    SYNTAX Integer32
    MAX-ACCESS read-only
    STATUS current
    DESCRIPTION
        "Maximum number of 10Gigabit Ethernet input transport streams
         that can be opened on this APEX.  This is the maximum across
         all installed GigE interfaces.  One GigE interface can use
         all Input streams.
        "
::= { apexGbeStatusGeneral 1 }

apexGbeTotalInputTsCount OBJECT-TYPE
    SYNTAX Counter32
    MAX-ACCESS read-only
    STATUS current
    DESCRIPTION
        "Number of input transport streams in use on the APEX. An input stream
         is considered to be in use even when it is not actively opened and 
         receiving data. The total number of input streams is a count of the number
         of primary input streams. For input streams that have a primary and a backup 
         stream, those streams count as 1 input stream. Each input stream is marked 
         as in use to reserve that stream to ensure it can be opened at any time. 
        "
::= { apexGbeStatusGeneral 2 }

apexGbeTotalSecInputTsCount OBJECT-TYPE
    SYNTAX Counter32
    MAX-ACCESS read-only
    STATUS current
    DESCRIPTION
        "Number of secondary input transport streams in use on the APEX. A secondary
         input stream is considered to be in use even when it is not actively opened 
         and receiving data. 
        "
::= { apexGbeStatusGeneral 3 }

apexGbeMulticastInputTsCount OBJECT-TYPE
    SYNTAX Counter32
    MAX-ACCESS read-only
    STATUS current
    DESCRIPTION
        "Number of multicast input transport streams in use on the APEX. This is a
         count of all input streams that have been configured for multicast reception.
         An input stream is considered to be in use even when it is not actively opened 
         and receiving data. For input streams that have a primary and a backup stream,
         those streams count as 1 input stream.
        "
::= { apexGbeStatusGeneral 4 }

apexGbeSinglecastInputTsCount OBJECT-TYPE
    SYNTAX Counter32
    MAX-ACCESS read-only
    STATUS current
    DESCRIPTION
        "Number of singlecast input transport streams in use on the APEX. This is a
         count of all input streams that have been configured for singlecast reception.
         An input stream is considered to be in use even when it is not actively opened 
         and receiving data. For input streams that have a primary and a backup stream,
         those streams count as 1 input stream.
        "
::= { apexGbeStatusGeneral 5 }

apexGbeRoutedPacketUpdateInterval OBJECT-TYPE
    SYNTAX Integer32
    MAX-ACCESS read-only
    STATUS current
    DESCRIPTION
        "Time in seconds between Gigabit Ethernet Routed Packet
         Count updates.  The count during this time is defined as one sample.

         This time applies to packet counts contained in
         apexGbeStatusRoutedPacketTable.

         To compute rate from packet count for the last update interval:
         Rate(bps) = (Packet_Count * 188 bytes/packet * 8 bits/byte) / Update_Interval

         This value is set by the APEX at startup and is constant.
        "
::= { apexGbeStatusGeneral 6 }


-- ------------------------------------------------------------------------------
--
-- apexGbeStatusTable
--

apexGbeStatusTable OBJECT-TYPE
    SYNTAX SEQUENCE OF ApexGbeStatusEntry
    MAX-ACCESS not-accessible
    STATUS current
    DESCRIPTION
        "This is a table of status parameters for the
         Gigabit Ethernet Interface."
::= { apexGbeStatus 2 }

apexGbeStatusEntry OBJECT-TYPE
    SYNTAX ApexGbeStatusEntry
    MAX-ACCESS not-accessible
    STATUS current
    DESCRIPTION
        "Gigabit Ethernet Interface Status Table Entry."
    INDEX { apexGbeStatusGbeInterfaceNum }
::= { apexGbeStatusTable 1 }

ApexGbeStatusEntry ::= SEQUENCE
    {
     apexGbeStatusGbeInterfaceNum        Integer32,
     apexGbeStatusMacAddr                DisplayString,
     apexGbeStatusLinkActive             ActiveTYPE,
     apexGbeStatusIgmpVersion            INTEGER,
     apexGbeStatusLossOfPhysicalInput    INTEGER,
     apexGbeStatusRedundState            INTEGER,
     apexGbeStatusRedundFailedInterface  Integer32,
     apexGbeStatusRedundFailoverStatus   INTEGER,
     apexGbeStatusInvalidApplyText       DisplayString,
     apexGbeStatusSpeed                  INTEGER
    }

apexGbeStatusGbeInterfaceNum OBJECT-TYPE
    SYNTAX Integer32(1..12)
    MAX-ACCESS not-accessible
    STATUS current
    DESCRIPTION
        "Gigabit Ethernet Interface Number."
::= { apexGbeStatusEntry 1 }

apexGbeStatusMacAddr OBJECT-TYPE
    SYNTAX DisplayString (SIZE (0..17))
    MAX-ACCESS read-only
    STATUS current
    DESCRIPTION
        "This is the MAC address of the Gigabit Ethernet Interface.
         It is set at the factory and cannot be changed.
         The string length is 17 characters in the format
         'hh:hh:hh:hh:hh:hh' where 'hh' is a hexadecimal number."
::= { apexGbeStatusEntry 2 }

apexGbeStatusLinkActive OBJECT-TYPE
    SYNTAX ActiveTYPE
    MAX-ACCESS read-only
    STATUS current
    DESCRIPTION
        "This indicates if the Gigabit Ethernet optical link is active."
::= { apexGbeStatusEntry 3 }

apexGbeStatusIgmpVersion OBJECT-TYPE
    SYNTAX INTEGER
        {
         notApplicable (0),
         igmpV1 (1),
         igmpV2 (2),
         igmpV3 (3)
        }
    MAX-ACCESS read-only
    STATUS current
    DESCRIPTION
        "This indicates the IGMP Version being used on this interface."
::= { apexGbeStatusEntry 4 }

apexGbeStatusLossOfPhysicalInput OBJECT-TYPE
    SYNTAX INTEGER
        {
         notApplicable (0),
         ok(1),
         indeterminate(2),
         warning(3),
         minor(4),
         major(5),
         critical(6)
        }
    MAX-ACCESS read-only
    STATUS current
    DESCRIPTION
        "The current severity of apexAlarmGbeLossOfPhysicalInput
         for this interface.
        "
::= { apexGbeStatusEntry 5 }

apexGbeStatusRedundState OBJECT-TYPE
    SYNTAX INTEGER
        {
         notApplicable (0),
         active        (1),
         failedOver    (2),
         standby       (3)
        }
    MAX-ACCESS read-only
    STATUS current
    DESCRIPTION
        "Interface Redundancy status for this interface.
         
         'notApplicable' for a disabled or mirror interface.
         
         'active' or 'failedOver' for a primary interface.
         
         'active' or 'standby' for a backup interface.
        "
::= { apexGbeStatusEntry 6 }

apexGbeStatusRedundFailedInterface OBJECT-TYPE
    SYNTAX Integer32(0..12)
    MAX-ACCESS read-only
    STATUS current
    DESCRIPTION
        "For an active backup interface, this indicates the primary that has
         failed over to this backup.
         
         Only applicable for backup interface.
        "
::= { apexGbeStatusEntry 7 }

apexGbeStatusRedundFailoverStatus OBJECT-TYPE
    SYNTAX INTEGER
        {
         ok(1),
         indeterminate(2),
         warning(3),
         minor(4),
         major(5),
         critical(6)
        }
    MAX-ACCESS read-only
    STATUS current
    DESCRIPTION
        "The current severity of apexAlarmGbeInterfaceRedundFailover
         for this interface.
        "
::= { apexGbeStatusEntry  8 }

apexGbeStatusInvalidApplyText OBJECT-TYPE
    SYNTAX DisplayString (SIZE (0..80))
    MAX-ACCESS read-only
    STATUS current
    DESCRIPTION
        "When apexGbeConfigTableApplyChange is set to applyNotInProgressInvalidData
         this entry may contain a text description of what was wrong with the data.
         This entry contains the description for the most recent apply of a
         table entry that was invalid.  It contains the description for the GBE interface
         in the associated with the current row of apexGbeConfigTable 
        "
::= { apexGbeStatusEntry 9 }

apexGbeStatusSpeed OBJECT-TYPE
    SYNTAX INTEGER
        {
         interfaceSpeedUnknown  (0),
         interfaceSpeed10Mbps   (1),
         interfaceSpeed100Mbps  (2),
         interfaceSpeed1000Mbps (3),
         interfaceSpeed10Gbps   (4)
        }
    MAX-ACCESS read-only
    STATUS current
    DESCRIPTION
        "Gigabit Ethernet speed. This is determined by the 
         type of SFP installed. "
::= { apexGbeStatusEntry 10 }


-- ------------------------------------------------------------------------------
--
-- apexGbeInputTsAssignedTable
--

apexGbeInputTsAssignedTable OBJECT-TYPE
    SYNTAX SEQUENCE OF ApexGbeInputTsAssignedEntry
    MAX-ACCESS not-accessible
    STATUS current
    DESCRIPTION
        "Table of Gigabit Ethernet Input TS Assigned data."
::= { apexGbeStatus 3 }

apexGbeInputTsAssignedEntry OBJECT-TYPE
    SYNTAX ApexGbeInputTsAssignedEntry
    MAX-ACCESS not-accessible
    STATUS current
    DESCRIPTION
        "Gigabit Ethernet Interface Input TS Assigned Table Entry."
    INDEX { apexGbeInputTsAssignedGbeInterfaceNum }
::= { apexGbeInputTsAssignedTable 1 }

ApexGbeInputTsAssignedEntry ::= SEQUENCE
    {
     apexGbeInputTsAssignedGbeInterfaceNum Integer32,
     apexGbeInputTsAssignedCount           Counter32,
     apexGbeSecInputTsAssignedCount        Counter32,
     apexGbeInputTsInUseCount              Counter32,
     apexGbeInputTsDepiEngaged             ActiveTYPE
    }

apexGbeInputTsAssignedGbeInterfaceNum OBJECT-TYPE
    SYNTAX Integer32(1..12)
    MAX-ACCESS not-accessible
    STATUS current
    DESCRIPTION
        "The index of the Gigabit Ethernet Input TS Assigned Table.
         Represents the Gigabit Ethernet interface number."
::= { apexGbeInputTsAssignedEntry 1 }

apexGbeInputTsAssignedCount OBJECT-TYPE
    SYNTAX Counter32
    MAX-ACCESS read-only
    STATUS current
    DESCRIPTION
        "Number of input transport streams assigned to the GigE interface.
         This is a count of inputs assigned for the Primary input stream.
         For GigE interface redundancy, the counts of input streams are 
         always indicated on the Primary interface index.

         This is not a count of opened or in use input streams. Assigned input streams
         are set when mappings are started to reserve an input stream for future use. 
        "
::= { apexGbeInputTsAssignedEntry 2 }

apexGbeSecInputTsAssignedCount OBJECT-TYPE
    SYNTAX Counter32
    MAX-ACCESS read-only
    STATUS current
    DESCRIPTION
        "Number of secondary input transport streams assigned to the GigE interface.
         This is a count of the number of secondary input streams when TS redundancy
         is in use. Each secondary is associated with just 1 primary input stream.
         
         This is not a count of opened or in use input streams. Assigned input streams
         are set when mappings are started to reserve an input stream for future use. 
        "
::= { apexGbeInputTsAssignedEntry 3 }

apexGbeInputTsInUseCount OBJECT-TYPE
    SYNTAX Counter32
    MAX-ACCESS read-only
    STATUS current
    DESCRIPTION
        "Total number of input streams currently in use for each GigE interface port.
         This indicates the number of unique input streams actively opened per port.
         This count includes primary and secondary.
        "
::= { apexGbeInputTsAssignedEntry 4 }

apexGbeInputTsDepiEngaged OBJECT-TYPE
    SYNTAX ActiveTYPE
    MAX-ACCESS read-only
    STATUS current
    DESCRIPTION
        "Indicates if DEPI control connections or sessions are currently established
         for each GigE interface port.
        "
::= { apexGbeInputTsAssignedEntry 5 }


-- ------------------------------------------------------------------------------
--
-- apexGbeStatusRoutedPacketTable
--

apexGbeStatusRoutedPacketTable OBJECT-TYPE
    SYNTAX SEQUENCE OF ApexGbeStatusRoutedPacketEntry
    MAX-ACCESS not-accessible
    STATUS current
    DESCRIPTION
        "This table contains Gigabit Ethernet MPEG packet counts for
         each QAM blade and Output Transport Stream of this APEX.

         Update interval is apexGbeRoutedPacketUpdateInterval."
::= { apexGbeStatus 4 }

apexGbeStatusRoutedPacketEntry OBJECT-TYPE
    SYNTAX ApexGbeStatusRoutedPacketEntry
    MAX-ACCESS not-accessible
    STATUS current
    DESCRIPTION
        "Gigabit Ethernet Interface Status Routed Packet
         Table Entry."
    INDEX { apexGbeStatusRoutedPacketBladeNum, apexGbeStatusRoutedPacketOutputTsNum }
::= { apexGbeStatusRoutedPacketTable 1 }

ApexGbeStatusRoutedPacketEntry ::= SEQUENCE
    {
     apexGbeStatusRoutedPacketBladeNum    Integer32,
     apexGbeStatusRoutedPacketOutputTsNum Integer32,
     apexGbeStatusTotRoutedPackets        Counter32,
     apexGbeStatusNumRoutedPackets        Counter32
    }

apexGbeStatusRoutedPacketBladeNum OBJECT-TYPE
    SYNTAX Integer32(1..8)
    MAX-ACCESS not-accessible
    STATUS current
    DESCRIPTION
        "Blade Number."
::= { apexGbeStatusRoutedPacketEntry 1 }

apexGbeStatusRoutedPacketOutputTsNum OBJECT-TYPE
    SYNTAX Integer32(1..256)
    MAX-ACCESS not-accessible
    STATUS current
    DESCRIPTION
        "Output Stream Index."
::= { apexGbeStatusRoutedPacketEntry 2 }

apexGbeStatusTotRoutedPackets OBJECT-TYPE
    SYNTAX Counter32
    MAX-ACCESS read-only
    STATUS current
    DESCRIPTION
        "Total number of Gigabit Ethernet MPEG packets routed to this
         Output Transport Stream."
::= { apexGbeStatusRoutedPacketEntry 3 }

apexGbeStatusNumRoutedPackets OBJECT-TYPE
    SYNTAX Counter32
    MAX-ACCESS read-only
    STATUS current
    DESCRIPTION
        "Number of Gigabit Ethernet MPEG packets routed to this Output
         Transport Stream during the last monitoring period
         (apexGbeRoutedPacketUpdateInterval)."
::= { apexGbeStatusRoutedPacketEntry 4 }


-- ------------------------------------------------------------------------------
--
-- apexGbeStatusQamRoutedPacketTable
--

apexGbeStatusQamRoutedPacketTable OBJECT-TYPE
    SYNTAX SEQUENCE OF ApexGbeStatusQamRoutedPacketEntry
    MAX-ACCESS not-accessible
    STATUS current
    DESCRIPTION
        "This table contains Gigabit Ethernet stream counts that
         are routed out to all active output streams for each QAM 
         blade of this APEX.

         Update interval is apexGbeRoutedPacketUpdateInterval."
::= { apexGbeStatus 5 }

apexGbeStatusQamRoutedPacketEntry OBJECT-TYPE
    SYNTAX ApexGbeStatusQamRoutedPacketEntry
    MAX-ACCESS not-accessible
    STATUS current
    DESCRIPTION
        "Gigabit Ethernet Interface Status QAM Routed Packet
         Table Entry."
    INDEX { apexGbeStatusQamRoutedPacketBladeNum}
::= { apexGbeStatusQamRoutedPacketTable 1 }

ApexGbeStatusQamRoutedPacketEntry ::= SEQUENCE
    {
     apexGbeStatusQamRoutedPacketBladeNum        Integer32,     
     apexGbeStatusQamRoutedPacketCurStreamCount  Counter32,
     apexGbeStatusQamRoutedPacketTotStreamCount  Counter32
    }

apexGbeStatusQamRoutedPacketBladeNum OBJECT-TYPE
    SYNTAX Integer32(1..8)
    MAX-ACCESS not-accessible
    STATUS current
    DESCRIPTION
        "Blade Number."
::= { apexGbeStatusQamRoutedPacketEntry 1 }

apexGbeStatusQamRoutedPacketCurStreamCount OBJECT-TYPE
    SYNTAX Counter32
    MAX-ACCESS read-only
    STATUS current
    DESCRIPTION
        "Five second count of number of packets that are routed to all 
         output streams on this QAM Blade during the last monitoring 
         period. This count is only of packets processed by the Network
         Processing Unit of the QAM blade and transmitted out to all active
         output streams. Only non-null packets are routed out of the NPU.
        "
::= { apexGbeStatusQamRoutedPacketEntry 2 }

apexGbeStatusQamRoutedPacketTotStreamCount OBJECT-TYPE
    SYNTAX Counter32
    MAX-ACCESS read-only
    STATUS current
    DESCRIPTION
        "Total number of packets routed to all outputs on this QAM blade."         
::= { apexGbeStatusQamRoutedPacketEntry 3 }


-- ------------------------------------------------------------------------------
--
-- apexGbeStatusFrameCounter
--
-- apexGbeStatusFrameCounterGeneral
--

apexGbeFrameCounterUpdateInterval OBJECT-TYPE
    SYNTAX Integer32
    MAX-ACCESS read-only
    STATUS current
    DESCRIPTION
        "Time in seconds between Gigabit Ethernet Frame Counter
         updates.  The count during this time is defined as one sample.

         This time applies to packet counts contained in
         apexGbeStatusFrameCounterTable.

         To compute rate from frame count for the last update interval:
         Rate(bps) = (Frame_Count * 7 packets/frame 188 bytes/packet * 8 bits/byte)
                     / Update_Interval

         This value is set by the APEX at startup and is constant.
        "
::= { apexGbeStatusFrameCounterGeneral 1 }


-- ------------------------------------------------------------------------------
--
-- apexGbeStatusFrameCounterTable
--

apexGbeStatusFrameCounterTable OBJECT-TYPE
    SYNTAX SEQUENCE OF ApexGbeStatusFrameCounterEntry
    MAX-ACCESS not-accessible
    STATUS current
    DESCRIPTION
        "Table of Gigabit Ethernet Frame Counter Statistics. Periodic
         statistics in this table are updated by the time interval
         specified by apexGbeFrameCounterUpdateInterval."
::= { apexGbeStatusFrameCounter 2 }

apexGbeStatusFrameCounterEntry OBJECT-TYPE
    SYNTAX ApexGbeStatusFrameCounterEntry
    MAX-ACCESS not-accessible
    STATUS current
    DESCRIPTION
        "Gigabit Ethernet Interface Frame Counter Table Entry."
    INDEX { apexGbeFrameCounterGbeInterfaceNum }
::= { apexGbeStatusFrameCounterTable 1 }

ApexGbeStatusFrameCounterEntry ::= SEQUENCE
    {
     apexGbeFrameCounterGbeInterfaceNum Integer32,
     apexGbeTotalRxSinglecastFrames     Counter32,
     apexGbeTotalRxMulticastFrames      Counter32,
     apexGbeTotalRxBroadcastFrames      Counter32,
     apexGbeTotalRxErrorFrames          Counter32,
     apexGbeTotalRxFrames               Counter32,
     apexGbeRxSinglecastFrames          Counter32,
     apexGbeRxMulticastFrames           Counter32,
     apexGbeRxBroadcastFrames           Counter32,
     apexGbeRxErrorFrames               Counter32,
     apexGbeRxFrames                    Counter32,
     apexGbeTotalTxGoodFrames           Counter32,
     apexGbeTotalTxErrorFrames          Counter32,
     apexGbeTxGoodFrames                Counter32,
     apexGbeTxErrorFrames               Counter32,
     apexGbeRxStreamRate                Integer32
    }

apexGbeFrameCounterGbeInterfaceNum OBJECT-TYPE
    SYNTAX Integer32(1..12)
    MAX-ACCESS not-accessible
    STATUS current
    DESCRIPTION
        "The index of the Gigabit Ethernet Frame Counter Table.
         Represents the Gigabit Ethernet interface number."
::= { apexGbeStatusFrameCounterEntry 1 }

apexGbeTotalRxSinglecastFrames OBJECT-TYPE
    SYNTAX Counter32
    MAX-ACCESS read-only
    STATUS current
    DESCRIPTION
        "Total number of singlecast Ethernet frames received since last reset.
         Reset using apexGbeConfFrameCounterTableResetAll or apexGbeFrameCounterReset."
::= { apexGbeStatusFrameCounterEntry 2 }

apexGbeTotalRxMulticastFrames OBJECT-TYPE
    SYNTAX Counter32
    MAX-ACCESS read-only
    STATUS current
    DESCRIPTION
        "Total number of multicast Ethernet frames received since last reset.
         Reset using apexGbeConfFrameCounterTableResetAll or apexGbeFrameCounterReset."
::= { apexGbeStatusFrameCounterEntry 3 }

apexGbeTotalRxBroadcastFrames OBJECT-TYPE
    SYNTAX Counter32
    MAX-ACCESS read-only
    STATUS current
    DESCRIPTION
        "Total number of broadcast Ethernet frames received since last reset.
         Reset using apexGbeConfFrameCounterTableResetAll or apexGbeFrameCounterReset."
::= { apexGbeStatusFrameCounterEntry 4 }

apexGbeTotalRxErrorFrames OBJECT-TYPE
    SYNTAX Counter32
    MAX-ACCESS read-only
    STATUS current
    DESCRIPTION
        "Total number of bad Ethernet frames received since last reset.
         Reset using apexGbeConfFrameCounterTableResetAll or apexGbeFrameCounterReset."
::= { apexGbeStatusFrameCounterEntry 5 }

apexGbeTotalRxFrames OBJECT-TYPE
    SYNTAX Counter32
    MAX-ACCESS read-only
    STATUS current
    DESCRIPTION
        "Total number of Ethernet frames received since last reset.
         This is the sum of apexGbeTotalRxSinglecastFrames, apexGbeTotalRxMulticastFrames,
         apexGbeTotalRxBroadcastFrames, and apexGbeTotalRxErrorFrames.
         Reset using apexGbeConfFrameCounterTableResetAll or apexGbeFrameCounterReset."
::= { apexGbeStatusFrameCounterEntry 6 }

apexGbeRxSinglecastFrames OBJECT-TYPE
    SYNTAX Counter32
    MAX-ACCESS read-only
    STATUS current
    DESCRIPTION
        "Number of singlecast Ethernet frames received during last
         status checking interval."
::= { apexGbeStatusFrameCounterEntry 7 }

apexGbeRxMulticastFrames OBJECT-TYPE
    SYNTAX Counter32
    MAX-ACCESS read-only
    STATUS current
    DESCRIPTION
        "Number of multicast Ethernet frames received during
         last status checking interval."
::= { apexGbeStatusFrameCounterEntry 8 }

apexGbeRxBroadcastFrames OBJECT-TYPE
    SYNTAX Counter32
    MAX-ACCESS read-only
    STATUS current
    DESCRIPTION
        "Number of broadcast Ethernet frames received during last status
         checking interval."
::= { apexGbeStatusFrameCounterEntry 9 }

apexGbeRxErrorFrames OBJECT-TYPE
    SYNTAX Counter32
    MAX-ACCESS read-only
    STATUS current
    DESCRIPTION
        "Number of bad Ethernet frames received during
         last status checking interval. "
::= { apexGbeStatusFrameCounterEntry 10 }

apexGbeRxFrames OBJECT-TYPE
    SYNTAX Counter32
    MAX-ACCESS read-only
    STATUS current
    DESCRIPTION
        "Number of Ethernet frames received during last
         status checking interval.
         This is the sum of apexGbeRxSinglecastFrames, apexGbeRxMulticastFrames,
         apexGbeRxBroadcastFrames, and apexGbeRxErrorFrames."
::= { apexGbeStatusFrameCounterEntry 11 }

apexGbeTotalTxGoodFrames OBJECT-TYPE
    SYNTAX Counter32
    MAX-ACCESS read-only
    STATUS current
    DESCRIPTION
        "Total number of good Ethernet frames (singlecast, multicast, and broadcast)
         transmitted since last reset.
         Reset using apexGbeConfFrameCounterTableResetAll or apexGbeFrameCounterReset."
::= { apexGbeStatusFrameCounterEntry 12 }

apexGbeTotalTxErrorFrames OBJECT-TYPE
    SYNTAX Counter32
    MAX-ACCESS read-only
    STATUS current
    DESCRIPTION
        "Total number of bad Ethernet frames transmitted since last reset.
         Reset using apexGbeConfFrameCounterTableResetAll or apexGbeFrameCounterReset."
::= { apexGbeStatusFrameCounterEntry 13 }

apexGbeTxGoodFrames OBJECT-TYPE
    SYNTAX Counter32
    MAX-ACCESS read-only
    STATUS current
    DESCRIPTION
        "Number of good Ethernet frames (singlecast, multicast, and broadcast)
         transmitted during last status checking interval."
::= { apexGbeStatusFrameCounterEntry 14 }

apexGbeTxErrorFrames OBJECT-TYPE
    SYNTAX Counter32
    MAX-ACCESS read-only
    STATUS current
    DESCRIPTION
        "Number of bad Ethernet frames transmitted during last
         status checking interval."
::= { apexGbeStatusFrameCounterEntry 15 }

apexGbeRxStreamRate OBJECT-TYPE
    SYNTAX Integer32
    MAX-ACCESS read-only
    STATUS current
    DESCRIPTION
        "Input stream rate in Kbps for each interface port. This is the input
         rate of all Ethernet packets received. Rate is updated during every
         status checking interval."
::= { apexGbeStatusFrameCounterEntry 16 }


-- ------------------------------------------------------------------------------
--
-- apexGbeFrameBufferStats
--
-- apexGbeFrameBufferStatsGeneral
--

-- none


-- ------------------------------------------------------------------------------
--
-- apexGbeFrameBufferStatsTable
--

apexGbeFrameBufferStatsTable OBJECT-TYPE
    SYNTAX SEQUENCE OF ApexGbeFrameBufferStatsEntry
    MAX-ACCESS not-accessible
    STATUS current
    DESCRIPTION
        "Table of Gigabit Ethernet Frame Buffer Statistics."
::= { apexGbeFrameBufferStats 2 }

apexGbeFrameBufferStatsEntry OBJECT-TYPE
    SYNTAX ApexGbeFrameBufferStatsEntry
    MAX-ACCESS not-accessible
    STATUS current
    DESCRIPTION
        "Gigabit Ethernet Frame Buffer Statistics Table Entry."
    INDEX { apexGbeFrameBufferBladeNum }
::= { apexGbeFrameBufferStatsTable 1 }

ApexGbeFrameBufferStatsEntry ::= SEQUENCE
    {
     apexGbeFrameBufferBladeNum        Integer32,
     apexGbeFrameBufferResetLevelLimit Integer32,
     apexGbeFrameBufferHighMsLevel     Integer32,
     apexGbeFrameBufferHighPercentFull Integer32,
     apexGbeFrameBufferLowMsLevel      Integer32,
     apexGbeFrameBufferLowPercentFull  Integer32
    }

apexGbeFrameBufferBladeNum OBJECT-TYPE
    SYNTAX Integer32(1..8)
    MAX-ACCESS not-accessible
    STATUS current
    DESCRIPTION
        "Blade number."
::= { apexGbeFrameBufferStatsEntry 1 }

apexGbeFrameBufferResetLevelLimit OBJECT-TYPE
    SYNTAX Integer32
    MAX-ACCESS read-only
    STATUS current
    DESCRIPTION
        "The point at which the GigE frame buffer will be reset, in milliseconds.
         This level is fixed at 650 milliseconds.
        "
::= { apexGbeFrameBufferStatsEntry 2 }

apexGbeFrameBufferHighMsLevel OBJECT-TYPE
    SYNTAX Integer32
    MAX-ACCESS read-only
    STATUS current
    DESCRIPTION
        "Highest current Gigabit Ethernet Frame Buffer level in milliseconds."
::= { apexGbeFrameBufferStatsEntry 3 }

apexGbeFrameBufferHighPercentFull OBJECT-TYPE
    SYNTAX Integer32 (0..100)
    MAX-ACCESS read-only
    STATUS current
    DESCRIPTION
        "Highest current Gigabit Ethernet Frame Buffer fullness as a percentage of
         the reset level. This percentage is calculated using the reset level limit 
         (apexGbeFrameBufferResetLevelLimit) and the actual input data rate."
::= { apexGbeFrameBufferStatsEntry 4 }

apexGbeFrameBufferLowMsLevel OBJECT-TYPE
    SYNTAX Integer32
    MAX-ACCESS read-only
    STATUS current
    DESCRIPTION
        "Lowest current Gigabit Ethernet Frame Buffer level in milliseconds."
::= { apexGbeFrameBufferStatsEntry 5 }

apexGbeFrameBufferLowPercentFull OBJECT-TYPE
    SYNTAX Integer32 (0..100)
    MAX-ACCESS read-only
    STATUS current
    DESCRIPTION
        "Lowest current Gigabit Ethernet Frame Buffer fullness as a percentage of
         the reset level. This percentage is calculated using the reset level limit 
         (apexGbeFrameBufferResetLevelLimit) and the actual input data rate."
::= { apexGbeFrameBufferStatsEntry 6 }


-- ------------------------------------------------------------------------------
--
-- apexGbeStatusInputTransportStream
--
-- apexGbeStatusInputTsGeneral
--

apexGbeStatusInputTsUpdateInterval OBJECT-TYPE
    SYNTAX Integer32
    MAX-ACCESS read-only
    STATUS current
    DESCRIPTION
        "Time in seconds between Gigabit Ethernet Input Transport Stream Packet
         Count updates.  The count during this time is defined as one sample.

         This time applies to packet counts contained in
         apexGbeStatusInputTsTable.

         To compute rate from packet count for the last update interval:
         Rate(bps) = (Packet_Count * 188 bytes/packet * 8 bits/byte) / Update_Interval

         This value is set by the APEX at startup and is constant.
        "
::= { apexGbeStatusInputTsGeneral 1 }


-- ------------------------------------------------------------------------------
--
-- apexGbeStatusInputTsTable
--

apexGbeStatusInputTsTable OBJECT-TYPE
    SYNTAX SEQUENCE OF ApexGbeStatusInputTsEntry
    MAX-ACCESS not-accessible
    STATUS current
    DESCRIPTION
        "Table of Gigabit Ethernet Input Transport Stream status.

         A row in this table corresponds to the same index row in
         apexGbeStatusInputTsStatTable and apexGbeStatusInputTsErrorTable.

         Packet Counts are updated every apexGbeStatusInputTsUpdateInterval.
         The count during a apexGbeStatusInputTsUpdateInterval is a sample.
         The samples are accumulated into a set of rolling statistics that cover
         a maximum of a 15 minute sampling time period.  The sampling period is
         the amount of time over which the data in the corresponding row has been
         collected.  When the sampling period reaches 15 minutes, old data is
         removed from the accumulated statistics and new data is rolled in.  In
         this way, the average, minimum, and peak rates for the sampling period
         are maintained.
        "
::= { apexGbeStatusInputTransportStream 2 }

apexGbeStatusInputTsEntry OBJECT-TYPE
    SYNTAX ApexGbeStatusInputTsEntry
    MAX-ACCESS not-accessible
    STATUS current
    DESCRIPTION
        "Gigabit Ethernet Input Transport Stream Status Table Entry."
    INDEX { apexGbeStatInTsBladeNum, apexGbeStatInTsInputTsNum }
::= { apexGbeStatusInputTsTable 1 }

ApexGbeStatusInputTsEntry ::= SEQUENCE
    {
     apexGbeStatInTsBladeNum            Integer32,
     apexGbeStatInTsInputTsNum          Integer32,
     apexGbeStatInTsSamplingPeriod      Integer32,
     apexGbeStatInTsCurDataCount        Counter32,
     apexGbeStatInTsMinDataCount        Counter32,
     apexGbeStatInTsPeakDataCount       Counter32,
     apexGbeStatInTsCurStreamCount      Counter32,
     apexGbeStatInTsMinStreamCount      Counter32,
     apexGbeStatInTsPeakStreamCount     Counter32     
    }

apexGbeStatInTsBladeNum OBJECT-TYPE
    SYNTAX Integer32(1..8)
    MAX-ACCESS not-accessible
    STATUS current
    DESCRIPTION
        "Blade number.

         A row in this table corresponds to the same index row in
         apexGbeStatusInputTsStatTable, apexGbeStatusInputTsErrorTable, and
         apexGbeStatusInputTsBufferLevelTable.
        "
::= { apexGbeStatusInputTsEntry 1 }

apexGbeStatInTsInputTsNum OBJECT-TYPE
    SYNTAX Integer32(1..1920)
    MAX-ACCESS not-accessible
    STATUS current
    DESCRIPTION
        "Input Transport Stream number.

         A row in this table corresponds to the same index row in
         apexGbeStatusInputTsStatTable, apexGbeStatusInputTsErrorTable, and
         apexGbeStatusInputTsBufferLevelTable.
        "
::= { apexGbeStatusInputTsEntry 2 }

apexGbeStatInTsSamplingPeriod OBJECT-TYPE
    SYNTAX Integer32(0..900)
    MAX-ACCESS read-only
    STATUS current
    DESCRIPTION
        "The total time, in seconds, over which the packet counts statistics
         in this row have been collected.

         Refer to the description of apexGbeStatusInputTsTable for an
         explanation of packet counting.  Refer to the description of
         apexGbeStatusInputTsUpdateInterval for an explanation of update
         interval and computing rates.
        "
::= { apexGbeStatusInputTsEntry 3 }

apexGbeStatInTsCurDataCount OBJECT-TYPE
    SYNTAX Counter32
    MAX-ACCESS read-only
    STATUS current
    DESCRIPTION
        "The Data Packet Count of the most recent sample for the 
         stream in use.

         Refer to the description of apexGbeStatusInputTsTable for an
         explanation of packet counting.  Refer to the description of
         apexGbeStatusInputTsUpdateInterval for an explanation of update
         interval and computing rates.
        "
::= { apexGbeStatusInputTsEntry 4 }

apexGbeStatInTsMinDataCount OBJECT-TYPE
    SYNTAX Counter32
    MAX-ACCESS read-only
    STATUS current
    DESCRIPTION
        "The Minimum Data Packet Count sample during
         apexGbeStatInTsSamplingPeriod for the stream in use.

         Refer to the description of apexGbeStatusInputTsTable for an
         explanation of packet counting.  Refer to the description of
         apexGbeStatusInputTsUpdateInterval for an explanation of update
         interval and computing rates.
        "
::= { apexGbeStatusInputTsEntry 5 }

apexGbeStatInTsPeakDataCount OBJECT-TYPE
    SYNTAX Counter32
    MAX-ACCESS read-only
    STATUS current
    DESCRIPTION
        "The Peak Data Packet Count sample during
         apexGbeStatInTsSamplingPeriod for the stream in use.

         Refer to the description of apexGbeStatusInputTsTable for an
         explanation of packet counting.  Refer to the description of
         apexGbeStatusInputTsUpdateInterval for an explanation of update
         interval and computing rates.
        "
::= { apexGbeStatusInputTsEntry 6 }

apexGbeStatInTsCurStreamCount OBJECT-TYPE
    SYNTAX Counter32
    MAX-ACCESS read-only
    STATUS current
    DESCRIPTION
        "The Transport Stream Packet Count of the most recent sample for the 
         stream in use.

         Refer to the description of apexGbeStatusInputTsTable for an
         explanation of packet counting.  Refer to the description of
         apexGbeStatusInputTsUpdateInterval for an explanation of update
         interval and computing rates.
        "
::= { apexGbeStatusInputTsEntry 7 }

apexGbeStatInTsMinStreamCount OBJECT-TYPE
    SYNTAX Counter32
    MAX-ACCESS read-only
    STATUS current
    DESCRIPTION
        "The Minimum Transport Stream Packet Count sample during
         apexGbeStatInTsSamplingPeriod for the stream in use.

         Refer to the description of apexGbeStatusInputTsTable for an
         explanation of packet counting.  Refer to the description of
         apexGbeStatusInputTsUpdateInterval for an explanation of update
         interval and computing rates.
        "
::= { apexGbeStatusInputTsEntry 8 }

apexGbeStatInTsPeakStreamCount OBJECT-TYPE
    SYNTAX Counter32
    MAX-ACCESS read-only
    STATUS current
    DESCRIPTION
        "The Peak Transport Stream Packet Count sample during
         apexGbeStatInTsSamplingPeriod for the stream in use.

         Refer to the description of apexGbeStatusInputTsTable for an
         explanation of packet counting.  Refer to the description of
         apexGbeStatusInputTsUpdateInterval for an explanation of update
         interval and computing rates.
        "
::= { apexGbeStatusInputTsEntry 9 }


-- ------------------------------------------------------------------------------
--
-- apexGbeStatusInputTsErrorTable
--

apexGbeStatusInputTsErrorTable OBJECT-TYPE
    SYNTAX SEQUENCE OF ApexGbeStatusInputTsErrorEntry
    MAX-ACCESS not-accessible
    STATUS current
    DESCRIPTION
        "Table of Gigabit Ethernet Input Transport Stream Error status.

         A row in this table corresponds to the same index row in
         apexGbeStatusInputTsStatTable, apexGbeStatusInputTsTable, and
         apexGbeStatusInputTsBufferLevelTable.
        "
::= { apexGbeStatusInputTransportStream 3 }

apexGbeStatusInputTsErrorEntry OBJECT-TYPE
    SYNTAX ApexGbeStatusInputTsErrorEntry
    MAX-ACCESS not-accessible
    STATUS current
    DESCRIPTION
        "Gigabit Ethernet Input Transport Stream Error Status Table Entry."
    INDEX { apexGbeStatInTsErrorBladeNum, apexGbeStatInTsErrorInputTsNum }
::= { apexGbeStatusInputTsErrorTable 1 }

ApexGbeStatusInputTsErrorEntry ::= SEQUENCE
    {
     apexGbeStatInTsErrorBladeNum        Integer32,
     apexGbeStatInTsErrorInputTsNum      Integer32,
     apexGbeStatInTsPriErrorSummary      INTEGER,
     apexGbeStatInTsPriHighBitRateError  INTEGER,
     apexGbeStatInTsPriFailJoinMulticast INTEGER,
     apexGbeStatInTsPriLossOfInputStream INTEGER,
     apexGbeStatInTsRedundFailoverError  INTEGER,
     apexGbeStatInTsSecErrorSummary      INTEGER,
     apexGbeStatInTsSecHighBitRateError  INTEGER,
     apexGbeStatInTsSecFailJoinMulticast INTEGER,
     apexGbeStatInTsSecLossOfInputStream INTEGER
    }

apexGbeStatInTsErrorBladeNum OBJECT-TYPE
    SYNTAX Integer32(1..8)
    MAX-ACCESS not-accessible
    STATUS current
    DESCRIPTION
        "Blade number.

         A row in this table corresponds to the same index row in
         apexGbeStatusInputTsStatTable, apexGbeStatusInputTsTable, and
         apexGbeStatusInputTsBufferLevelTable.
        "
::= { apexGbeStatusInputTsErrorEntry 1 }

apexGbeStatInTsErrorInputTsNum OBJECT-TYPE
    SYNTAX Integer32(1..1920)
    MAX-ACCESS not-accessible
    STATUS current
    DESCRIPTION
        "The Gigabit Ethernet Input Transport Stream Error Status table index.

         A row in this table corresponds to the same index row in
         apexGbeStatusInputTsStatTable, apexGbeStatusInputTsTable, and
         apexGbeStatusInputTsBufferLevelTable.
        "
::= { apexGbeStatusInputTsErrorEntry 2 }

apexGbeStatInTsPriErrorSummary OBJECT-TYPE
    SYNTAX INTEGER
        {
         notApplicable (0),
         ok    (1),
         error (2)
        }
    MAX-ACCESS read-only
    STATUS current
    DESCRIPTION
        "The current highest error of the following errors for the primary
         input transport stream:
            apexGbeStatInTsPriHighBitRateError
            apexGbeStatInTsPriFailJoinMulticast
            apexGbeStatInTsPriLossOfInputStream
            apexGbeStatInTsRedundFailoverError
        "
::= { apexGbeStatusInputTsErrorEntry 3 }

apexGbeStatInTsPriHighBitRateError OBJECT-TYPE
    SYNTAX INTEGER
        {
         notApplicable (0),
         ok    (1),
         error (2)
        }
    MAX-ACCESS read-only
    STATUS current
    DESCRIPTION
        "The current high bit rate state for the primary input stream.
         Ok indicates no errors or not checking high bit rate. Error indicates
         primary input stream is above the high bit rate specified.
        "
::= { apexGbeStatusInputTsErrorEntry 4 }

apexGbeStatInTsPriFailJoinMulticast OBJECT-TYPE
    SYNTAX INTEGER
        {
         notApplicable (0),
         ok    (1),
         error (2)
        }
    MAX-ACCESS read-only
    STATUS current
    DESCRIPTION
        "The current failure to join multicast group state for the primary 
         input stream. Ok indicates no errors or not checking failure to join
         multicast group. Error indicates primary input has failed to
         join the multicast group.
        "
::= { apexGbeStatusInputTsErrorEntry 5 }

apexGbeStatInTsPriLossOfInputStream OBJECT-TYPE
    SYNTAX INTEGER
        {
         notApplicable (0),
         ok    (1),
         error (2)
        }
    MAX-ACCESS read-only
    STATUS current
    DESCRIPTION
        "The current loss of input stream state for the primary 
         input stream. Ok indicates no errors or not checking loss of input 
         stream.
         Error indicates primary input stream has been lost.
        "
::= { apexGbeStatusInputTsErrorEntry 6 }

apexGbeStatInTsRedundFailoverError OBJECT-TYPE
    SYNTAX INTEGER
        {
         notApplicable (0),
         ok    (1),
         error (2)
        }
    MAX-ACCESS read-only
    STATUS current
    DESCRIPTION
        "The current fail over state for a redundancy pair.
         Ok indicates no errors or input stream is not part of a redundant pair.
         Error indicates primary input stream is no longer in use and the APEX
         has fallen over to use the secondary input stream.
        "
::= { apexGbeStatusInputTsErrorEntry 7 }

apexGbeStatInTsSecErrorSummary OBJECT-TYPE
    SYNTAX INTEGER
        {
         notApplicable (0),
         ok    (1),
         error (2)
        }
    MAX-ACCESS read-only
    STATUS current
    DESCRIPTION
        "The current highest error state of the following for the secondary
         input transport stream:
            apexGbeStatInTsSecHighBitRateError
            apexGbeStatInTsSecFailJoinMulticast
            apexGbeStatInTsSecLossOfInputStream
        "
::= { apexGbeStatusInputTsErrorEntry 8 }

apexGbeStatInTsSecHighBitRateError OBJECT-TYPE
    SYNTAX INTEGER
        {
         notApplicable (0),
         ok    (1),
         error (2)
        }
    MAX-ACCESS read-only
    STATUS current
    DESCRIPTION
        "The current high bit rate state for the secondary input stream.
         Ok indicates no errors or not checking high bit rate. Error indicates
         secondary input stream is above the high bit rate specified.
        "
::= { apexGbeStatusInputTsErrorEntry 9 }

apexGbeStatInTsSecFailJoinMulticast OBJECT-TYPE
    SYNTAX INTEGER
        {
         notApplicable (0),
         ok    (1),
         error (2)
        }
    MAX-ACCESS read-only
    STATUS current
    DESCRIPTION
        "The current failure to join multicast group state for the secondary 
         input stream. Ok indicates no errors or not checking failure to join
         multicast group. Error indicates secondary input has failed to
         join the multicast group.
        "
::= { apexGbeStatusInputTsErrorEntry 10 }

apexGbeStatInTsSecLossOfInputStream OBJECT-TYPE
    SYNTAX INTEGER
        {
         notApplicable (0),
         ok    (1),
         error (2)
        }
    MAX-ACCESS read-only
    STATUS current
    DESCRIPTION
        "The current loss of input stream state for the secondary 
         input stream. Ok indicates no errors or not checking loss of input 
         stream.
         Error indicates secondary input stream has been lost.
        "
::= { apexGbeStatusInputTsErrorEntry 11 }


-- ------------------------------------------------------------------------------
--
-- apexGbeStatusInputTsBufferLevelTable
--

apexGbeStatusInputTsBufferLevelTable OBJECT-TYPE
    SYNTAX SEQUENCE OF ApexGbeStatusInputTsBufferLevelEntry
    MAX-ACCESS not-accessible
    STATUS current
    DESCRIPTION
        "Table of Gigabit Ethernet Input Transport Stream Buffer Level
         status.

         A row in this table corresponds to the same index row in
         apexGbeStatusInputTsStatTable, apexGbeStatusInputTsTable, and
         apexGbeStatusInputTsErrorTable.
        "
::= { apexGbeStatusInputTransportStream 4 }

apexGbeStatusInputTsBufferLevelEntry OBJECT-TYPE
    SYNTAX ApexGbeStatusInputTsBufferLevelEntry
    MAX-ACCESS not-accessible
    STATUS current
    DESCRIPTION
        "Gigabit Ethernet Input Transport Stream Buffer Level Table Entry."
    INDEX { apexGbeStatInTsBufferLevelBladeNum, apexGbeStatInTsBufferLevelTsNum }
::= { apexGbeStatusInputTsBufferLevelTable 1 }

ApexGbeStatusInputTsBufferLevelEntry ::= SEQUENCE
    {
     apexGbeStatInTsBufferLevelBladeNum        Integer32,     
     apexGbeStatInTsBufferLevelTsNum           Integer32,     
     apexGbeStatInTsBufferLevelInputInfo       DisplayString, 
     apexGbeStatInTsBufferLevelPriSecIndicator INTEGER,
     apexGbeStatInTsBufferLevelCur             Integer32,
     apexGbeStatInTsBufferLevelMin             Integer32,
     apexGbeStatInTsBufferLevelMax             Integer32,
     apexGbeStatInTsBufferLevelResetCount      Integer32
    }

apexGbeStatInTsBufferLevelBladeNum OBJECT-TYPE
    SYNTAX Integer32(1..8)
    MAX-ACCESS not-accessible
    STATUS current
    DESCRIPTION
        "Blade number.

         A row in this table corresponds to the same index row in
         apexGbeStatusInputTsStatTable and apexGbeStatusInputTsTable, and
         apexGbeStatusInputTsErrorTable.
        "
::= { apexGbeStatusInputTsBufferLevelEntry 1 }

apexGbeStatInTsBufferLevelTsNum OBJECT-TYPE
    SYNTAX Integer32(1..1920)
    MAX-ACCESS not-accessible
    STATUS current
    DESCRIPTION
        "Input Transport Stream Buffer Level table index.
        
         A row in this table corresponds to the same index row in
         apexGbeStatusInputTsStatTable and apexGbeStatusInputTsTable, and
         apexGbeStatusInputTsErrorTable.
        "
::= { apexGbeStatusInputTsBufferLevelEntry 2 }

apexGbeStatInTsBufferLevelInputInfo OBJECT-TYPE
    SYNTAX DisplayString
    MAX-ACCESS read-only
    STATUS current
    DESCRIPTION
        "Comma-separated string showing: Input Interface, UDP port, 
         Multicast IP, and Source IP for this input."
::= { apexGbeStatusInputTsBufferLevelEntry 3 }

apexGbeStatInTsBufferLevelPriSecIndicator OBJECT-TYPE
    SYNTAX INTEGER
        {
         notApplicable (0),
         primary       (1),
         secondary     (2)
        }
    MAX-ACCESS read-only
    STATUS current
    DESCRIPTION
        "This value is used to indicate whether the buffer
         level values pertain to the primary or secondary
         Gigabit Ethernet inputs.
        "
::= { apexGbeStatusInputTsBufferLevelEntry 4 }

apexGbeStatInTsBufferLevelCur OBJECT-TYPE
    SYNTAX Integer32
    MAX-ACCESS read-only
    STATUS current
    DESCRIPTION
        "The current Gigabit Ethernet frame buffer level (in milliseconds).
        "
::= { apexGbeStatusInputTsBufferLevelEntry 5 }

apexGbeStatInTsBufferLevelMin OBJECT-TYPE
    SYNTAX Integer32
    MAX-ACCESS read-only
    STATUS current
    DESCRIPTION
        "The minimum Gigabit Ethernet frame buffer level (in milliseconds)
         recorded for the hour for this input transport stream.
        "
::= { apexGbeStatusInputTsBufferLevelEntry 6 }

apexGbeStatInTsBufferLevelMax OBJECT-TYPE
    SYNTAX Integer32
    MAX-ACCESS read-only
    STATUS current
    DESCRIPTION
        "The maximum Gigabit Ethernet frame buffer level (in milliseconds)
         recorded for the hour for this input transport stream.
        "
::= { apexGbeStatusInputTsBufferLevelEntry 7 }

apexGbeStatInTsBufferLevelResetCount OBJECT-TYPE
    SYNTAX Integer32
    MAX-ACCESS read-only
    STATUS current
    DESCRIPTION
        "A count of the total number of resets for each input stream.
        "
::= { apexGbeStatusInputTsBufferLevelEntry 8 }


-- ------------------------------------------------------------------------------
--
-- apexGbeStatusInputTsStatTable
--

apexGbeStatusInputTsStatTable OBJECT-TYPE
    SYNTAX SEQUENCE OF ApexGbeStatusInputTsStatEntry
    MAX-ACCESS not-accessible
    STATUS current
    DESCRIPTION
        "Table of Input Transport Stream Status data. For each input stream
         in use, an entry in this row will be utilized. This table will indicate
         the input stream in use by type, interface, UDP, destination IP, and Source
         IP address. This table will also indicate if the input stream is a Primary
         or Secondary input stream.

         Each row contains an entry for Primary and Secondary
         information along with the one currently in use.
        "
::= { apexGbeStatusInputTransportStream 5 }

apexGbeStatusInputTsStatEntry OBJECT-TYPE
    SYNTAX ApexGbeStatusInputTsStatEntry
    MAX-ACCESS not-accessible
    STATUS current
    DESCRIPTION
        "Input Transport Stream Status Table Entry."
    INDEX { apexGbeStatusInputTsStatBladeNum, apexGbeStatusInputTsStatTsNum }
::= { apexGbeStatusInputTsStatTable 1 }

ApexGbeStatusInputTsStatEntry ::= SEQUENCE
    {
     apexGbeStatusInputTsStatBladeNum              Integer32,
     apexGbeStatusInputTsStatTsNum                 Integer32,
     apexGbeStatusInputTsStatStreamInUse           INTEGER,
     apexGbeStatusInputTsStatRoutingType           INTEGER,
     apexGbeStatusInputTsStatPriState              InputTsStateTYPE,
     apexGbeStatusInputTsStatPriInputInterface     Integer32,
     apexGbeStatusInputTsStatPriInputUdp           Integer32,
     apexGbeStatusInputTsStatPriInputDestinationIp IpAddress,
     apexGbeStatusInputTsStatPriInputSourceIp      IpAddress,
     apexGbeStatusInputTsStatSecState              InputTsStateTYPE,
     apexGbeStatusInputTsStatSecInputInterface     Integer32,
     apexGbeStatusInputTsStatSecInputUdp           Integer32,
     apexGbeStatusInputTsStatSecInputDestinationIp IpAddress,
     apexGbeStatusInputTsStatSecInputSourceIp      IpAddress
    }

apexGbeStatusInputTsStatBladeNum OBJECT-TYPE
    SYNTAX Integer32(1..8)
    MAX-ACCESS not-accessible
    STATUS current
    DESCRIPTION
        "Blade number."
::= { apexGbeStatusInputTsStatEntry 1 }

apexGbeStatusInputTsStatTsNum OBJECT-TYPE
    SYNTAX Integer32(1..1920)
    MAX-ACCESS not-accessible
    STATUS current
    DESCRIPTION
        "Input Transport Stream number."
::= { apexGbeStatusInputTsStatEntry 2 }

apexGbeStatusInputTsStatStreamInUse OBJECT-TYPE
    SYNTAX INTEGER
        {
         notApplicable (0),
         primary       (1),
         secondary     (2)
        }
    MAX-ACCESS read-only
    STATUS current
    DESCRIPTION
        "Indicates whether the primary or secondary is in use. Zero
         indicates this row is not in use.
        "
::= { apexGbeStatusInputTsStatEntry 3 }

apexGbeStatusInputTsStatRoutingType OBJECT-TYPE
    SYNTAX INTEGER
        {
         notApplicable (0),
         session       (1),
         manual        (2),
         udpMapping    (3)
        }
    MAX-ACCESS read-only
    STATUS current
    DESCRIPTION
        "Routing Type of both primary and secondary inputs.

         'session' - applies to SDV session routes (RPC, RTSP).
         'manual'  - applies to all manual routes (Manual Routing, PID
                     Mapping, and stream pass through).
         'udpMapping - applies to UDP Port Mapping routes.
        "
::= { apexGbeStatusInputTsStatEntry 4 }

apexGbeStatusInputTsStatPriState OBJECT-TYPE
    SYNTAX InputTsStateTYPE
    MAX-ACCESS read-only
    STATUS current
    DESCRIPTION
        "The current state of the primary Gigabit Ethernet Input TS.
         States are:
            closed              (0) - Input TS is closed or table row is not in use.
            openedInUse         (1) - Input TS is opened and in use.
        "
::= { apexGbeStatusInputTsStatEntry 5 }

apexGbeStatusInputTsStatPriInputInterface OBJECT-TYPE
    SYNTAX Integer32
    MAX-ACCESS read-only
    STATUS current
    DESCRIPTION
        "Interface number of the primary input interface.
        "
::= { apexGbeStatusInputTsStatEntry 6 }

apexGbeStatusInputTsStatPriInputUdp OBJECT-TYPE
SYNTAX Integer32
    MAX-ACCESS read-only
    STATUS current
    DESCRIPTION
        "Input UDP Port for primary input.
        "
::= { apexGbeStatusInputTsStatEntry 7 }

apexGbeStatusInputTsStatPriInputDestinationIp OBJECT-TYPE
    SYNTAX IpAddress
    MAX-ACCESS read-only
    STATUS current
    DESCRIPTION
        "The Destination receive IP address for primary input.
         This could be a singlecast or multicast IP address. 
        "
::= { apexGbeStatusInputTsStatEntry 8 }

apexGbeStatusInputTsStatPriInputSourceIp OBJECT-TYPE
    SYNTAX IpAddress
    MAX-ACCESS read-only
    STATUS current
    DESCRIPTION
        "This is the IGMP v3 Source IP address of the source device for the primary input.
        "
::= { apexGbeStatusInputTsStatEntry 9 }

apexGbeStatusInputTsStatSecState OBJECT-TYPE
    SYNTAX InputTsStateTYPE
    MAX-ACCESS read-only
    STATUS current
    DESCRIPTION
        "The current state of the secondary Gigabit Ethernet Input TS.
         States are:
            closed              (0) - Input TS is closed or table row is not in use.
            openedInUse         (1) - Input TS is opened and in use.
        "
::= { apexGbeStatusInputTsStatEntry 10 }

apexGbeStatusInputTsStatSecInputInterface OBJECT-TYPE
    SYNTAX Integer32
    MAX-ACCESS read-only
    STATUS current
    DESCRIPTION
        "Interface number of the secondary input interface.
        "
::= { apexGbeStatusInputTsStatEntry 11 }

apexGbeStatusInputTsStatSecInputUdp OBJECT-TYPE
SYNTAX Integer32
    MAX-ACCESS read-only
    STATUS current
    DESCRIPTION
        "Input UDP Port for secondary input.
        "
::= { apexGbeStatusInputTsStatEntry 12 }

apexGbeStatusInputTsStatSecInputDestinationIp OBJECT-TYPE
    SYNTAX IpAddress
    MAX-ACCESS read-only
    STATUS current
    DESCRIPTION
        "The Destination receive IP address for secondary input.
         This could be a singlecast or multicast IP address. 
        "
::= { apexGbeStatusInputTsStatEntry 13 }

apexGbeStatusInputTsStatSecInputSourceIp OBJECT-TYPE
    SYNTAX IpAddress
    MAX-ACCESS read-only
    STATUS current
    DESCRIPTION
        "This is the IGMP v3 Source IP address of the source device for the secondary input.
        "
::= { apexGbeStatusInputTsStatEntry 14 }


-- ------------------------------------------------------------------------------
--
-- apexGbeStatusQamInputStatTable
--

apexGbeStatusQamInputStatTable OBJECT-TYPE
    SYNTAX SEQUENCE OF ApexGbeStatusQamInputStatEntry
    MAX-ACCESS not-accessible
    STATUS current
    DESCRIPTION
        "Table of Input Transport Stream Status data per QAM blade. For each blade
         in use, an entry in this row will be utilized. This table will indicate
         current and total stream and data counts for the blade.         
        "
::= { apexGbeStatusInputTransportStream 6 }

apexGbeStatusQamInputStatEntry OBJECT-TYPE
    SYNTAX ApexGbeStatusQamInputStatEntry
    MAX-ACCESS not-accessible
    STATUS current
    DESCRIPTION
        "Input Transport Stream Status QAM Table Entry."
    INDEX { apexGbeStatusQamInputStatBladeNum}
::= { apexGbeStatusQamInputStatTable 1 }

ApexGbeStatusQamInputStatEntry ::= SEQUENCE
    {
     apexGbeStatusQamInputStatBladeNum             Integer32,
     apexGbeStatusQamInputStatCurDataCount         Counter32,
     apexGbeStatusQamInputStatCurStreamCount       Counter32,
     apexGbeStatusQamInputStatTotDataCount         Counter32,
     apexGbeStatusQamInputStatTotStreamCount       Counter32
    }

apexGbeStatusQamInputStatBladeNum OBJECT-TYPE
    SYNTAX Integer32(1..8)
    MAX-ACCESS not-accessible
    STATUS current
    DESCRIPTION
        "Blade number."
::= { apexGbeStatusQamInputStatEntry 1 }

apexGbeStatusQamInputStatCurDataCount OBJECT-TYPE
    SYNTAX Counter32
    MAX-ACCESS read-only
    STATUS current
    DESCRIPTION
        "Five second count of number of non-null packets input to this
         QAM Blade during the last monitoring period
         (apexGbeRoutedPacketUpdateInterval)."
::= { apexGbeStatusQamInputStatEntry 2 }

apexGbeStatusQamInputStatCurStreamCount OBJECT-TYPE
    SYNTAX Counter32
    MAX-ACCESS read-only
    STATUS current
    DESCRIPTION
        "Five second count of number of null and non-null packets input to this
         QAM Blade during the last monitoring period
         (apexGbeRoutedPacketUpdateInterval)."
::= { apexGbeStatusQamInputStatEntry 3 }

apexGbeStatusQamInputStatTotDataCount OBJECT-TYPE
    SYNTAX Counter32
    MAX-ACCESS read-only
    STATUS current
    DESCRIPTION
        "Total count of number of non-null packets input to this
         QAM Blade."
::= { apexGbeStatusQamInputStatEntry 4 }

apexGbeStatusQamInputStatTotStreamCount OBJECT-TYPE
    SYNTAX Counter32
    MAX-ACCESS read-only
    STATUS current
    DESCRIPTION
        "Total count of number of null and non-null packets input to this
         QAM Blade."
::= { apexGbeStatusQamInputStatEntry 5 }


-- ------------------------------------------------------------------------------
--
-- apexGbeSfp
--
-- apexGbeSfpConfig
--
-- apexGbeSfpConfigGeneral
--

apexGbeSfpUpdateStatus OBJECT-TYPE
    SYNTAX INTEGER
        {
         notApplicable        (0),
         updateNotInProgress  (1),
         update               (2)
        }
    MAX-ACCESS read-write
    STATUS current
    DESCRIPTION
        "When set to 'update' the APEX will update the apexGbeSfpStatusTable
         by performing an one-time read of SFP memory.
 
         APEX sets back to 'updateNotInProgress' when complete.
 
         Once written, the change to this parameter will take immediate effect.
 
         @Config(config=no, reboot=no)
        "
::= { apexGbeSfpConfigGeneral 1 }


-- ------------------------------------------------------------------------------
--
-- apexGbeSfpStatus
--
-- apexGbeSfpStatusTable
--

apexGbeSfpStatusTable OBJECT-TYPE
    SYNTAX SEQUENCE OF ApexGbeSfpStatusEntry 
    MAX-ACCESS not-accessible
    STATUS current
    DESCRIPTION
        "Table of SFP status parameters.
         Indexed by Gigabit Ethernet Interface Number.
        "
::= { apexGbeSfpStatus 2 }

apexGbeSfpStatusEntry OBJECT-TYPE
    SYNTAX ApexGbeSfpStatusEntry
    MAX-ACCESS not-accessible
    STATUS current
    DESCRIPTION
        "SFP status table entry."
    INDEX { apexGbeSfpStatusGbeIfNum }
::= { apexGbeSfpStatusTable 1 }

ApexGbeSfpStatusEntry ::= SEQUENCE
    {
     apexGbeSfpStatusGbeIfNum     Integer32,
     apexGbeSfpStatusVendorId     DisplayString,
     apexGbeSfpStatusDiagInfo     DisplayString
    }

apexGbeSfpStatusGbeIfNum OBJECT-TYPE
    SYNTAX Integer32 (1..12)
    MAX-ACCESS not-accessible
    STATUS current
    DESCRIPTION
        "Gigabit Ethernet Interface Number."
::= { apexGbeSfpStatusEntry 1 }

apexGbeSfpStatusVendorId OBJECT-TYPE
    SYNTAX DisplayString
    MAX-ACCESS read-only
    STATUS current
    DESCRIPTION
        "ASCII format of bytes 0-127 from SFP-MSA ID Memory Map address A0h.
         Zero-length indicates that no SFP module is installed.
        "
::= { apexGbeSfpStatusEntry 2 }

apexGbeSfpStatusDiagInfo OBJECT-TYPE
    SYNTAX DisplayString (SIZE (0..64))
    MAX-ACCESS read-only
    STATUS current
    DESCRIPTION
        "ASCII format of bytes 96-127 from SFP Diagnostic Memory address A2h.
         Zero-length indicates that diagnostic information is not available.
        "
::= { apexGbeSfpStatusEntry 3 }


-- ------------------------------------------------------------------------------
--
-- apexRf
--
-- apexRfConfig
--
-- apexRfConfigGeneral
--

apexRfConfigTransmissionMode OBJECT-TYPE
    SYNTAX QamRfTransmissionModeTYPE
    MAX-ACCESS read-write
    STATUS current
    DESCRIPTION
        "This is the QAM RF Transmission Mode as defined in:
         Series J: Transmission of Television, Sound Programme
         and other Multimedia Signals, ITU-T J.83.
         
         **** NOTE: annexA-DVB and annexC-Asia-Pacific are currently not
         ****       supported in APEX3000.
         
         Once written, the change to this parameter will take immediate effect.
         
         @Config(config=yes, reboot=no)
         @Save(apexSaveConfig, value=2)
         @File(qamcfg.ini, type='ini')
        "
::= { apexRfConfigGeneral 1 }


-- ------------------------------------------------------------------------------
--
-- apexRfConfigBladeApplyTable
--

apexRfConfigBladeApplyTable OBJECT-TYPE
    SYNTAX SEQUENCE OF ApexRfConfigBladeApplyEntry
    MAX-ACCESS not-accessible
    STATUS current
    DESCRIPTION
        "Table of Apply Change for the RF configuration data
         in the apexRfConfigBladeX groups.

         A row in this table corresponds to a blade.
        "
::= { apexRfConfig 2 }

apexRfConfigBladeApplyEntry OBJECT-TYPE
    SYNTAX ApexRfConfigBladeApplyEntry
    MAX-ACCESS not-accessible
    STATUS current
    DESCRIPTION
        "Blade RF Configuration Apply Table Entry."
    INDEX { apexRfConfigBladeApplyBladeNum }
::= { apexRfConfigBladeApplyTable 1 }

ApexRfConfigBladeApplyEntry ::= SEQUENCE
    {
     apexRfConfigBladeApplyBladeNum      Integer32,
     apexRfConfigBladeApplyChange        ApplyDataToDeviceTYPE,
     apexRfConfigBladeInvalidApplyText   DisplayString
    }

apexRfConfigBladeApplyBladeNum OBJECT-TYPE
    SYNTAX Integer32(1..8)
    MAX-ACCESS not-accessible
    STATUS current
    DESCRIPTION
        "Blade number."
::= { apexRfConfigBladeApplyEntry 1 }

apexRfConfigBladeApplyChange OBJECT-TYPE
    SYNTAX ApplyDataToDeviceTYPE
    MAX-ACCESS read-write
    STATUS current
    DESCRIPTION
        "The Apply for all data in the corresponding apexRfConfigBladeX group.

         A row in this table corresponds to a blade.

         This parameter MUST be set to 'apply' in order for any of the data
         in the apexRfConfigBladeX group to take effect in the APEX.  This
         parameter MUST be set LAST after all other data in the apexRfConfigBladeX
         group has been configured.

         @Config(config=no, reboot=no)
        "
::= { apexRfConfigBladeApplyEntry 2 }

apexRfConfigBladeInvalidApplyText OBJECT-TYPE
    SYNTAX DisplayString (SIZE (0..80))
    MAX-ACCESS read-only
    STATUS current
    DESCRIPTION
        "When apexRfConfigBladeApplyChange is set to applyNotInProgressInvalidData
         this entry may contain a text description of what was wrong with the data.
         This entry contains the description for the most recent apply of a
         table entry that was invalid.
        "
::= { apexRfConfigBladeApplyEntry 3 }


-- ------------------------------------------------------------------------------
--
-- apexRfConfigBlade1
--
-- apexRfConfigBlade1General
--

-- none


-- ------------------------------------------------------------------------------
--
-- apexRfConfigBlade1ModesTable
--

apexRfConfigBlade1ModesTable OBJECT-TYPE
    SYNTAX SEQUENCE OF ApexRfConfigBlade1ModesEntry
    MAX-ACCESS not-accessible
    STATUS current
    DESCRIPTION
        "Table of RF Mode Combinations for QAM Blade1.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade1 2 }

apexRfConfigBlade1ModesEntry OBJECT-TYPE
    SYNTAX ApexRfConfigBlade1ModesEntry
    MAX-ACCESS not-accessible
    STATUS current
    DESCRIPTION
        "RF Configuration Blade1 RF Mode Combinations Table Entry."
    INDEX { apexRfConfigBlade1ModesIndex }
::= { apexRfConfigBlade1ModesTable 1 }

ApexRfConfigBlade1ModesEntry ::= SEQUENCE
    {
     apexRfConfigBlade1ModesIndex                   Integer32,
     apexRfConfigBlade1ModesModulationModeAnnexB    QamRfModulationModeTYPE,
     apexRfConfigBlade1ModesInterleaverDepthAnnexB  QamRfInterleaverDepthAnnexBTYPE,
     apexRfConfigBlade1ModesModulationModeAnnexA    QamRfModulationModeTYPE,
     apexRfConfigBlade1ModesSymbolRateAnnexA        Integer32,
     apexRfConfigBlade1ModesModulationModeAnnexC    QamRfModulationModeTYPE,
     apexRfConfigBlade1ModesSymbolRateAnnexC        Integer32
    }

apexRfConfigBlade1ModesIndex OBJECT-TYPE
    SYNTAX Integer32(1..4)
    MAX-ACCESS not-accessible
    STATUS current
    DESCRIPTION
        "Index for RF Configuration Blade1 RF Mode Combinations Table.
        "
::= { apexRfConfigBlade1ModesEntry 1 }

apexRfConfigBlade1ModesModulationModeAnnexB OBJECT-TYPE
    SYNTAX QamRfModulationModeTYPE
    MAX-ACCESS read-write
    STATUS current
    DESCRIPTION
        "QAM RF Modulation mode for Annex B.
         Used only when apexRfStatusTransmissionMode 'annexB-ATSC-DCII'.
        "
::= { apexRfConfigBlade1ModesEntry 2 }

apexRfConfigBlade1ModesInterleaverDepthAnnexB OBJECT-TYPE
    SYNTAX QamRfInterleaverDepthAnnexBTYPE
    MAX-ACCESS read-write
    STATUS current
    DESCRIPTION
        "QAM RF Interleaver setting for Annex B.
         Used only when apexRfStatusTransmissionMode 'annexB-ATSC-DCII'.
        "
::= { apexRfConfigBlade1ModesEntry 3 }

apexRfConfigBlade1ModesModulationModeAnnexA OBJECT-TYPE
    SYNTAX QamRfModulationModeTYPE
    MAX-ACCESS read-write
    STATUS current
    DESCRIPTION
        "QAM RF Modulation mode for Annex A.
         Only used when apexRfStatusTransmissionMode is 'annexA-DVB'.
        "
::= { apexRfConfigBlade1ModesEntry 4 }

apexRfConfigBlade1ModesSymbolRateAnnexA OBJECT-TYPE
    SYNTAX Integer32(1000000..6980000)
    MAX-ACCESS read-write
    STATUS current
    DESCRIPTION
        "QAM RF Symbol Rate for Annex A.
         Only used when apexRfStatusTransmissionMode is 'annexA-DVB'.
         It is in symbols per second (sps) in 1000 sps steps.

         @Range(step=1000)
        "
::= { apexRfConfigBlade1ModesEntry 5 }

apexRfConfigBlade1ModesModulationModeAnnexC OBJECT-TYPE
    SYNTAX QamRfModulationModeTYPE
    MAX-ACCESS read-write
    STATUS current
    DESCRIPTION
        "QAM RF Modulation mode for Annex C.
         Used only when apexRfStatusTransmissionMode 'annexC-Asia-Pacific'.
        "
::= { apexRfConfigBlade1ModesEntry 6 }

apexRfConfigBlade1ModesSymbolRateAnnexC OBJECT-TYPE
    SYNTAX Integer32(800000..5310000)
    MAX-ACCESS read-write
    STATUS current
    DESCRIPTION
        "QAM RF Symbol Rate for Annex C.
         Only used when apexRfStatusTransmissionMode is 'annexC-Asia-Pacific'.
         It is in symbols per second (sps) in 1000 sps steps.

         @Range(step=1000)
        "
::= { apexRfConfigBlade1ModesEntry 7 }


-- ------------------------------------------------------------------------------
--
-- apexRfConfigBlade1RfPortTable
--

apexRfConfigBlade1RfPortTable OBJECT-TYPE
    SYNTAX SEQUENCE OF ApexRfConfigBlade1RfPortEntry
    MAX-ACCESS not-accessible
    STATUS current
    DESCRIPTION
        "Table of RF Port configuration for QAM Blade1.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade1 3 }

apexRfConfigBlade1RfPortEntry OBJECT-TYPE
    SYNTAX ApexRfConfigBlade1RfPortEntry
    MAX-ACCESS not-accessible
    STATUS current
    DESCRIPTION
        "Blade1 RF Port Configuration Table Entry."
    INDEX { apexRfConfigBlade1RfPortNum }
::= { apexRfConfigBlade1RfPortTable 1 }

ApexRfConfigBlade1RfPortEntry ::= SEQUENCE
    {
     apexRfConfigBlade1RfPortNum                   Integer32,
     apexRfConfigBlade1RfPortSpectrumInversion     QamRfSpectrumInversionTYPE,
     apexRfConfigBlade1RfPortMute                  QamRfMuteTYPE,
     apexRfConfigBlade1RfPortRfLevel               Integer32,
     apexRfConfigBlade1RfPortDiagSuppressMode      QamRfDiagSuppressModeTYPE,
     apexRfConfigBlade1RfPortDiagSuppressChannel   Integer32,
     apexRfConfigBlade1RfPortNprimeMax             Integer32,
     apexRfConfigBlade1RfPortNprimeMaxMode         AutomaticManualTYPE
    }

apexRfConfigBlade1RfPortNum OBJECT-TYPE
    SYNTAX Integer32(1..4)
    MAX-ACCESS not-accessible
    STATUS current
    DESCRIPTION
        "RF Port number on QAM Blade.
        "
::= { apexRfConfigBlade1RfPortEntry 1 }

apexRfConfigBlade1RfPortSpectrumInversion OBJECT-TYPE
    SYNTAX QamRfSpectrumInversionTYPE
    MAX-ACCESS read-write
    STATUS current
    DESCRIPTION
        "The Spectrum Inversion Setting of the QAM Channels
         on the RF Port.
        "
::= { apexRfConfigBlade1RfPortEntry 2 }

apexRfConfigBlade1RfPortMute OBJECT-TYPE
    SYNTAX QamRfMuteTYPE
    MAX-ACCESS read-write
    STATUS current
    DESCRIPTION
        "Mute the RF Port.  This will mute all QAM channels on the
         RF Port.
        "
::= { apexRfConfigBlade1RfPortEntry 3 }

apexRfConfigBlade1RfPortRfLevel OBJECT-TYPE
    SYNTAX Integer32(3000..5600)
    MAX-ACCESS read-write
    STATUS current
    DESCRIPTION
        "The RF level setting of each channel in-use(*) on the RF Port.
         
         Range is 30.00 to 56.00 dBmV per channel in 0.01 dBmV steps.
         
         Value must be within >= -8.00 dBmV below and <= 4.00 dBmV above DRFI nominal 
         for the number of channels in-use(*) based on max 48 channel output.
         
         (*) In-use = assigned a frequency, unmuted, and not suppressed.
        "
::= { apexRfConfigBlade1RfPortEntry 4 }

apexRfConfigBlade1RfPortDiagSuppressMode OBJECT-TYPE
    SYNTAX QamRfDiagSuppressModeTYPE
    MAX-ACCESS read-write
    STATUS current
    DESCRIPTION
        "Diagnostic Suppression Mode of the RF Port.
                 
         none               - No suppression.
         oneChannel         - One channel suppressed
         allChannelsButOne  - All channels suppressed except one
         allChannels        - All channels suppressed
         
         Use apexRfConfigBlade1RfPortDiagSuppressChannel to define the 'one'
         channel for 'oneChannel' and 'allChannelsButOne' modes.
         
         This setting will override apexRfConfigBlade1ChannelTestMode.
         
         Test mode status is reflected in apexRfStatusChannelOutputMode.
        "
::= { apexRfConfigBlade1RfPortEntry 5 }

apexRfConfigBlade1RfPortDiagSuppressChannel OBJECT-TYPE
    SYNTAX Integer32(1..64)
    MAX-ACCESS read-write
    STATUS current
    DESCRIPTION
        "Channel defined for Diagnostic Suppression.
         
         Used to define the 'one' channel for the 'oneChannel' and
         'allChannelsButOne' modes of apexRfConfigBlade1RfPortDiagSuppressMode.
         
         This setting will override apexRfConfigBlade1ChannelTestMode.
         
         Test mode status is reflected in apexRfStatusChannelOutputMode.
        "
::= { apexRfConfigBlade1RfPortEntry 6 }

apexRfConfigBlade1RfPortNprimeMax OBJECT-TYPE
    SYNTAX Integer32(0..64)
    MAX-ACCESS read-write
    STATUS current
    DESCRIPTION
        "User defined DRFI N'max value used by APEX when RfPortNprimeMaxMode
         is 'manual'.  This parameter is ignored when RfPortNprimeMaxMode
         is 'automatic'.
         
         N'max must be greater than or equal to the number of channels
         in-use (assigned a frequency, unmuted, and not suppressed).
         
         Using the RfPortNprimeMax value guarantees glitchless RF port
         reconfiguration as per the DRFI specification described below.
         
         NOTE: RF performance will be degraded for large differences
               between the number of channels in-use and the user selected
               N'max value.
         
         The N'max value in use by the APEX is reflected in apexRfStatusRfPortNprimeMax.
         
         From CM-SP-DRFI-I10-100611:
         A CMTS or EQAM capable of generating more than eight channels per
         physical RF port MUST be capable of glitchless reconfiguration over
         a range of active channels from ceiling[7*N'max/8] to N'max. Channels
         which are undergoing configuration changes are referred to as the
         'changed channels.' The channels which are active and are not being
         reconfigured are referred to as the 'continuous channels'. Each DRFI
         modulator capable of generating more than eight channels per physical
         RF port MUST accept a command setting N'max. Glitchless reconfiguration
         consists of any of the following actions while introducing no
         discontinuity or detriment to the continuous channels, where the
         modulator is operating in a valid DRFI-required mode both before and
         after the reconfiguration with an active number of channels staying in
         the range {ceiling[7*N'max/8], N'max}: adding and/or deleting one or
         more channels, and/or moving some channels to new RF carrier
         frequencies, and/or changing the interleaver depth, modulation, power
         level, or frequency on one or more channels. Any change in the
         modulation characteristics (power level, modulation density, interleaver
         parameters, center frequency) of a channel excuses that channel from
         being required to operate in a glitchless manner. For example, changing
         the power per channel of a given channel means that channel is not
         considered a continuous channel for the purposes of the glitchless
         modulation requirements. Glitchless operation is not required when N'max
         is changed, even if no reconfigurations accompany the change in N'max.
        "
::= { apexRfConfigBlade1RfPortEntry 7 }

apexRfConfigBlade1RfPortNprimeMaxMode OBJECT-TYPE
    SYNTAX AutomaticManualTYPE
    MAX-ACCESS read-write
    STATUS current
    DESCRIPTION
        "DRFI N'max configuration mode.
        
         'automatic' - In this mode the APEX is responsible for selecting the N'max
                       and will automatically set N'max to the number of channels in-use
                       (assigned a frequency, unmuted, and not suppressed).  This guarantees
                       optimal RF performance for the number of channels in-use but
                       reconfiguration of the RF port may cause RF glitches.  If,
                       after testing, the user determines reconfiguration of RF ports
                       in 'standard' mode causes unacceptable RF interruption, the
                       'advanced' mode may be used.  
         
         'manual'    - In this advanced mode the user is responsible for manually setting
                       N'max in the RfPortNprimeMax parameter.  The APEX will use the value
                       in the RfPortNprimeMax parameter.  This will guarantee glitchless RF
                       port reconfiguration as per the DRFI specification described below.
                       NOTE: RF performance will be degraded for large differences
                             between the number of channels in-use and the user selected
                             N'max value.
         
         The N'max value in use by the APEX is reflected in apexRfStatusRfPortNprimeMax.
         
         From CM-SP-DRFI-I10-100611:
         A CMTS or EQAM capable of generating more than eight channels per
         physical RF port MUST be capable of glitchless reconfiguration over
         a range of active channels from ceiling[7*N'max/8] to N'max. Channels
         which are undergoing configuration changes are referred to as the
         'changed channels.' The channels which are active and are not being
         reconfigured are referred to as the 'continuous channels'. Each DRFI
         modulator capable of generating more than eight channels per physical
         RF port MUST accept a command setting N'max. Glitchless reconfiguration
         consists of any of the following actions while introducing no
         discontinuity or detriment to the continuous channels, where the
         modulator is operating in a valid DRFI-required mode both before and
         after the reconfiguration with an active number of channels staying in
         the range {ceiling[7*N'max/8], N'max}: adding and/or deleting one or
         more channels, and/or moving some channels to new RF carrier
         frequencies, and/or changing the interleaver depth, modulation, power
         level, or frequency on one or more channels. Any change in the
         modulation characteristics (power level, modulation density, interleaver
         parameters, center frequency) of a channel excuses that channel from
         being required to operate in a glitchless manner. For example, changing
         the power per channel of a given channel means that channel is not
         considered a continuous channel for the purposes of the glitchless
         modulation requirements. Glitchless operation is not required when N'max
         is changed, even if no reconfigurations accompany the change in N'max.
        "
::= { apexRfConfigBlade1RfPortEntry 8 }


-- ------------------------------------------------------------------------------
--
-- apexRfConfigBlade1SuperBlockFreqTable
--

apexRfConfigBlade1SuperBlockFreqTable OBJECT-TYPE
    SYNTAX SEQUENCE OF ApexRfConfigBlade1SuperBlockFreqEntry
    MAX-ACCESS not-accessible
    STATUS current
    DESCRIPTION
        "Table of RF Port Super Block Frequency configuration for QAM Blade1.
         
         **** NOTE: Super Block Frequency configuration is currently limited:
         ****       - Super blocks cannot overlap.
         ****       - Super blocks must be in order 1..4 from low to high frequency.
         ****       - Super block 4 frequency must be selected such that the center
         ****         frequency of the last channel of the block is no greater than
         ****         the MAX frequency range (i.e., SB 4 freq <= 813000000 Hz).
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade1 4 }

apexRfConfigBlade1SuperBlockFreqEntry OBJECT-TYPE
    SYNTAX ApexRfConfigBlade1SuperBlockFreqEntry
    MAX-ACCESS not-accessible
    STATUS current
    DESCRIPTION
        "Blade1 RF Port Super Block Frequency Configuration Table Entry."
    INDEX { apexRfConfigBlade1SuperBlockFreqRfPortNum,
            apexRfConfigBlade1SuperBlockFreqBlockNum }
::= { apexRfConfigBlade1SuperBlockFreqTable 1 }

ApexRfConfigBlade1SuperBlockFreqEntry ::= SEQUENCE
    {
     apexRfConfigBlade1SuperBlockFreqRfPortNum  Integer32,
     apexRfConfigBlade1SuperBlockFreqBlockNum   Integer32,
     apexRfConfigBlade1SuperBlockFreqAnnexB     Integer32,
     apexRfConfigBlade1SuperBlockFreqAnnexC     Integer32,
     apexRfConfigBlade1SuperBlockFreqAnnexA     Integer32
    }

apexRfConfigBlade1SuperBlockFreqRfPortNum OBJECT-TYPE
    SYNTAX Integer32(1..4)
    MAX-ACCESS not-accessible
    STATUS current
    DESCRIPTION
        "RF Port number on QAM Blade.
        "
::= { apexRfConfigBlade1SuperBlockFreqEntry 1 }

apexRfConfigBlade1SuperBlockFreqBlockNum OBJECT-TYPE
    SYNTAX Integer32(1..4)
    MAX-ACCESS not-accessible
    STATUS current
    DESCRIPTION
        "Super-block number on RF Port.
        "
::= { apexRfConfigBlade1SuperBlockFreqEntry 2 }

apexRfConfigBlade1SuperBlockFreqAnnexB OBJECT-TYPE
    SYNTAX Integer32(57000000..999000000)
    MAX-ACCESS read-write
    STATUS current
    DESCRIPTION
        "Center frequency of first channel of super-block for Annex B.
         This value must be in Hz in the range 57,000,000 Hz to 999,000,000 Hz
         in 125,000 Hz steps.
         Used only when apexRfStatusTransmissionMode 'annexB-ATSC-DCII'.

         @Range(step=125000)
        "
::= { apexRfConfigBlade1SuperBlockFreqEntry 3 }

apexRfConfigBlade1SuperBlockFreqAnnexC OBJECT-TYPE
    SYNTAX Integer32(57000000..999000000)
    MAX-ACCESS read-write
    STATUS current
    DESCRIPTION
        "Center frequency of first channel of super-block for Annex C.
         This value must be in Hz in the range 57,000,000 Hz to 999,000,000 Hz
         in 125,000 Hz steps.
         Used only when apexRfStatusTransmissionMode 'annexC-Asia-Pacific'.

         @Range(step=125000)
        "
::= { apexRfConfigBlade1SuperBlockFreqEntry 4 }

apexRfConfigBlade1SuperBlockFreqAnnexA OBJECT-TYPE
    SYNTAX Integer32(85000000..999000000)
    MAX-ACCESS read-write
    STATUS current
    DESCRIPTION
        "Center frequency of first channel of super-block for Annex A.
         This value must be in Hz in the range 85,000,000 Hz to 999,000,000 Hz
         in 125,000 Hz steps.
         Used only when apexRfStatusTransmissionMode 'annexA-DVB'.

         @Range(step=125000)
        "
::= { apexRfConfigBlade1SuperBlockFreqEntry 5 }


-- ------------------------------------------------------------------------------
--
-- apexRfConfigBlade1SubBlockFreqTable
--

apexRfConfigBlade1SubBlockFreqTable OBJECT-TYPE
    SYNTAX SEQUENCE OF ApexRfConfigBlade1SubBlockFreqEntry
    MAX-ACCESS not-accessible
    STATUS current
    DESCRIPTION
        "TABLE NOT SUPPORTED.
         
         Table of RF Port Sub Block Frequency configuration for QAM Blade1.
         
         **** NOTE: This table is currently unsupported in APEX3000.
         ****       APEX3000 will set values consistent with settings
         ****       in blade Super Block Frequency Table.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade1 5 }

apexRfConfigBlade1SubBlockFreqEntry OBJECT-TYPE
    SYNTAX ApexRfConfigBlade1SubBlockFreqEntry
    MAX-ACCESS not-accessible
    STATUS current
    DESCRIPTION
        "Blade1 RF Port Sub Block Frequency Configuration Table Entry."
    INDEX { apexRfConfigBlade1SubBlockFreqRfPortNum,
            apexRfConfigBlade1SubBlockFreqBlockNum }
::= { apexRfConfigBlade1SubBlockFreqTable 1 }

ApexRfConfigBlade1SubBlockFreqEntry ::= SEQUENCE
    {
     apexRfConfigBlade1SubBlockFreqRfPortNum      Integer32,
     apexRfConfigBlade1SubBlockFreqBlockNum       Integer32,
     apexRfConfigBlade1SubBlockFreqAnnexB         Integer32,
     apexRfConfigBlade1SubBlockFreqAnnexC         Integer32,
     apexRfConfigBlade1SubBlockFreqAnnexA         Integer32,
     apexRfConfigBlade1SubBlockChanSpacingAnnexA  Integer32
    }

apexRfConfigBlade1SubBlockFreqRfPortNum OBJECT-TYPE
    SYNTAX Integer32(1..4)
    MAX-ACCESS not-accessible
    STATUS current
    DESCRIPTION
        "RF Port number on QAM Blade.
        "
::= { apexRfConfigBlade1SubBlockFreqEntry 1 }

apexRfConfigBlade1SubBlockFreqBlockNum OBJECT-TYPE
    SYNTAX Integer32(1..16)
    MAX-ACCESS not-accessible
    STATUS current
    DESCRIPTION
        "Sub-block number on RF Port.
        "
::= { apexRfConfigBlade1SubBlockFreqEntry 2 }

apexRfConfigBlade1SubBlockFreqAnnexB OBJECT-TYPE
    SYNTAX Integer32(57000000..999000000)
    MAX-ACCESS read-write
    STATUS current
    DESCRIPTION
        "Center frequency of first channel of sub-block for Annex B.
         This value must be in Hz in the range 57,000,000 Hz to 999,000,000 Hz
         in 125,000 Hz steps.
         Used only when apexRfStatusTransmissionMode 'annexB-ATSC-DCII'.

         @Range(step=125000)
        "
::= { apexRfConfigBlade1SubBlockFreqEntry 3 }

apexRfConfigBlade1SubBlockFreqAnnexC OBJECT-TYPE
    SYNTAX Integer32(57000000..999000000)
    MAX-ACCESS read-write
    STATUS current
    DESCRIPTION
        "Center frequency of first channel of sub-block for Annex C.
         This value must be in Hz in the range 57,000,000 Hz to 999,000,000 Hz
         in 125,000 Hz steps.
         Used only when apexRfStatusTransmissionMode 'annexC-Asia-Pacific'.

         @Range(step=125000)
        "
::= { apexRfConfigBlade1SubBlockFreqEntry 4 }

apexRfConfigBlade1SubBlockFreqAnnexA OBJECT-TYPE
    SYNTAX Integer32(85000000..999000000)
    MAX-ACCESS read-write
    STATUS current
    DESCRIPTION
        "Center frequency of first channel of sub-block for Annex A.
         This value must be in Hz in the range 85,000,000 Hz to 999,000,000 Hz
         in 125,000 Hz steps.
         Used only when apexRfStatusTransmissionMode 'annexA-DVB'.

         @Range(step=125000)
        "
::= { apexRfConfigBlade1SubBlockFreqEntry 5 }

apexRfConfigBlade1SubBlockChanSpacingAnnexA OBJECT-TYPE
    SYNTAX Integer32(1000000..8000000)
    MAX-ACCESS read-write
    STATUS current
    DESCRIPTION
        "*** This entry is not supported. ***
         
         Channel spacing of sub-block for Annex A.
         This value must be in Hz in the range 1,000,000 Hz to 8,000,000 Hz
         in 500,000 Hz steps.
         Used only when apexRfStatusTransmissionMode 'annexA-DVB'.

         @Range(step=500000)
        "
::= { apexRfConfigBlade1SubBlockFreqEntry 6 }


-- ------------------------------------------------------------------------------
--
-- apexRfConfigBlade1ChannelTable
--

apexRfConfigBlade1ChannelTable OBJECT-TYPE
    SYNTAX SEQUENCE OF ApexRfConfigBlade1ChannelEntry
    MAX-ACCESS not-accessible
    STATUS current
    DESCRIPTION
        "Table of QAM Channel configuration for QAM Blade1.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade1 6 }

apexRfConfigBlade1ChannelEntry OBJECT-TYPE
    SYNTAX ApexRfConfigBlade1ChannelEntry
    MAX-ACCESS not-accessible
    STATUS current
    DESCRIPTION
        "Blade1 QAM Channel Configuration Table Entry."
    INDEX { apexRfConfigBlade1ChannelRfPortNum,
            apexRfConfigBlade1ChannelChanNum }
::= { apexRfConfigBlade1ChannelTable 1 }

ApexRfConfigBlade1ChannelEntry ::= SEQUENCE
    {
     apexRfConfigBlade1ChannelRfPortNum              Integer32,
     apexRfConfigBlade1ChannelChanNum                Integer32,
     apexRfConfigBlade1ChannelFrequencyGridSelect    Integer32,
     apexRfConfigBlade1ChannelModeComboSelectAnnexA  Integer32,
     apexRfConfigBlade1ChannelModeComboSelectAnnexB  Integer32,
     apexRfConfigBlade1ChannelModeComboSelectAnnexC  Integer32,
     apexRfConfigBlade1ChannelRfLevelAdjust          Integer32,
     apexRfConfigBlade1ChannelTestMode               QamChannelTestModeTYPE,
     apexRfConfigBlade1ChannelMute                   QamRfMuteTYPE
    }

apexRfConfigBlade1ChannelRfPortNum OBJECT-TYPE
    SYNTAX Integer32(1..4)
    MAX-ACCESS not-accessible
    STATUS current
    DESCRIPTION
        "RF Port number on QAM Blade.
        "
::= { apexRfConfigBlade1ChannelEntry 1 }

apexRfConfigBlade1ChannelChanNum OBJECT-TYPE
    SYNTAX Integer32(1..64)
    MAX-ACCESS not-accessible
    STATUS current
    DESCRIPTION
        "QAM channel number on RF Port.
        "
::= { apexRfConfigBlade1ChannelEntry 2 }

apexRfConfigBlade1ChannelFrequencyGridSelect OBJECT-TYPE
    SYNTAX Integer32(0..128)
    MAX-ACCESS read-write
    STATUS current
    DESCRIPTION
        "RF Port frequency grid slot selection for this channel.
         Zero indicates the channel is not in use (disabled).
         
         The frequency is selected from a grid of 128 total frequency assignment
         selections (or 'slots').  The grid is divided into 4 super blocks (192
         MHz wide) with 32 assignment slots each.  Each super block is divided
         into 4 sub blocks (48 MHz wide) with 8 assignment slots each.  Using 'B'
         for super blocks and 'b' sub blocks numbering of super and sub blocks is
         B1..B4 and b1..b16 respectively.  The sub blocks are contained in
         superblocks as follows:
            B1[b1..b4],
            B2[b5..b8],
            B3[b9..b12], and
            B4[b13..b16].
         Numbering of the slots within the blocks is as follows:
            B1[b1(1..8), b2(9..16), b3(17..24), b4(25..32)],
            B2[b5(33..40), b6(41..48), b7(49..56), b8(57..64)],
            B3[b9(65..72), b10(73..80), b11(81..88), b12(89..96)], and
            B4[b13(97..105), b14(106..112), b15(113..120), b16(121..128)].

         Annex B/C: For apexRfStatusTransmissionMode of 'annexB-ATSC-DCII' or
         'annexC-Asia-Pacific' the full range of slots [1..128] may be selected.

         Annex A: For apexRfStatusTransmissionMode of 'annexA-DVB' not all slots
         may be selected.  Since a sub block represents a 48 MHz wide band and
         'annexA-DVB' channel spacing is currently a fixed 8 MHz, only the first
         6 slots in each sub block can be assigned.  Therefore, the 'annexA-DVB'
         assignments may be as follows:
            B1[b1(1..6), b2(9..14), b3(17..22), b4(25..30)],
            B2[b5(33..38), b6(41..46), b7(49..54), b8(57..62)],
            B3[b9(65..70), b10(73..78), b11(81..86), b12(89..94)], and
            B4[b13(97..102), b14(105..110), b15(113..118), b16(121..126)].
         The APEX3000 will automatically clear any assignments to the following
         slots:
            B1[b1(7, 8), b2(15, 16), b3(23, 24), b4(31, 32)],
            B2[b5(39, 40), b6(47, 48), b7(55, 56), b8(63, 64)],
            B3[b9(71, 72), b10(79, 80), b11(87, 88), b12(95, 96)], and
            B4[b13(103, 104), b14(111, 112), b15(119, 120), b16(127, 128)].
        "
::= { apexRfConfigBlade1ChannelEntry 3 }

apexRfConfigBlade1ChannelModeComboSelectAnnexA OBJECT-TYPE
    SYNTAX Integer32(1..4)
    MAX-ACCESS read-write
    STATUS current
    DESCRIPTION
        "QAM Mode Combination selection for Annex A.
         Mode combinations are configured in apexRfConfigBlade1ModesTable.
         Used only when apexRfStatusTransmissionMode 'annexA-DVB'.
        "
::= { apexRfConfigBlade1ChannelEntry 4 }

apexRfConfigBlade1ChannelModeComboSelectAnnexB OBJECT-TYPE
    SYNTAX Integer32(1..4)
    MAX-ACCESS read-write
    STATUS current
    DESCRIPTION
        "QAM Mode Combination selection for Annex B.
         Mode combinations are configured in apexRfConfigBlade1ModesTable.
         Used only when apexRfStatusTransmissionMode 'annexB-ATSC-DCII'.
        "
::= { apexRfConfigBlade1ChannelEntry 5 }

apexRfConfigBlade1ChannelModeComboSelectAnnexC OBJECT-TYPE
    SYNTAX Integer32(1..4)
    MAX-ACCESS read-write
    STATUS current
    DESCRIPTION
        "QAM Mode Combination selection for Annex C.
         Mode combinations are configured in apexRfConfigBlade1ModesTable.
         Used only when apexRfStatusTransmissionMode 'annexC-Asia-Pacific'.
        "
::= { apexRfConfigBlade1ChannelEntry 6 }

apexRfConfigBlade1ChannelRfLevelAdjust OBJECT-TYPE
    SYNTAX Integer32(-20..0)
    MAX-ACCESS read-write
    STATUS current
    DESCRIPTION
        "RF Level adjustment for the channel.
         
         Range is -2.0 dB to 0.0 dB relative to apexRfConfigBlade1RfPortRfLevel.
         Value is in 0.1 dB steps.
         
         Final RF Level after adjustment applied must be within >= -8.00 dB below
         and <= 4.00 dB above DRFI nominal for the number of channels in-use(*)
         based on max 48 channel output.
         
         (*) In-use = assigned a frequency, unmuted, and not suppressed.
        "
::= { apexRfConfigBlade1ChannelEntry 7 }

apexRfConfigBlade1ChannelTestMode OBJECT-TYPE
    SYNTAX QamChannelTestModeTYPE
    MAX-ACCESS read-write
    STATUS current
    DESCRIPTION
        "Test mode for the channel.
         
         RF Port diagnostic suppression configuration will override
         this setting.  (apexRfConfigBlade1RfPortDiagSuppressMode and
         apexRfConfigBlade1RfPortDiagSuppressChannel)
         
         Test mode status is reflected in apexRfStatusChannelOutputMode.
         
         noTest     - Test mode is off.  Channel is in normal operation.
         suppress   - Suppress the channel.
         cwtest     - CW test.
         prbs23m    - PRBS-23 with MPEG Sync.
         prbsUnique - Unique PRBS. Multiple channels configured in this
                      mode will transmit uncorrelated data. Pattern is
                      generated in the APEX.
         mpegNull   - MPEG Null packets.
         biPhase    - Bi-phase Mode (alternating symbols).
        "
::= { apexRfConfigBlade1ChannelEntry 8 }

apexRfConfigBlade1ChannelMute OBJECT-TYPE
    SYNTAX QamRfMuteTYPE
    MAX-ACCESS read-write
    STATUS current
    DESCRIPTION
        "Mute the QAM Channel.
        "
::= { apexRfConfigBlade1ChannelEntry 9 }


-- ------------------------------------------------------------------------------
--
-- apexRfConfigBlade2
--
-- apexRfConfigBlade2General
--

-- none


-- ------------------------------------------------------------------------------
--
-- apexRfConfigBlade2ModesTable
--

apexRfConfigBlade2ModesTable OBJECT-TYPE
    SYNTAX SEQUENCE OF ApexRfConfigBlade2ModesEntry
    MAX-ACCESS not-accessible
    STATUS current
    DESCRIPTION
        "Table of RF Mode Combinations for QAM Blade2.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade2 2 }

apexRfConfigBlade2ModesEntry OBJECT-TYPE
    SYNTAX ApexRfConfigBlade2ModesEntry
    MAX-ACCESS not-accessible
    STATUS current
    DESCRIPTION
        "RF Configuration Blade2 RF Mode Combinations Table Entry."
    INDEX { apexRfConfigBlade2ModesIndex }
::= { apexRfConfigBlade2ModesTable 1 }

ApexRfConfigBlade2ModesEntry ::= SEQUENCE
    {
     apexRfConfigBlade2ModesIndex                   Integer32,
     apexRfConfigBlade2ModesModulationModeAnnexB    QamRfModulationModeTYPE,
     apexRfConfigBlade2ModesInterleaverDepthAnnexB  QamRfInterleaverDepthAnnexBTYPE,
     apexRfConfigBlade2ModesModulationModeAnnexA    QamRfModulationModeTYPE,
     apexRfConfigBlade2ModesSymbolRateAnnexA        Integer32,
     apexRfConfigBlade2ModesModulationModeAnnexC    QamRfModulationModeTYPE,
     apexRfConfigBlade2ModesSymbolRateAnnexC        Integer32
    }

apexRfConfigBlade2ModesIndex OBJECT-TYPE
    SYNTAX Integer32(1..4)
    MAX-ACCESS not-accessible
    STATUS current
    DESCRIPTION
        "Index for RF Configuration Blade2 RF Mode Combinations Table.
        "
::= { apexRfConfigBlade2ModesEntry 1 }

apexRfConfigBlade2ModesModulationModeAnnexB OBJECT-TYPE
    SYNTAX QamRfModulationModeTYPE
    MAX-ACCESS read-write
    STATUS current
    DESCRIPTION
        "QAM RF Modulation mode for Annex B.
         Used only when apexRfStatusTransmissionMode 'annexB-ATSC-DCII'.
        "
::= { apexRfConfigBlade2ModesEntry 2 }

apexRfConfigBlade2ModesInterleaverDepthAnnexB OBJECT-TYPE
    SYNTAX QamRfInterleaverDepthAnnexBTYPE
    MAX-ACCESS read-write
    STATUS current
    DESCRIPTION
        "QAM RF Interleaver setting for Annex B.
         Used only when apexRfStatusTransmissionMode 'annexB-ATSC-DCII'.
        "
::= { apexRfConfigBlade2ModesEntry 3 }

apexRfConfigBlade2ModesModulationModeAnnexA OBJECT-TYPE
    SYNTAX QamRfModulationModeTYPE
    MAX-ACCESS read-write
    STATUS current
    DESCRIPTION
        "QAM RF Modulation mode for Annex A.
         Only used when apexRfStatusTransmissionMode is 'annexA-DVB'.
        "
::= { apexRfConfigBlade2ModesEntry 4 }

apexRfConfigBlade2ModesSymbolRateAnnexA OBJECT-TYPE
    SYNTAX Integer32(1000000..6980000)
    MAX-ACCESS read-write
    STATUS current
    DESCRIPTION
        "QAM RF Symbol Rate for Annex A.
         Only used when apexRfStatusTransmissionMode is 'annexA-DVB'.
         It is in symbols per second (sps) in 1000 sps steps.

         @Range(step=1000)
        "
::= { apexRfConfigBlade2ModesEntry 5 }

apexRfConfigBlade2ModesModulationModeAnnexC OBJECT-TYPE
    SYNTAX QamRfModulationModeTYPE
    MAX-ACCESS read-write
    STATUS current
    DESCRIPTION
        "QAM RF Modulation mode for Annex C.
         Used only when apexRfStatusTransmissionMode 'annexC-Asia-Pacific'.
        "
::= { apexRfConfigBlade2ModesEntry 6 }

apexRfConfigBlade2ModesSymbolRateAnnexC OBJECT-TYPE
    SYNTAX Integer32(800000..5310000)
    MAX-ACCESS read-write
    STATUS current
    DESCRIPTION
        "QAM RF Symbol Rate for Annex C.
         Only used when apexRfStatusTransmissionMode is 'annexC-Asia-Pacific'.
         It is in symbols per second (sps) in 1000 sps steps.

         @Range(step=1000)
        "
::= { apexRfConfigBlade2ModesEntry 7 }


-- ------------------------------------------------------------------------------
--
-- apexRfConfigBlade2RfPortTable
--

apexRfConfigBlade2RfPortTable OBJECT-TYPE
    SYNTAX SEQUENCE OF ApexRfConfigBlade2RfPortEntry
    MAX-ACCESS not-accessible
    STATUS current
    DESCRIPTION
        "Table of RF Port configuration for QAM Blade2.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade2 3 }

apexRfConfigBlade2RfPortEntry OBJECT-TYPE
    SYNTAX ApexRfConfigBlade2RfPortEntry
    MAX-ACCESS not-accessible
    STATUS current
    DESCRIPTION
        "Blade2 RF Port Configuration Table Entry."
    INDEX { apexRfConfigBlade2RfPortNum }
::= { apexRfConfigBlade2RfPortTable 1 }

ApexRfConfigBlade2RfPortEntry ::= SEQUENCE
    {
     apexRfConfigBlade2RfPortNum                   Integer32,
     apexRfConfigBlade2RfPortSpectrumInversion     QamRfSpectrumInversionTYPE,
     apexRfConfigBlade2RfPortMute                  QamRfMuteTYPE,
     apexRfConfigBlade2RfPortRfLevel               Integer32,
     apexRfConfigBlade2RfPortDiagSuppressMode      QamRfDiagSuppressModeTYPE,
     apexRfConfigBlade2RfPortDiagSuppressChannel   Integer32,
     apexRfConfigBlade2RfPortNprimeMax             Integer32,
     apexRfConfigBlade2RfPortNprimeMaxMode         AutomaticManualTYPE
    }

apexRfConfigBlade2RfPortNum OBJECT-TYPE
    SYNTAX Integer32(1..4)
    MAX-ACCESS not-accessible
    STATUS current
    DESCRIPTION
        "RF Port number on QAM Blade.
        "
::= { apexRfConfigBlade2RfPortEntry 1 }

apexRfConfigBlade2RfPortSpectrumInversion OBJECT-TYPE
    SYNTAX QamRfSpectrumInversionTYPE
    MAX-ACCESS read-write
    STATUS current
    DESCRIPTION
        "The Spectrum Inversion Setting of the QAM Channels
         on the RF Port.
        "
::= { apexRfConfigBlade2RfPortEntry 2 }

apexRfConfigBlade2RfPortMute OBJECT-TYPE
    SYNTAX QamRfMuteTYPE
    MAX-ACCESS read-write
    STATUS current
    DESCRIPTION
        "Mute the RF Port.  This will mute all QAM channels on the
         RF Port.
        "
::= { apexRfConfigBlade2RfPortEntry 3 }

apexRfConfigBlade2RfPortRfLevel OBJECT-TYPE
    SYNTAX Integer32(3000..5600)
    MAX-ACCESS read-write
    STATUS current
    DESCRIPTION
        "The RF level setting of each channel in-use(*) on the RF Port.
         
         Range is 30.00 to 56.00 dBmV per channel in 0.01 dBmV steps.
         
         Value must be within >= -8.00 dBmV below and <= 4.00 dBmV above DRFI nominal 
         for the number of channels in-use(*) based on max 48 channel output.
         
         (*) In-use = assigned a frequency, unmuted, and not suppressed.
        "
::= { apexRfConfigBlade2RfPortEntry 4 }

apexRfConfigBlade2RfPortDiagSuppressMode OBJECT-TYPE
    SYNTAX QamRfDiagSuppressModeTYPE
    MAX-ACCESS read-write
    STATUS current
    DESCRIPTION
        "Diagnostic Suppression Mode of the RF Port.
                 
         none               - No suppression.
         oneChannel         - One channel suppressed
         allChannelsButOne  - All channels suppressed except one
         allChannels        - All channels suppressed
         
         Use apexRfConfigBlade2RfPortDiagSuppressChannel to define the 'one'
         channel for 'oneChannel' and 'allChannelsButOne' modes.
         
         This setting will override apexRfConfigBlade2ChannelTestMode.
         
         Test mode status is reflected in apexRfStatusChannelOutputMode.
        "
::= { apexRfConfigBlade2RfPortEntry 5 }

apexRfConfigBlade2RfPortDiagSuppressChannel OBJECT-TYPE
    SYNTAX Integer32(1..64)
    MAX-ACCESS read-write
    STATUS current
    DESCRIPTION
        "Channel defined for Diagnostic Suppression.
         
         Used to define the 'one' channel for the 'oneChannel' and
         'allChannelsButOne' modes of apexRfConfigBlade2RfPortDiagSuppressMode.
         
         This setting will override apexRfConfigBlade2ChannelTestMode.
         
         Test mode status is reflected in apexRfStatusChannelOutputMode.
        "
::= { apexRfConfigBlade2RfPortEntry 6 }

apexRfConfigBlade2RfPortNprimeMax OBJECT-TYPE
    SYNTAX Integer32(0..64)
    MAX-ACCESS read-write
    STATUS current
    DESCRIPTION
        "User defined DRFI N'max value used by APEX when RfPortNprimeMaxMode
         is 'manual'.  This parameter is ignored when RfPortNprimeMaxMode
         is 'automatic'.
         
         N'max must be greater than or equal to the number of channels
         in-use (assigned a frequency, unmuted, and not suppressed).
         
         Using the RfPortNprimeMax value guarantees glitchless RF port
         reconfiguration as per the DRFI specification described below.
         
         NOTE: RF performance will be degraded for large differences
               between the number of channels in-use and the user selected
               N'max value.
         
         The N'max value in use by the APEX is reflected in apexRfStatusRfPortNprimeMax.
         
         From CM-SP-DRFI-I10-100611:
         A CMTS or EQAM capable of generating more than eight channels per
         physical RF port MUST be capable of glitchless reconfiguration over
         a range of active channels from ceiling[7*N'max/8] to N'max. Channels
         which are undergoing configuration changes are referred to as the
         'changed channels.' The channels which are active and are not being
         reconfigured are referred to as the 'continuous channels'. Each DRFI
         modulator capable of generating more than eight channels per physical
         RF port MUST accept a command setting N'max. Glitchless reconfiguration
         consists of any of the following actions while introducing no
         discontinuity or detriment to the continuous channels, where the
         modulator is operating in a valid DRFI-required mode both before and
         after the reconfiguration with an active number of channels staying in
         the range {ceiling[7*N'max/8], N'max}: adding and/or deleting one or
         more channels, and/or moving some channels to new RF carrier
         frequencies, and/or changing the interleaver depth, modulation, power
         level, or frequency on one or more channels. Any change in the
         modulation characteristics (power level, modulation density, interleaver
         parameters, center frequency) of a channel excuses that channel from
         being required to operate in a glitchless manner. For example, changing
         the power per channel of a given channel means that channel is not
         considered a continuous channel for the purposes of the glitchless
         modulation requirements. Glitchless operation is not required when N'max
         is changed, even if no reconfigurations accompany the change in N'max.
        "
::= { apexRfConfigBlade2RfPortEntry 7 }

apexRfConfigBlade2RfPortNprimeMaxMode OBJECT-TYPE
    SYNTAX AutomaticManualTYPE
    MAX-ACCESS read-write
    STATUS current
    DESCRIPTION
        "DRFI N'max configuration mode.
        
         'automatic' - In this mode the APEX is responsible for selecting the N'max
                       and will automatically set N'max to the number of channels in-use
                       (assigned a frequency, unmuted, and not suppressed).  This guarantees
                       optimal RF performance for the number of channels in-use but
                       reconfiguration of the RF port may cause RF glitches.  If,
                       after testing, the user determines reconfiguration of RF ports
                       in 'standard' mode causes unacceptable RF interruption, the
                       'advanced' mode may be used.  
         
         'manual'    - In this advanced mode the user is responsible for manually setting
                       N'max in the RfPortNprimeMax parameter.  The APEX will use the value
                       in the RfPortNprimeMax parameter.  This will guarantee glitchless RF
                       port reconfiguration as per the DRFI specification described below.
                       NOTE: RF performance will be degraded for large differences
                             between the number of channels in-use and the user selected
                             N'max value.
         
         The N'max value in use by the APEX is reflected in apexRfStatusRfPortNprimeMax.
         
         From CM-SP-DRFI-I10-100611:
         A CMTS or EQAM capable of generating more than eight channels per
         physical RF port MUST be capable of glitchless reconfiguration over
         a range of active channels from ceiling[7*N'max/8] to N'max. Channels
         which are undergoing configuration changes are referred to as the
         'changed channels.' The channels which are active and are not being
         reconfigured are referred to as the 'continuous channels'. Each DRFI
         modulator capable of generating more than eight channels per physical
         RF port MUST accept a command setting N'max. Glitchless reconfiguration
         consists of any of the following actions while introducing no
         discontinuity or detriment to the continuous channels, where the
         modulator is operating in a valid DRFI-required mode both before and
         after the reconfiguration with an active number of channels staying in
         the range {ceiling[7*N'max/8], N'max}: adding and/or deleting one or
         more channels, and/or moving some channels to new RF carrier
         frequencies, and/or changing the interleaver depth, modulation, power
         level, or frequency on one or more channels. Any change in the
         modulation characteristics (power level, modulation density, interleaver
         parameters, center frequency) of a channel excuses that channel from
         being required to operate in a glitchless manner. For example, changing
         the power per channel of a given channel means that channel is not
         considered a continuous channel for the purposes of the glitchless
         modulation requirements. Glitchless operation is not required when N'max
         is changed, even if no reconfigurations accompany the change in N'max.
        "
::= { apexRfConfigBlade2RfPortEntry 8 }


-- ------------------------------------------------------------------------------
--
-- apexRfConfigBlade2SuperBlockFreqTable
--

apexRfConfigBlade2SuperBlockFreqTable OBJECT-TYPE
    SYNTAX SEQUENCE OF ApexRfConfigBlade2SuperBlockFreqEntry
    MAX-ACCESS not-accessible
    STATUS current
    DESCRIPTION
        "Table of RF Port Super Block Frequency configuration for QAM Blade2.
         
         **** NOTE: Super Block Frequency configuration is currently limited:
         ****       - Super blocks cannot overlap.
         ****       - Super blocks must be in order 1..4 from low to high frequency.
         ****       - Super block 4 frequency must be selected such that the center
         ****         frequency of the last channel of the block is no greater than
         ****         the MAX frequency range (i.e., SB 4 freq <= 813000000 Hz).
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade2 4 }

apexRfConfigBlade2SuperBlockFreqEntry OBJECT-TYPE
    SYNTAX ApexRfConfigBlade2SuperBlockFreqEntry
    MAX-ACCESS not-accessible
    STATUS current
    DESCRIPTION
        "Blade2 RF Port Super Block Frequency Configuration Table Entry."
    INDEX { apexRfConfigBlade2SuperBlockFreqRfPortNum,
            apexRfConfigBlade2SuperBlockFreqBlockNum }
::= { apexRfConfigBlade2SuperBlockFreqTable 1 }

ApexRfConfigBlade2SuperBlockFreqEntry ::= SEQUENCE
    {
     apexRfConfigBlade2SuperBlockFreqRfPortNum  Integer32,
     apexRfConfigBlade2SuperBlockFreqBlockNum   Integer32,
     apexRfConfigBlade2SuperBlockFreqAnnexB     Integer32,
     apexRfConfigBlade2SuperBlockFreqAnnexC     Integer32,
     apexRfConfigBlade2SuperBlockFreqAnnexA     Integer32
    }

apexRfConfigBlade2SuperBlockFreqRfPortNum OBJECT-TYPE
    SYNTAX Integer32(1..4)
    MAX-ACCESS not-accessible
    STATUS current
    DESCRIPTION
        "RF Port number on QAM Blade.
        "
::= { apexRfConfigBlade2SuperBlockFreqEntry 1 }

apexRfConfigBlade2SuperBlockFreqBlockNum OBJECT-TYPE
    SYNTAX Integer32(1..4)
    MAX-ACCESS not-accessible
    STATUS current
    DESCRIPTION
        "Super-block number on RF Port.
        "
::= { apexRfConfigBlade2SuperBlockFreqEntry 2 }

apexRfConfigBlade2SuperBlockFreqAnnexB OBJECT-TYPE
    SYNTAX Integer32(57000000..999000000)
    MAX-ACCESS read-write
    STATUS current
    DESCRIPTION
        "Center frequency of first channel of super-block for Annex B.
         This value must be in Hz in the range 57,000,000 Hz to 999,000,000 Hz
         in 125,000 Hz steps.
         Used only when apexRfStatusTransmissionMode 'annexB-ATSC-DCII'.

         @Range(step=125000)
        "
::= { apexRfConfigBlade2SuperBlockFreqEntry 3 }

apexRfConfigBlade2SuperBlockFreqAnnexC OBJECT-TYPE
    SYNTAX Integer32(57000000..999000000)
    MAX-ACCESS read-write
    STATUS current
    DESCRIPTION
        "Center frequency of first channel of super-block for Annex C.
         This value must be in Hz in the range 57,000,000 Hz to 999,000,000 Hz
         in 125,000 Hz steps.
         Used only when apexRfStatusTransmissionMode 'annexC-Asia-Pacific'.

         @Range(step=125000)
        "
::= { apexRfConfigBlade2SuperBlockFreqEntry 4 }

apexRfConfigBlade2SuperBlockFreqAnnexA OBJECT-TYPE
    SYNTAX Integer32(85000000..999000000)
    MAX-ACCESS read-write
    STATUS current
    DESCRIPTION
        "Center frequency of first channel of super-block for Annex A.
         This value must be in Hz in the range 85,000,000 Hz to 999,000,000 Hz
         in 125,000 Hz steps.
         Used only when apexRfStatusTransmissionMode 'annexA-DVB'.

         @Range(step=125000)
        "
::= { apexRfConfigBlade2SuperBlockFreqEntry 5 }


-- ------------------------------------------------------------------------------
--
-- apexRfConfigBlade2SubBlockFreqTable
--

apexRfConfigBlade2SubBlockFreqTable OBJECT-TYPE
    SYNTAX SEQUENCE OF ApexRfConfigBlade2SubBlockFreqEntry
    MAX-ACCESS not-accessible
    STATUS current
    DESCRIPTION
        "TABLE NOT SUPPORTED.
         
         Table of RF Port Sub Block Frequency configuration for QAM Blade2.
         
         **** NOTE: This table is currently unsupported in APEX3000.
         ****       APEX3000 will set values consistent with settings
         ****       in blade Super Block Frequency Table.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade2 5 }

apexRfConfigBlade2SubBlockFreqEntry OBJECT-TYPE
    SYNTAX ApexRfConfigBlade2SubBlockFreqEntry
    MAX-ACCESS not-accessible
    STATUS current
    DESCRIPTION
        "Blade2 RF Port Sub Block Frequency Configuration Table Entry."
    INDEX { apexRfConfigBlade2SubBlockFreqRfPortNum,
            apexRfConfigBlade2SubBlockFreqBlockNum }
::= { apexRfConfigBlade2SubBlockFreqTable 1 }

ApexRfConfigBlade2SubBlockFreqEntry ::= SEQUENCE
    {
     apexRfConfigBlade2SubBlockFreqRfPortNum      Integer32,
     apexRfConfigBlade2SubBlockFreqBlockNum       Integer32,
     apexRfConfigBlade2SubBlockFreqAnnexB         Integer32,
     apexRfConfigBlade2SubBlockFreqAnnexC         Integer32,
     apexRfConfigBlade2SubBlockFreqAnnexA         Integer32,
     apexRfConfigBlade2SubBlockChanSpacingAnnexA  Integer32
    }

apexRfConfigBlade2SubBlockFreqRfPortNum OBJECT-TYPE
    SYNTAX Integer32(1..4)
    MAX-ACCESS not-accessible
    STATUS current
    DESCRIPTION
        "RF Port number on QAM Blade.
        "
::= { apexRfConfigBlade2SubBlockFreqEntry 1 }

apexRfConfigBlade2SubBlockFreqBlockNum OBJECT-TYPE
    SYNTAX Integer32(1..16)
    MAX-ACCESS not-accessible
    STATUS current
    DESCRIPTION
        "Sub-block number on RF Port.
        "
::= { apexRfConfigBlade2SubBlockFreqEntry 2 }

apexRfConfigBlade2SubBlockFreqAnnexB OBJECT-TYPE
    SYNTAX Integer32(57000000..999000000)
    MAX-ACCESS read-write
    STATUS current
    DESCRIPTION
        "Center frequency of first channel of sub-block for Annex B.
         This value must be in Hz in the range 57,000,000 Hz to 999,000,000 Hz
         in 125,000 Hz steps.
         Used only when apexRfStatusTransmissionMode 'annexB-ATSC-DCII'.

         @Range(step=125000)
        "
::= { apexRfConfigBlade2SubBlockFreqEntry 3 }

apexRfConfigBlade2SubBlockFreqAnnexC OBJECT-TYPE
    SYNTAX Integer32(57000000..999000000)
    MAX-ACCESS read-write
    STATUS current
    DESCRIPTION
        "Center frequency of first channel of sub-block for Annex C.
         This value must be in Hz in the range 57,000,000 Hz to 999,000,000 Hz
         in 125,000 Hz steps.
         Used only when apexRfStatusTransmissionMode 'annexC-Asia-Pacific'.

         @Range(step=125000)
        "
::= { apexRfConfigBlade2SubBlockFreqEntry 4 }

apexRfConfigBlade2SubBlockFreqAnnexA OBJECT-TYPE
    SYNTAX Integer32(85000000..999000000)
    MAX-ACCESS read-write
    STATUS current
    DESCRIPTION
        "Center frequency of first channel of sub-block for Annex A.
         This value must be in Hz in the range 85,000,000 Hz to 999,000,000 Hz
         in 125,000 Hz steps.
         Used only when apexRfStatusTransmissionMode 'annexA-DVB'.

         @Range(step=125000)
        "
::= { apexRfConfigBlade2SubBlockFreqEntry 5 }

apexRfConfigBlade2SubBlockChanSpacingAnnexA OBJECT-TYPE
    SYNTAX Integer32(1000000..8000000)
    MAX-ACCESS read-write
    STATUS current
    DESCRIPTION
        "*** This entry is not supported. ***
         
         Channel spacing of sub-block for Annex A.
         This value must be in Hz in the range 1,000,000 Hz to 8,000,000 Hz
         in 500,000 Hz steps.
         Used only when apexRfStatusTransmissionMode 'annexA-DVB'.

         @Range(step=500000)
        "
::= { apexRfConfigBlade2SubBlockFreqEntry 6 }


-- ------------------------------------------------------------------------------
--
-- apexRfConfigBlade2ChannelTable
--

apexRfConfigBlade2ChannelTable OBJECT-TYPE
    SYNTAX SEQUENCE OF ApexRfConfigBlade2ChannelEntry
    MAX-ACCESS not-accessible
    STATUS current
    DESCRIPTION
        "Table of QAM Channel configuration for QAM Blade2.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade2 6 }

apexRfConfigBlade2ChannelEntry OBJECT-TYPE
    SYNTAX ApexRfConfigBlade2ChannelEntry
    MAX-ACCESS not-accessible
    STATUS current
    DESCRIPTION
        "Blade2 QAM Channel Configuration Table Entry."
    INDEX { apexRfConfigBlade2ChannelRfPortNum,
            apexRfConfigBlade2ChannelChanNum }
::= { apexRfConfigBlade2ChannelTable 1 }

ApexRfConfigBlade2ChannelEntry ::= SEQUENCE
    {
     apexRfConfigBlade2ChannelRfPortNum              Integer32,
     apexRfConfigBlade2ChannelChanNum                Integer32,
     apexRfConfigBlade2ChannelFrequencyGridSelect    Integer32,
     apexRfConfigBlade2ChannelModeComboSelectAnnexA  Integer32,
     apexRfConfigBlade2ChannelModeComboSelectAnnexB  Integer32,
     apexRfConfigBlade2ChannelModeComboSelectAnnexC  Integer32,
     apexRfConfigBlade2ChannelRfLevelAdjust          Integer32,
     apexRfConfigBlade2ChannelTestMode               QamChannelTestModeTYPE,
     apexRfConfigBlade2ChannelMute                   QamRfMuteTYPE
    }

apexRfConfigBlade2ChannelRfPortNum OBJECT-TYPE
    SYNTAX Integer32(1..4)
    MAX-ACCESS not-accessible
    STATUS current
    DESCRIPTION
        "RF Port number on QAM Blade.
        "
::= { apexRfConfigBlade2ChannelEntry 1 }

apexRfConfigBlade2ChannelChanNum OBJECT-TYPE
    SYNTAX Integer32(1..64)
    MAX-ACCESS not-accessible
    STATUS current
    DESCRIPTION
        "QAM channel number on RF Port.
        "
::= { apexRfConfigBlade2ChannelEntry 2 }

apexRfConfigBlade2ChannelFrequencyGridSelect OBJECT-TYPE
    SYNTAX Integer32(0..128)
    MAX-ACCESS read-write
    STATUS current
    DESCRIPTION
        "RF Port frequency grid slot selection for this channel.
         Zero indicates the channel is not in use (disabled).
         
         The frequency is selected from a grid of 128 total frequency assignment
         selections (or 'slots').  The grid is divided into 4 super blocks (192
         MHz wide) with 32 assignment slots each.  Each super block is divided
         into 4 sub blocks (48 MHz wide) with 8 assignment slots each.  Using 'B'
         for super blocks and 'b' sub blocks numbering of super and sub blocks is
         B1..B4 and b1..b16 respectively.  The sub blocks are contained in
         superblocks as follows:
            B1[b1..b4],
            B2[b5..b8],
            B3[b9..b12], and
            B4[b13..b16].
         Numbering of the slots within the blocks is as follows:
            B1[b1(1..8), b2(9..16), b3(17..24), b4(25..32)],
            B2[b5(33..40), b6(41..48), b7(49..56), b8(57..64)],
            B3[b9(65..72), b10(73..80), b11(81..88), b12(89..96)], and
            B4[b13(97..105), b14(106..112), b15(113..120), b16(121..128)].

         Annex B/C: For apexRfStatusTransmissionMode of 'annexB-ATSC-DCII' or
         'annexC-Asia-Pacific' the full range of slots [1..128] may be selected.

         Annex A: For apexRfStatusTransmissionMode of 'annexA-DVB' not all slots
         may be selected.  Since a sub block represents a 48 MHz wide band and
         'annexA-DVB' channel spacing is currently a fixed 8 MHz, only the first
         6 slots in each sub block can be assigned.  Therefore, the 'annexA-DVB'
         assignments may be as follows:
            B1[b1(1..6), b2(9..14), b3(17..22), b4(25..30)],
            B2[b5(33..38), b6(41..46), b7(49..54), b8(57..62)],
            B3[b9(65..70), b10(73..78), b11(81..86), b12(89..94)], and
            B4[b13(97..102), b14(105..110), b15(113..118), b16(121..126)].
         The APEX3000 will automatically clear any assignments to the following
         slots:
            B1[b1(7, 8), b2(15, 16), b3(23, 24), b4(31, 32)],
            B2[b5(39, 40), b6(47, 48), b7(55, 56), b8(63, 64)],
            B3[b9(71, 72), b10(79, 80), b11(87, 88), b12(95, 96)], and
            B4[b13(103, 104), b14(111, 112), b15(119, 120), b16(127, 128)].
        "
::= { apexRfConfigBlade2ChannelEntry 3 }

apexRfConfigBlade2ChannelModeComboSelectAnnexA OBJECT-TYPE
    SYNTAX Integer32(1..4)
    MAX-ACCESS read-write
    STATUS current
    DESCRIPTION
        "QAM Mode Combination selection for Annex A.
         Mode combinations are configured in apexRfConfigBlade2ModesTable.
         Used only when apexRfStatusTransmissionMode 'annexA-DVB'.
        "
::= { apexRfConfigBlade2ChannelEntry 4 }

apexRfConfigBlade2ChannelModeComboSelectAnnexB OBJECT-TYPE
    SYNTAX Integer32(1..4)
    MAX-ACCESS read-write
    STATUS current
    DESCRIPTION
        "QAM Mode Combination selection for Annex B.
         Mode combinations are configured in apexRfConfigBlade2ModesTable.
         Used only when apexRfStatusTransmissionMode 'annexB-ATSC-DCII'.
        "
::= { apexRfConfigBlade2ChannelEntry 5 }

apexRfConfigBlade2ChannelModeComboSelectAnnexC OBJECT-TYPE
    SYNTAX Integer32(1..4)
    MAX-ACCESS read-write
    STATUS current
    DESCRIPTION
        "QAM Mode Combination selection for Annex C.
         Mode combinations are configured in apexRfConfigBlade2ModesTable.
         Used only when apexRfStatusTransmissionMode 'annexC-Asia-Pacific'.
        "
::= { apexRfConfigBlade2ChannelEntry 6 }

apexRfConfigBlade2ChannelRfLevelAdjust OBJECT-TYPE
    SYNTAX Integer32(-20..0)
    MAX-ACCESS read-write
    STATUS current
    DESCRIPTION
        "RF Level adjustment for the channel.
         
         Range is -2.0 dB to 0.0 dB relative to apexRfConfigBlade2RfPortRfLevel.
         Value is in 0.1 dB steps.
         
         Final RF Level after adjustment applied must be within >= -8.00 dB below
         and <= 4.00 dB above DRFI nominal for the number of channels in-use(*)
         based on max 48 channel output.
         
         (*) In-use = assigned a frequency, unmuted, and not suppressed.
        "
::= { apexRfConfigBlade2ChannelEntry 7 }

apexRfConfigBlade2ChannelTestMode OBJECT-TYPE
    SYNTAX QamChannelTestModeTYPE
    MAX-ACCESS read-write
    STATUS current
    DESCRIPTION
        "Test mode for the channel.
         
         RF Port diagnostic suppression configuration will override
         this setting.  (apexRfConfigBlade2RfPortDiagSuppressMode and
         apexRfConfigBlade2RfPortDiagSuppressChannel)
         
         Test mode status is reflected in apexRfStatusChannelOutputMode.
         
         noTest     - Test mode is off.  Channel is in normal operation.
         suppress   - Suppress the channel.
         cwtest     - CW test.
         prbs23m    - PRBS-23 with MPEG Sync.
         prbsUnique - Unique PRBS. Multiple channels configured in this
                      mode will transmit uncorrelated data. Pattern is
                      generated in the APEX.
         mpegNull   - MPEG Null packets.
         biPhase    - Bi-phase Mode (alternating symbols).
        "
::= { apexRfConfigBlade2ChannelEntry 8 }

apexRfConfigBlade2ChannelMute OBJECT-TYPE
    SYNTAX QamRfMuteTYPE
    MAX-ACCESS read-write
    STATUS current
    DESCRIPTION
        "Mute the QAM Channel.
        "
::= { apexRfConfigBlade2ChannelEntry 9 }


-- ------------------------------------------------------------------------------
--
-- apexRfConfigBlade3
--
-- apexRfConfigBlade3General
--

-- none


-- ------------------------------------------------------------------------------
--
-- apexRfConfigBlade3ModesTable
--

apexRfConfigBlade3ModesTable OBJECT-TYPE
    SYNTAX SEQUENCE OF ApexRfConfigBlade3ModesEntry
    MAX-ACCESS not-accessible
    STATUS current
    DESCRIPTION
        "Table of RF Mode Combinations for QAM Blade3.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade3 2 }

apexRfConfigBlade3ModesEntry OBJECT-TYPE
    SYNTAX ApexRfConfigBlade3ModesEntry
    MAX-ACCESS not-accessible
    STATUS current
    DESCRIPTION
        "RF Configuration Blade3 RF Mode Combinations Table Entry."
    INDEX { apexRfConfigBlade3ModesIndex }
::= { apexRfConfigBlade3ModesTable 1 }

ApexRfConfigBlade3ModesEntry ::= SEQUENCE
    {
     apexRfConfigBlade3ModesIndex                   Integer32,
     apexRfConfigBlade3ModesModulationModeAnnexB    QamRfModulationModeTYPE,
     apexRfConfigBlade3ModesInterleaverDepthAnnexB  QamRfInterleaverDepthAnnexBTYPE,
     apexRfConfigBlade3ModesModulationModeAnnexA    QamRfModulationModeTYPE,
     apexRfConfigBlade3ModesSymbolRateAnnexA        Integer32,
     apexRfConfigBlade3ModesModulationModeAnnexC    QamRfModulationModeTYPE,
     apexRfConfigBlade3ModesSymbolRateAnnexC        Integer32
    }

apexRfConfigBlade3ModesIndex OBJECT-TYPE
    SYNTAX Integer32(1..4)
    MAX-ACCESS not-accessible
    STATUS current
    DESCRIPTION
        "Index for RF Configuration Blade3 RF Mode Combinations Table.
        "
::= { apexRfConfigBlade3ModesEntry 1 }

apexRfConfigBlade3ModesModulationModeAnnexB OBJECT-TYPE
    SYNTAX QamRfModulationModeTYPE
    MAX-ACCESS read-write
    STATUS current
    DESCRIPTION
        "QAM RF Modulation mode for Annex B.
         Used only when apexRfStatusTransmissionMode 'annexB-ATSC-DCII'.
        "
::= { apexRfConfigBlade3ModesEntry 2 }

apexRfConfigBlade3ModesInterleaverDepthAnnexB OBJECT-TYPE
    SYNTAX QamRfInterleaverDepthAnnexBTYPE
    MAX-ACCESS read-write
    STATUS current
    DESCRIPTION
        "QAM RF Interleaver setting for Annex B.
         Used only when apexRfStatusTransmissionMode 'annexB-ATSC-DCII'.
        "
::= { apexRfConfigBlade3ModesEntry 3 }

apexRfConfigBlade3ModesModulationModeAnnexA OBJECT-TYPE
    SYNTAX QamRfModulationModeTYPE
    MAX-ACCESS read-write
    STATUS current
    DESCRIPTION
        "QAM RF Modulation mode for Annex A.
         Only used when apexRfStatusTransmissionMode is 'annexA-DVB'.
        "
::= { apexRfConfigBlade3ModesEntry 4 }

apexRfConfigBlade3ModesSymbolRateAnnexA OBJECT-TYPE
    SYNTAX Integer32(1000000..6980000)
    MAX-ACCESS read-write
    STATUS current
    DESCRIPTION
        "QAM RF Symbol Rate for Annex A.
         Only used when apexRfStatusTransmissionMode is 'annexA-DVB'.
         It is in symbols per second (sps) in 1000 sps steps.

         @Range(step=1000)
        "
::= { apexRfConfigBlade3ModesEntry 5 }

apexRfConfigBlade3ModesModulationModeAnnexC OBJECT-TYPE
    SYNTAX QamRfModulationModeTYPE
    MAX-ACCESS read-write
    STATUS current
    DESCRIPTION
        "QAM RF Modulation mode for Annex C.
         Used only when apexRfStatusTransmissionMode 'annexC-Asia-Pacific'.
        "
::= { apexRfConfigBlade3ModesEntry 6 }

apexRfConfigBlade3ModesSymbolRateAnnexC OBJECT-TYPE
    SYNTAX Integer32(800000..5310000)
    MAX-ACCESS read-write
    STATUS current
    DESCRIPTION
        "QAM RF Symbol Rate for Annex C.
         Only used when apexRfStatusTransmissionMode is 'annexC-Asia-Pacific'.
         It is in symbols per second (sps) in 1000 sps steps.

         @Range(step=1000)
        "
::= { apexRfConfigBlade3ModesEntry 7 }


-- ------------------------------------------------------------------------------
--
-- apexRfConfigBlade3RfPortTable
--

apexRfConfigBlade3RfPortTable OBJECT-TYPE
    SYNTAX SEQUENCE OF ApexRfConfigBlade3RfPortEntry
    MAX-ACCESS not-accessible
    STATUS current
    DESCRIPTION
        "Table of RF Port configuration for QAM Blade3.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade3 3 }

apexRfConfigBlade3RfPortEntry OBJECT-TYPE
    SYNTAX ApexRfConfigBlade3RfPortEntry
    MAX-ACCESS not-accessible
    STATUS current
    DESCRIPTION
        "Blade3 RF Port Configuration Table Entry."
    INDEX { apexRfConfigBlade3RfPortNum }
::= { apexRfConfigBlade3RfPortTable 1 }

ApexRfConfigBlade3RfPortEntry ::= SEQUENCE
    {
     apexRfConfigBlade3RfPortNum                   Integer32,
     apexRfConfigBlade3RfPortSpectrumInversion     QamRfSpectrumInversionTYPE,
     apexRfConfigBlade3RfPortMute                  QamRfMuteTYPE,
     apexRfConfigBlade3RfPortRfLevel               Integer32,
     apexRfConfigBlade3RfPortDiagSuppressMode      QamRfDiagSuppressModeTYPE,
     apexRfConfigBlade3RfPortDiagSuppressChannel   Integer32,
     apexRfConfigBlade3RfPortNprimeMax             Integer32,
     apexRfConfigBlade3RfPortNprimeMaxMode         AutomaticManualTYPE
    }

apexRfConfigBlade3RfPortNum OBJECT-TYPE
    SYNTAX Integer32(1..4)
    MAX-ACCESS not-accessible
    STATUS current
    DESCRIPTION
        "RF Port number on QAM Blade.
        "
::= { apexRfConfigBlade3RfPortEntry 1 }

apexRfConfigBlade3RfPortSpectrumInversion OBJECT-TYPE
    SYNTAX QamRfSpectrumInversionTYPE
    MAX-ACCESS read-write
    STATUS current
    DESCRIPTION
        "The Spectrum Inversion Setting of the QAM Channels
         on the RF Port.
        "
::= { apexRfConfigBlade3RfPortEntry 2 }

apexRfConfigBlade3RfPortMute OBJECT-TYPE
    SYNTAX QamRfMuteTYPE
    MAX-ACCESS read-write
    STATUS current
    DESCRIPTION
        "Mute the RF Port.  This will mute all QAM channels on the
         RF Port.
        "
::= { apexRfConfigBlade3RfPortEntry 3 }

apexRfConfigBlade3RfPortRfLevel OBJECT-TYPE
    SYNTAX Integer32(3000..5600)
    MAX-ACCESS read-write
    STATUS current
    DESCRIPTION
        "The RF level setting of each channel in-use(*) on the RF Port.
         
         Range is 30.00 to 56.00 dBmV per channel in 0.01 dBmV steps.
         
         Value must be within >= -8.00 dBmV below and <= 4.00 dBmV above DRFI nominal 
         for the number of channels in-use(*) based on max 48 channel output.
         
         (*) In-use = assigned a frequency, unmuted, and not suppressed.
        "
::= { apexRfConfigBlade3RfPortEntry 4 }

apexRfConfigBlade3RfPortDiagSuppressMode OBJECT-TYPE
    SYNTAX QamRfDiagSuppressModeTYPE
    MAX-ACCESS read-write
    STATUS current
    DESCRIPTION
        "Diagnostic Suppression Mode of the RF Port.
                 
         none               - No suppression.
         oneChannel         - One channel suppressed
         allChannelsButOne  - All channels suppressed except one
         allChannels        - All channels suppressed
         
         Use apexRfConfigBlade3RfPortDiagSuppressChannel to define the 'one'
         channel for 'oneChannel' and 'allChannelsButOne' modes.
         
         This setting will override apexRfConfigBlade3ChannelTestMode.
         
         Test mode status is reflected in apexRfStatusChannelOutputMode.
        "
::= { apexRfConfigBlade3RfPortEntry 5 }

apexRfConfigBlade3RfPortDiagSuppressChannel OBJECT-TYPE
    SYNTAX Integer32(1..64)
    MAX-ACCESS read-write
    STATUS current
    DESCRIPTION
        "Channel defined for Diagnostic Suppression.
         
         Used to define the 'one' channel for the 'oneChannel' and
         'allChannelsButOne' modes of apexRfConfigBlade3RfPortDiagSuppressMode.
         
         This setting will override apexRfConfigBlade3ChannelTestMode.
         
         Test mode status is reflected in apexRfStatusChannelOutputMode.
        "
::= { apexRfConfigBlade3RfPortEntry 6 }

apexRfConfigBlade3RfPortNprimeMax OBJECT-TYPE
    SYNTAX Integer32(0..64)
    MAX-ACCESS read-write
    STATUS current
    DESCRIPTION
        "User defined DRFI N'max value used by APEX when RfPortNprimeMaxMode
         is 'manual'.  This parameter is ignored when RfPortNprimeMaxMode
         is 'automatic'.
         
         N'max must be greater than or equal to the number of channels
         in-use (assigned a frequency, unmuted, and not suppressed).
         
         Using the RfPortNprimeMax value guarantees glitchless RF port
         reconfiguration as per the DRFI specification described below.
         
         NOTE: RF performance will be degraded for large differences
               between the number of channels in-use and the user selected
               N'max value.
         
         The N'max value in use by the APEX is reflected in apexRfStatusRfPortNprimeMax.
         
         From CM-SP-DRFI-I10-100611:
         A CMTS or EQAM capable of generating more than eight channels per
         physical RF port MUST be capable of glitchless reconfiguration over
         a range of active channels from ceiling[7*N'max/8] to N'max. Channels
         which are undergoing configuration changes are referred to as the
         'changed channels.' The channels which are active and are not being
         reconfigured are referred to as the 'continuous channels'. Each DRFI
         modulator capable of generating more than eight channels per physical
         RF port MUST accept a command setting N'max. Glitchless reconfiguration
         consists of any of the following actions while introducing no
         discontinuity or detriment to the continuous channels, where the
         modulator is operating in a valid DRFI-required mode both before and
         after the reconfiguration with an active number of channels staying in
         the range {ceiling[7*N'max/8], N'max}: adding and/or deleting one or
         more channels, and/or moving some channels to new RF carrier
         frequencies, and/or changing the interleaver depth, modulation, power
         level, or frequency on one or more channels. Any change in the
         modulation characteristics (power level, modulation density, interleaver
         parameters, center frequency) of a channel excuses that channel from
         being required to operate in a glitchless manner. For example, changing
         the power per channel of a given channel means that channel is not
         considered a continuous channel for the purposes of the glitchless
         modulation requirements. Glitchless operation is not required when N'max
         is changed, even if no reconfigurations accompany the change in N'max.
        "
::= { apexRfConfigBlade3RfPortEntry 7 }

apexRfConfigBlade3RfPortNprimeMaxMode OBJECT-TYPE
    SYNTAX AutomaticManualTYPE
    MAX-ACCESS read-write
    STATUS current
    DESCRIPTION
        "DRFI N'max configuration mode.
        
         'automatic' - In this mode the APEX is responsible for selecting the N'max
                       and will automatically set N'max to the number of channels in-use
                       (assigned a frequency, unmuted, and not suppressed).  This guarantees
                       optimal RF performance for the number of channels in-use but
                       reconfiguration of the RF port may cause RF glitches.  If,
                       after testing, the user determines reconfiguration of RF ports
                       in 'standard' mode causes unacceptable RF interruption, the
                       'advanced' mode may be used.  
         
         'manual'    - In this advanced mode the user is responsible for manually setting
                       N'max in the RfPortNprimeMax parameter.  The APEX will use the value
                       in the RfPortNprimeMax parameter.  This will guarantee glitchless RF
                       port reconfiguration as per the DRFI specification described below.
                       NOTE: RF performance will be degraded for large differences
                             between the number of channels in-use and the user selected
                             N'max value.
         
         The N'max value in use by the APEX is reflected in apexRfStatusRfPortNprimeMax.
         
         From CM-SP-DRFI-I10-100611:
         A CMTS or EQAM capable of generating more than eight channels per
         physical RF port MUST be capable of glitchless reconfiguration over
         a range of active channels from ceiling[7*N'max/8] to N'max. Channels
         which are undergoing configuration changes are referred to as the
         'changed channels.' The channels which are active and are not being
         reconfigured are referred to as the 'continuous channels'. Each DRFI
         modulator capable of generating more than eight channels per physical
         RF port MUST accept a command setting N'max. Glitchless reconfiguration
         consists of any of the following actions while introducing no
         discontinuity or detriment to the continuous channels, where the
         modulator is operating in a valid DRFI-required mode both before and
         after the reconfiguration with an active number of channels staying in
         the range {ceiling[7*N'max/8], N'max}: adding and/or deleting one or
         more channels, and/or moving some channels to new RF carrier
         frequencies, and/or changing the interleaver depth, modulation, power
         level, or frequency on one or more channels. Any change in the
         modulation characteristics (power level, modulation density, interleaver
         parameters, center frequency) of a channel excuses that channel from
         being required to operate in a glitchless manner. For example, changing
         the power per channel of a given channel means that channel is not
         considered a continuous channel for the purposes of the glitchless
         modulation requirements. Glitchless operation is not required when N'max
         is changed, even if no reconfigurations accompany the change in N'max.
        "
::= { apexRfConfigBlade3RfPortEntry 8 }


-- ------------------------------------------------------------------------------
--
-- apexRfConfigBlade3SuperBlockFreqTable
--

apexRfConfigBlade3SuperBlockFreqTable OBJECT-TYPE
    SYNTAX SEQUENCE OF ApexRfConfigBlade3SuperBlockFreqEntry
    MAX-ACCESS not-accessible
    STATUS current
    DESCRIPTION
        "Table of RF Port Super Block Frequency configuration for QAM Blade3.
         
         **** NOTE: Super Block Frequency configuration is currently limited:
         ****       - Super blocks cannot overlap.
         ****       - Super blocks must be in order 1..4 from low to high frequency.
         ****       - Super block 4 frequency must be selected such that the center
         ****         frequency of the last channel of the block is no greater than
         ****         the MAX frequency range (i.e., SB 4 freq <= 813000000 Hz).
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade3 4 }

apexRfConfigBlade3SuperBlockFreqEntry OBJECT-TYPE
    SYNTAX ApexRfConfigBlade3SuperBlockFreqEntry
    MAX-ACCESS not-accessible
    STATUS current
    DESCRIPTION
        "Blade3 RF Port Super Block Frequency Configuration Table Entry."
    INDEX { apexRfConfigBlade3SuperBlockFreqRfPortNum,
            apexRfConfigBlade3SuperBlockFreqBlockNum }
::= { apexRfConfigBlade3SuperBlockFreqTable 1 }

ApexRfConfigBlade3SuperBlockFreqEntry ::= SEQUENCE
    {
     apexRfConfigBlade3SuperBlockFreqRfPortNum  Integer32,
     apexRfConfigBlade3SuperBlockFreqBlockNum   Integer32,
     apexRfConfigBlade3SuperBlockFreqAnnexB     Integer32,
     apexRfConfigBlade3SuperBlockFreqAnnexC     Integer32,
     apexRfConfigBlade3SuperBlockFreqAnnexA     Integer32
    }

apexRfConfigBlade3SuperBlockFreqRfPortNum OBJECT-TYPE
    SYNTAX Integer32(1..4)
    MAX-ACCESS not-accessible
    STATUS current
    DESCRIPTION
        "RF Port number on QAM Blade.
        "
::= { apexRfConfigBlade3SuperBlockFreqEntry 1 }

apexRfConfigBlade3SuperBlockFreqBlockNum OBJECT-TYPE
    SYNTAX Integer32(1..4)
    MAX-ACCESS not-accessible
    STATUS current
    DESCRIPTION
        "Super-block number on RF Port.
        "
::= { apexRfConfigBlade3SuperBlockFreqEntry 2 }

apexRfConfigBlade3SuperBlockFreqAnnexB OBJECT-TYPE
    SYNTAX Integer32(57000000..999000000)
    MAX-ACCESS read-write
    STATUS current
    DESCRIPTION
        "Center frequency of first channel of super-block for Annex B.
         This value must be in Hz in the range 57,000,000 Hz to 999,000,000 Hz
         in 125,000 Hz steps.
         Used only when apexRfStatusTransmissionMode 'annexB-ATSC-DCII'.

         @Range(step=125000)
        "
::= { apexRfConfigBlade3SuperBlockFreqEntry 3 }

apexRfConfigBlade3SuperBlockFreqAnnexC OBJECT-TYPE
    SYNTAX Integer32(57000000..999000000)
    MAX-ACCESS read-write
    STATUS current
    DESCRIPTION
        "Center frequency of first channel of super-block for Annex C.
         This value must be in Hz in the range 57,000,000 Hz to 999,000,000 Hz
         in 125,000 Hz steps.
         Used only when apexRfStatusTransmissionMode 'annexC-Asia-Pacific'.

         @Range(step=125000)
        "
::= { apexRfConfigBlade3SuperBlockFreqEntry 4 }

apexRfConfigBlade3SuperBlockFreqAnnexA OBJECT-TYPE
    SYNTAX Integer32(85000000..999000000)
    MAX-ACCESS read-write
    STATUS current
    DESCRIPTION
        "Center frequency of first channel of super-block for Annex A.
         This value must be in Hz in the range 85,000,000 Hz to 999,000,000 Hz
         in 125,000 Hz steps.
         Used only when apexRfStatusTransmissionMode 'annexA-DVB'.

         @Range(step=125000)
        "
::= { apexRfConfigBlade3SuperBlockFreqEntry 5 }


-- ------------------------------------------------------------------------------
--
-- apexRfConfigBlade3SubBlockFreqTable
--

apexRfConfigBlade3SubBlockFreqTable OBJECT-TYPE
    SYNTAX SEQUENCE OF ApexRfConfigBlade3SubBlockFreqEntry
    MAX-ACCESS not-accessible
    STATUS current
    DESCRIPTION
        "TABLE NOT SUPPORTED.
         
         Table of RF Port Sub Block Frequency configuration for QAM Blade3.
         
         **** NOTE: This table is currently unsupported in APEX3000.
         ****       APEX3000 will set values consistent with settings
         ****       in blade Super Block Frequency Table.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade3 5 }

apexRfConfigBlade3SubBlockFreqEntry OBJECT-TYPE
    SYNTAX ApexRfConfigBlade3SubBlockFreqEntry
    MAX-ACCESS not-accessible
    STATUS current
    DESCRIPTION
        "Blade3 RF Port Sub Block Frequency Configuration Table Entry."
    INDEX { apexRfConfigBlade3SubBlockFreqRfPortNum,
            apexRfConfigBlade3SubBlockFreqBlockNum }
::= { apexRfConfigBlade3SubBlockFreqTable 1 }

ApexRfConfigBlade3SubBlockFreqEntry ::= SEQUENCE
    {
     apexRfConfigBlade3SubBlockFreqRfPortNum      Integer32,
     apexRfConfigBlade3SubBlockFreqBlockNum       Integer32,
     apexRfConfigBlade3SubBlockFreqAnnexB         Integer32,
     apexRfConfigBlade3SubBlockFreqAnnexC         Integer32,
     apexRfConfigBlade3SubBlockFreqAnnexA         Integer32,
     apexRfConfigBlade3SubBlockChanSpacingAnnexA  Integer32
    }

apexRfConfigBlade3SubBlockFreqRfPortNum OBJECT-TYPE
    SYNTAX Integer32(1..4)
    MAX-ACCESS not-accessible
    STATUS current
    DESCRIPTION
        "RF Port number on QAM Blade.
        "
::= { apexRfConfigBlade3SubBlockFreqEntry 1 }

apexRfConfigBlade3SubBlockFreqBlockNum OBJECT-TYPE
    SYNTAX Integer32(1..16)
    MAX-ACCESS not-accessible
    STATUS current
    DESCRIPTION
        "Sub-block number on RF Port.
        "
::= { apexRfConfigBlade3SubBlockFreqEntry 2 }

apexRfConfigBlade3SubBlockFreqAnnexB OBJECT-TYPE
    SYNTAX Integer32(57000000..999000000)
    MAX-ACCESS read-write
    STATUS current
    DESCRIPTION
        "Center frequency of first channel of sub-block for Annex B.
         This value must be in Hz in the range 57,000,000 Hz to 999,000,000 Hz
         in 125,000 Hz steps.
         Used only when apexRfStatusTransmissionMode 'annexB-ATSC-DCII'.

         @Range(step=125000)
        "
::= { apexRfConfigBlade3SubBlockFreqEntry 3 }

apexRfConfigBlade3SubBlockFreqAnnexC OBJECT-TYPE
    SYNTAX Integer32(57000000..999000000)
    MAX-ACCESS read-write
    STATUS current
    DESCRIPTION
        "Center frequency of first channel of sub-block for Annex C.
         This value must be in Hz in the range 57,000,000 Hz to 999,000,000 Hz
         in 125,000 Hz steps.
         Used only when apexRfStatusTransmissionMode 'annexC-Asia-Pacific'.

         @Range(step=125000)
        "
::= { apexRfConfigBlade3SubBlockFreqEntry 4 }

apexRfConfigBlade3SubBlockFreqAnnexA OBJECT-TYPE
    SYNTAX Integer32(85000000..999000000)
    MAX-ACCESS read-write
    STATUS current
    DESCRIPTION
        "Center frequency of first channel of sub-block for Annex A.
         This value must be in Hz in the range 85,000,000 Hz to 999,000,000 Hz
         in 125,000 Hz steps.
         Used only when apexRfStatusTransmissionMode 'annexA-DVB'.

         @Range(step=125000)
        "
::= { apexRfConfigBlade3SubBlockFreqEntry 5 }

apexRfConfigBlade3SubBlockChanSpacingAnnexA OBJECT-TYPE
    SYNTAX Integer32(1000000..8000000)
    MAX-ACCESS read-write
    STATUS current
    DESCRIPTION
        "*** This entry is not supported. ***
         
         Channel spacing of sub-block for Annex A.
         This value must be in Hz in the range 1,000,000 Hz to 8,000,000 Hz
         in 500,000 Hz steps.
         Used only when apexRfStatusTransmissionMode 'annexA-DVB'.

         @Range(step=500000)
        "
::= { apexRfConfigBlade3SubBlockFreqEntry 6 }


-- ------------------------------------------------------------------------------
--
-- apexRfConfigBlade3ChannelTable
--

apexRfConfigBlade3ChannelTable OBJECT-TYPE
    SYNTAX SEQUENCE OF ApexRfConfigBlade3ChannelEntry
    MAX-ACCESS not-accessible
    STATUS current
    DESCRIPTION
        "Table of QAM Channel configuration for QAM Blade3.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade3 6 }

apexRfConfigBlade3ChannelEntry OBJECT-TYPE
    SYNTAX ApexRfConfigBlade3ChannelEntry
    MAX-ACCESS not-accessible
    STATUS current
    DESCRIPTION
        "Blade3 QAM Channel Configuration Table Entry."
    INDEX { apexRfConfigBlade3ChannelRfPortNum,
            apexRfConfigBlade3ChannelChanNum }
::= { apexRfConfigBlade3ChannelTable 1 }

ApexRfConfigBlade3ChannelEntry ::= SEQUENCE
    {
     apexRfConfigBlade3ChannelRfPortNum              Integer32,
     apexRfConfigBlade3ChannelChanNum                Integer32,
     apexRfConfigBlade3ChannelFrequencyGridSelect    Integer32,
     apexRfConfigBlade3ChannelModeComboSelectAnnexA  Integer32,
     apexRfConfigBlade3ChannelModeComboSelectAnnexB  Integer32,
     apexRfConfigBlade3ChannelModeComboSelectAnnexC  Integer32,
     apexRfConfigBlade3ChannelRfLevelAdjust          Integer32,
     apexRfConfigBlade3ChannelTestMode               QamChannelTestModeTYPE,
     apexRfConfigBlade3ChannelMute                   QamRfMuteTYPE
    }

apexRfConfigBlade3ChannelRfPortNum OBJECT-TYPE
    SYNTAX Integer32(1..4)
    MAX-ACCESS not-accessible
    STATUS current
    DESCRIPTION
        "RF Port number on QAM Blade.
        "
::= { apexRfConfigBlade3ChannelEntry 1 }

apexRfConfigBlade3ChannelChanNum OBJECT-TYPE
    SYNTAX Integer32(1..64)
    MAX-ACCESS not-accessible
    STATUS current
    DESCRIPTION
        "QAM channel number on RF Port.
        "
::= { apexRfConfigBlade3ChannelEntry 2 }

apexRfConfigBlade3ChannelFrequencyGridSelect OBJECT-TYPE
    SYNTAX Integer32(0..128)
    MAX-ACCESS read-write
    STATUS current
    DESCRIPTION
        "RF Port frequency grid slot selection for this channel.
         Zero indicates the channel is not in use (disabled).
         
         The frequency is selected from a grid of 128 total frequency assignment
         selections (or 'slots').  The grid is divided into 4 super blocks (192
         MHz wide) with 32 assignment slots each.  Each super block is divided
         into 4 sub blocks (48 MHz wide) with 8 assignment slots each.  Using 'B'
         for super blocks and 'b' sub blocks numbering of super and sub blocks is
         B1..B4 and b1..b16 respectively.  The sub blocks are contained in
         superblocks as follows:
            B1[b1..b4],
            B2[b5..b8],
            B3[b9..b12], and
            B4[b13..b16].
         Numbering of the slots within the blocks is as follows:
            B1[b1(1..8), b2(9..16), b3(17..24), b4(25..32)],
            B2[b5(33..40), b6(41..48), b7(49..56), b8(57..64)],
            B3[b9(65..72), b10(73..80), b11(81..88), b12(89..96)], and
            B4[b13(97..105), b14(106..112), b15(113..120), b16(121..128)].

         Annex B/C: For apexRfStatusTransmissionMode of 'annexB-ATSC-DCII' or
         'annexC-Asia-Pacific' the full range of slots [1..128] may be selected.

         Annex A: For apexRfStatusTransmissionMode of 'annexA-DVB' not all slots
         may be selected.  Since a sub block represents a 48 MHz wide band and
         'annexA-DVB' channel spacing is currently a fixed 8 MHz, only the first
         6 slots in each sub block can be assigned.  Therefore, the 'annexA-DVB'
         assignments may be as follows:
            B1[b1(1..6), b2(9..14), b3(17..22), b4(25..30)],
            B2[b5(33..38), b6(41..46), b7(49..54), b8(57..62)],
            B3[b9(65..70), b10(73..78), b11(81..86), b12(89..94)], and
            B4[b13(97..102), b14(105..110), b15(113..118), b16(121..126)].
         The APEX3000 will automatically clear any assignments to the following
         slots:
            B1[b1(7, 8), b2(15, 16), b3(23, 24), b4(31, 32)],
            B2[b5(39, 40), b6(47, 48), b7(55, 56), b8(63, 64)],
            B3[b9(71, 72), b10(79, 80), b11(87, 88), b12(95, 96)], and
            B4[b13(103, 104), b14(111, 112), b15(119, 120), b16(127, 128)].
        "
::= { apexRfConfigBlade3ChannelEntry 3 }

apexRfConfigBlade3ChannelModeComboSelectAnnexA OBJECT-TYPE
    SYNTAX Integer32(1..4)
    MAX-ACCESS read-write
    STATUS current
    DESCRIPTION
        "QAM Mode Combination selection for Annex A.
         Mode combinations are configured in apexRfConfigBlade3ModesTable.
         Used only when apexRfStatusTransmissionMode 'annexA-DVB'.
        "
::= { apexRfConfigBlade3ChannelEntry 4 }

apexRfConfigBlade3ChannelModeComboSelectAnnexB OBJECT-TYPE
    SYNTAX Integer32(1..4)
    MAX-ACCESS read-write
    STATUS current
    DESCRIPTION
        "QAM Mode Combination selection for Annex B.
         Mode combinations are configured in apexRfConfigBlade3ModesTable.
         Used only when apexRfStatusTransmissionMode 'annexB-ATSC-DCII'.
        "
::= { apexRfConfigBlade3ChannelEntry 5 }

apexRfConfigBlade3ChannelModeComboSelectAnnexC OBJECT-TYPE
    SYNTAX Integer32(1..4)
    MAX-ACCESS read-write
    STATUS current
    DESCRIPTION
        "QAM Mode Combination selection for Annex C.
         Mode combinations are configured in apexRfConfigBlade3ModesTable.
         Used only when apexRfStatusTransmissionMode 'annexC-Asia-Pacific'.
        "
::= { apexRfConfigBlade3ChannelEntry 6 }

apexRfConfigBlade3ChannelRfLevelAdjust OBJECT-TYPE
    SYNTAX Integer32(-20..0)
    MAX-ACCESS read-write
    STATUS current
    DESCRIPTION
        "RF Level adjustment for the channel.
         
         Range is -2.0 dB to 0.0 dB relative to apexRfConfigBlade3RfPortRfLevel.
         Value is in 0.1 dB steps.
         
         Final RF Level after adjustment applied must be within >= -8.00 dB below
         and <= 4.00 dB above DRFI nominal for the number of channels in-use(*)
         based on max 48 channel output.
         
         (*) In-use = assigned a frequency, unmuted, and not suppressed.
        "
::= { apexRfConfigBlade3ChannelEntry 7 }

apexRfConfigBlade3ChannelTestMode OBJECT-TYPE
    SYNTAX QamChannelTestModeTYPE
    MAX-ACCESS read-write
    STATUS current
    DESCRIPTION
        "Test mode for the channel.
         
         RF Port diagnostic suppression configuration will override
         this setting.  (apexRfConfigBlade3RfPortDiagSuppressMode and
         apexRfConfigBlade3RfPortDiagSuppressChannel)
         
         Test mode status is reflected in apexRfStatusChannelOutputMode.
         
         noTest     - Test mode is off.  Channel is in normal operation.
         suppress   - Suppress the channel.
         cwtest     - CW test.
         prbs23m    - PRBS-23 with MPEG Sync.
         prbsUnique - Unique PRBS. Multiple channels configured in this
                      mode will transmit uncorrelated data. Pattern is
                      generated in the APEX.
         mpegNull   - MPEG Null packets.
         biPhase    - Bi-phase Mode (alternating symbols).
        "
::= { apexRfConfigBlade3ChannelEntry 8 }

apexRfConfigBlade3ChannelMute OBJECT-TYPE
    SYNTAX QamRfMuteTYPE
    MAX-ACCESS read-write
    STATUS current
    DESCRIPTION
        "Mute the QAM Channel.
        "
::= { apexRfConfigBlade3ChannelEntry 9 }


-- ------------------------------------------------------------------------------
--
-- apexRfConfigBlade4
--
-- apexRfConfigBlade4General
--

-- none


-- ------------------------------------------------------------------------------
--
-- apexRfConfigBlade4ModesTable
--

apexRfConfigBlade4ModesTable OBJECT-TYPE
    SYNTAX SEQUENCE OF ApexRfConfigBlade4ModesEntry
    MAX-ACCESS not-accessible
    STATUS current
    DESCRIPTION
        "Table of RF Mode Combinations for QAM Blade4.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade4 2 }

apexRfConfigBlade4ModesEntry OBJECT-TYPE
    SYNTAX ApexRfConfigBlade4ModesEntry
    MAX-ACCESS not-accessible
    STATUS current
    DESCRIPTION
        "RF Configuration Blade4 RF Mode Combinations Table Entry."
    INDEX { apexRfConfigBlade4ModesIndex }
::= { apexRfConfigBlade4ModesTable 1 }

ApexRfConfigBlade4ModesEntry ::= SEQUENCE
    {
     apexRfConfigBlade4ModesIndex                   Integer32,
     apexRfConfigBlade4ModesModulationModeAnnexB    QamRfModulationModeTYPE,
     apexRfConfigBlade4ModesInterleaverDepthAnnexB  QamRfInterleaverDepthAnnexBTYPE,
     apexRfConfigBlade4ModesModulationModeAnnexA    QamRfModulationModeTYPE,
     apexRfConfigBlade4ModesSymbolRateAnnexA        Integer32,
     apexRfConfigBlade4ModesModulationModeAnnexC    QamRfModulationModeTYPE,
     apexRfConfigBlade4ModesSymbolRateAnnexC        Integer32
    }

apexRfConfigBlade4ModesIndex OBJECT-TYPE
    SYNTAX Integer32(1..4)
    MAX-ACCESS not-accessible
    STATUS current
    DESCRIPTION
        "Index for RF Configuration Blade4 RF Mode Combinations Table.
        "
::= { apexRfConfigBlade4ModesEntry 1 }

apexRfConfigBlade4ModesModulationModeAnnexB OBJECT-TYPE
    SYNTAX QamRfModulationModeTYPE
    MAX-ACCESS read-write
    STATUS current
    DESCRIPTION
        "QAM RF Modulation mode for Annex B.
         Used only when apexRfStatusTransmissionMode 'annexB-ATSC-DCII'.
        "
::= { apexRfConfigBlade4ModesEntry 2 }

apexRfConfigBlade4ModesInterleaverDepthAnnexB OBJECT-TYPE
    SYNTAX QamRfInterleaverDepthAnnexBTYPE
    MAX-ACCESS read-write
    STATUS current
    DESCRIPTION
        "QAM RF Interleaver setting for Annex B.
         Used only when apexRfStatusTransmissionMode 'annexB-ATSC-DCII'.
        "
::= { apexRfConfigBlade4ModesEntry 3 }

apexRfConfigBlade4ModesModulationModeAnnexA OBJECT-TYPE
    SYNTAX QamRfModulationModeTYPE
    MAX-ACCESS read-write
    STATUS current
    DESCRIPTION
        "QAM RF Modulation mode for Annex A.
         Only used when apexRfStatusTransmissionMode is 'annexA-DVB'.
        "
::= { apexRfConfigBlade4ModesEntry 4 }

apexRfConfigBlade4ModesSymbolRateAnnexA OBJECT-TYPE
    SYNTAX Integer32(1000000..6980000)
    MAX-ACCESS read-write
    STATUS current
    DESCRIPTION
        "QAM RF Symbol Rate for Annex A.
         Only used when apexRfStatusTransmissionMode is 'annexA-DVB'.
         It is in symbols per second (sps) in 1000 sps steps.

         @Range(step=1000)
        "
::= { apexRfConfigBlade4ModesEntry 5 }

apexRfConfigBlade4ModesModulationModeAnnexC OBJECT-TYPE
    SYNTAX QamRfModulationModeTYPE
    MAX-ACCESS read-write
    STATUS current
    DESCRIPTION
        "QAM RF Modulation mode for Annex C.
         Used only when apexRfStatusTransmissionMode 'annexC-Asia-Pacific'.
        "
::= { apexRfConfigBlade4ModesEntry 6 }

apexRfConfigBlade4ModesSymbolRateAnnexC OBJECT-TYPE
    SYNTAX Integer32(800000..5310000)
    MAX-ACCESS read-write
    STATUS current
    DESCRIPTION
        "QAM RF Symbol Rate for Annex C.
         Only used when apexRfStatusTransmissionMode is 'annexC-Asia-Pacific'.
         It is in symbols per second (sps) in 1000 sps steps.

         @Range(step=1000)
        "
::= { apexRfConfigBlade4ModesEntry 7 }


-- ------------------------------------------------------------------------------
--
-- apexRfConfigBlade4RfPortTable
--

apexRfConfigBlade4RfPortTable OBJECT-TYPE
    SYNTAX SEQUENCE OF ApexRfConfigBlade4RfPortEntry
    MAX-ACCESS not-accessible
    STATUS current
    DESCRIPTION
        "Table of RF Port configuration for QAM Blade4.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade4 3 }

apexRfConfigBlade4RfPortEntry OBJECT-TYPE
    SYNTAX ApexRfConfigBlade4RfPortEntry
    MAX-ACCESS not-accessible
    STATUS current
    DESCRIPTION
        "Blade4 RF Port Configuration Table Entry."
    INDEX { apexRfConfigBlade4RfPortNum }
::= { apexRfConfigBlade4RfPortTable 1 }

ApexRfConfigBlade4RfPortEntry ::= SEQUENCE
    {
     apexRfConfigBlade4RfPortNum                   Integer32,
     apexRfConfigBlade4RfPortSpectrumInversion     QamRfSpectrumInversionTYPE,
     apexRfConfigBlade4RfPortMute                  QamRfMuteTYPE,
     apexRfConfigBlade4RfPortRfLevel               Integer32,
     apexRfConfigBlade4RfPortDiagSuppressMode      QamRfDiagSuppressModeTYPE,
     apexRfConfigBlade4RfPortDiagSuppressChannel   Integer32,
     apexRfConfigBlade4RfPortNprimeMax             Integer32,
     apexRfConfigBlade4RfPortNprimeMaxMode         AutomaticManualTYPE
    }

apexRfConfigBlade4RfPortNum OBJECT-TYPE
    SYNTAX Integer32(1..4)
    MAX-ACCESS not-accessible
    STATUS current
    DESCRIPTION
        "RF Port number on QAM Blade.
        "
::= { apexRfConfigBlade4RfPortEntry 1 }

apexRfConfigBlade4RfPortSpectrumInversion OBJECT-TYPE
    SYNTAX QamRfSpectrumInversionTYPE
    MAX-ACCESS read-write
    STATUS current
    DESCRIPTION
        "The Spectrum Inversion Setting of the QAM Channels
         on the RF Port.
        "
::= { apexRfConfigBlade4RfPortEntry 2 }

apexRfConfigBlade4RfPortMute OBJECT-TYPE
    SYNTAX QamRfMuteTYPE
    MAX-ACCESS read-write
    STATUS current
    DESCRIPTION
        "Mute the RF Port.  This will mute all QAM channels on the
         RF Port.
        "
::= { apexRfConfigBlade4RfPortEntry 3 }

apexRfConfigBlade4RfPortRfLevel OBJECT-TYPE
    SYNTAX Integer32(3000..5600)
    MAX-ACCESS read-write
    STATUS current
    DESCRIPTION
        "The RF level setting of each channel in-use(*) on the RF Port.
         
         Range is 30.00 to 56.00 dBmV per channel in 0.01 dBmV steps.
         
         Value must be within >= -8.00 dBmV below and <= 4.00 dBmV above DRFI nominal 
         for the number of channels in-use(*) based on max 48 channel output.
         
         (*) In-use = assigned a frequency, unmuted, and not suppressed.
        "
::= { apexRfConfigBlade4RfPortEntry 4 }

apexRfConfigBlade4RfPortDiagSuppressMode OBJECT-TYPE
    SYNTAX QamRfDiagSuppressModeTYPE
    MAX-ACCESS read-write
    STATUS current
    DESCRIPTION
        "Diagnostic Suppression Mode of the RF Port.
                 
         none               - No suppression.
         oneChannel         - One channel suppressed
         allChannelsButOne  - All channels suppressed except one
         allChannels        - All channels suppressed
         
         Use apexRfConfigBlade4RfPortDiagSuppressChannel to define the 'one'
         channel for 'oneChannel' and 'allChannelsButOne' modes.
         
         This setting will override apexRfConfigBlade4ChannelTestMode.
         
         Test mode status is reflected in apexRfStatusChannelOutputMode.
        "
::= { apexRfConfigBlade4RfPortEntry 5 }

apexRfConfigBlade4RfPortDiagSuppressChannel OBJECT-TYPE
    SYNTAX Integer32(1..64)
    MAX-ACCESS read-write
    STATUS current
    DESCRIPTION
        "Channel defined for Diagnostic Suppression.
         
         Used to define the 'one' channel for the 'oneChannel' and
         'allChannelsButOne' modes of apexRfConfigBlade4RfPortDiagSuppressMode.
         
         This setting will override apexRfConfigBlade4ChannelTestMode.
         
         Test mode status is reflected in apexRfStatusChannelOutputMode.
        "
::= { apexRfConfigBlade4RfPortEntry 6 }

apexRfConfigBlade4RfPortNprimeMax OBJECT-TYPE
    SYNTAX Integer32(0..64)
    MAX-ACCESS read-write
    STATUS current
    DESCRIPTION
        "User defined DRFI N'max value used by APEX when RfPortNprimeMaxMode
         is 'manual'.  This parameter is ignored when RfPortNprimeMaxMode
         is 'automatic'.
         
         N'max must be greater than or equal to the number of channels
         in-use (assigned a frequency, unmuted, and not suppressed).
         
         Using the RfPortNprimeMax value guarantees glitchless RF port
         reconfiguration as per the DRFI specification described below.
         
         NOTE: RF performance will be degraded for large differences
               between the number of channels in-use and the user selected
               N'max value.
         
         The N'max value in use by the APEX is reflected in apexRfStatusRfPortNprimeMax.
         
         From CM-SP-DRFI-I10-100611:
         A CMTS or EQAM capable of generating more than eight channels per
         physical RF port MUST be capable of glitchless reconfiguration over
         a range of active channels from ceiling[7*N'max/8] to N'max. Channels
         which are undergoing configuration changes are referred to as the
         'changed channels.' The channels which are active and are not being
         reconfigured are referred to as the 'continuous channels'. Each DRFI
         modulator capable of generating more than eight channels per physical
         RF port MUST accept a command setting N'max. Glitchless reconfiguration
         consists of any of the following actions while introducing no
         discontinuity or detriment to the continuous channels, where the
         modulator is operating in a valid DRFI-required mode both before and
         after the reconfiguration with an active number of channels staying in
         the range {ceiling[7*N'max/8], N'max}: adding and/or deleting one or
         more channels, and/or moving some channels to new RF carrier
         frequencies, and/or changing the interleaver depth, modulation, power
         level, or frequency on one or more channels. Any change in the
         modulation characteristics (power level, modulation density, interleaver
         parameters, center frequency) of a channel excuses that channel from
         being required to operate in a glitchless manner. For example, changing
         the power per channel of a given channel means that channel is not
         considered a continuous channel for the purposes of the glitchless
         modulation requirements. Glitchless operation is not required when N'max
         is changed, even if no reconfigurations accompany the change in N'max.
        "
::= { apexRfConfigBlade4RfPortEntry 7 }

apexRfConfigBlade4RfPortNprimeMaxMode OBJECT-TYPE
    SYNTAX AutomaticManualTYPE
    MAX-ACCESS read-write
    STATUS current
    DESCRIPTION
        "DRFI N'max configuration mode.
        
         'automatic' - In this mode the APEX is responsible for selecting the N'max
                       and will automatically set N'max to the number of channels in-use
                       (assigned a frequency, unmuted, and not suppressed).  This guarantees
                       optimal RF performance for the number of channels in-use but
                       reconfiguration of the RF port may cause RF glitches.  If,
                       after testing, the user determines reconfiguration of RF ports
                       in 'standard' mode causes unacceptable RF interruption, the
                       'advanced' mode may be used.  
         
         'manual'    - In this advanced mode the user is responsible for manually setting
                       N'max in the RfPortNprimeMax parameter.  The APEX will use the value
                       in the RfPortNprimeMax parameter.  This will guarantee glitchless RF
                       port reconfiguration as per the DRFI specification described below.
                       NOTE: RF performance will be degraded for large differences
                             between the number of channels in-use and the user selected
                             N'max value.
         
         The N'max value in use by the APEX is reflected in apexRfStatusRfPortNprimeMax.
         
         From CM-SP-DRFI-I10-100611:
         A CMTS or EQAM capable of generating more than eight channels per
         physical RF port MUST be capable of glitchless reconfiguration over
         a range of active channels from ceiling[7*N'max/8] to N'max. Channels
         which are undergoing configuration changes are referred to as the
         'changed channels.' The channels which are active and are not being
         reconfigured are referred to as the 'continuous channels'. Each DRFI
         modulator capable of generating more than eight channels per physical
         RF port MUST accept a command setting N'max. Glitchless reconfiguration
         consists of any of the following actions while introducing no
         discontinuity or detriment to the continuous channels, where the
         modulator is operating in a valid DRFI-required mode both before and
         after the reconfiguration with an active number of channels staying in
         the range {ceiling[7*N'max/8], N'max}: adding and/or deleting one or
         more channels, and/or moving some channels to new RF carrier
         frequencies, and/or changing the interleaver depth, modulation, power
         level, or frequency on one or more channels. Any change in the
         modulation characteristics (power level, modulation density, interleaver
         parameters, center frequency) of a channel excuses that channel from
         being required to operate in a glitchless manner. For example, changing
         the power per channel of a given channel means that channel is not
         considered a continuous channel for the purposes of the glitchless
         modulation requirements. Glitchless operation is not required when N'max
         is changed, even if no reconfigurations accompany the change in N'max.
        "
::= { apexRfConfigBlade4RfPortEntry 8 }


-- ------------------------------------------------------------------------------
--
-- apexRfConfigBlade4SuperBlockFreqTable
--

apexRfConfigBlade4SuperBlockFreqTable OBJECT-TYPE
    SYNTAX SEQUENCE OF ApexRfConfigBlade4SuperBlockFreqEntry
    MAX-ACCESS not-accessible
    STATUS current
    DESCRIPTION
        "Table of RF Port Super Block Frequency configuration for QAM Blade4.
         
         **** NOTE: Super Block Frequency configuration is currently limited:
         ****       - Super blocks cannot overlap.
         ****       - Super blocks must be in order 1..4 from low to high frequency.
         ****       - Super block 4 frequency must be selected such that the center
         ****         frequency of the last channel of the block is no greater than
         ****         the MAX frequency range (i.e., SB 4 freq <= 813000000 Hz).
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade4 4 }

apexRfConfigBlade4SuperBlockFreqEntry OBJECT-TYPE
    SYNTAX ApexRfConfigBlade4SuperBlockFreqEntry
    MAX-ACCESS not-accessible
    STATUS current
    DESCRIPTION
        "Blade4 RF Port Super Block Frequency Configuration Table Entry."
    INDEX { apexRfConfigBlade4SuperBlockFreqRfPortNum,
            apexRfConfigBlade4SuperBlockFreqBlockNum }
::= { apexRfConfigBlade4SuperBlockFreqTable 1 }

ApexRfConfigBlade4SuperBlockFreqEntry ::= SEQUENCE
    {
     apexRfConfigBlade4SuperBlockFreqRfPortNum  Integer32,
     apexRfConfigBlade4SuperBlockFreqBlockNum   Integer32,
     apexRfConfigBlade4SuperBlockFreqAnnexB     Integer32,
     apexRfConfigBlade4SuperBlockFreqAnnexC     Integer32,
     apexRfConfigBlade4SuperBlockFreqAnnexA     Integer32
    }

apexRfConfigBlade4SuperBlockFreqRfPortNum OBJECT-TYPE
    SYNTAX Integer32(1..4)
    MAX-ACCESS not-accessible
    STATUS current
    DESCRIPTION
        "RF Port number on QAM Blade.
        "
::= { apexRfConfigBlade4SuperBlockFreqEntry 1 }

apexRfConfigBlade4SuperBlockFreqBlockNum OBJECT-TYPE
    SYNTAX Integer32(1..4)
    MAX-ACCESS not-accessible
    STATUS current
    DESCRIPTION
        "Super-block number on RF Port.
        "
::= { apexRfConfigBlade4SuperBlockFreqEntry 2 }

apexRfConfigBlade4SuperBlockFreqAnnexB OBJECT-TYPE
    SYNTAX Integer32(57000000..999000000)
    MAX-ACCESS read-write
    STATUS current
    DESCRIPTION
        "Center frequency of first channel of super-block for Annex B.
         This value must be in Hz in the range 57,000,000 Hz to 999,000,000 Hz
         in 125,000 Hz steps.
         Used only when apexRfStatusTransmissionMode 'annexB-ATSC-DCII'.

         @Range(step=125000)
        "
::= { apexRfConfigBlade4SuperBlockFreqEntry 3 }

apexRfConfigBlade4SuperBlockFreqAnnexC OBJECT-TYPE
    SYNTAX Integer32(57000000..999000000)
    MAX-ACCESS read-write
    STATUS current
    DESCRIPTION
        "Center frequency of first channel of super-block for Annex C.
         This value must be in Hz in the range 57,000,000 Hz to 999,000,000 Hz
         in 125,000 Hz steps.
         Used only when apexRfStatusTransmissionMode 'annexC-Asia-Pacific'.

         @Range(step=125000)
        "
::= { apexRfConfigBlade4SuperBlockFreqEntry 4 }

apexRfConfigBlade4SuperBlockFreqAnnexA OBJECT-TYPE
    SYNTAX Integer32(85000000..999000000)
    MAX-ACCESS read-write
    STATUS current
    DESCRIPTION
        "Center frequency of first channel of super-block for Annex A.
         This value must be in Hz in the range 85,000,000 Hz to 999,000,000 Hz
         in 125,000 Hz steps.
         Used only when apexRfStatusTransmissionMode 'annexA-DVB'.

         @Range(step=125000)
        "
::= { apexRfConfigBlade4SuperBlockFreqEntry 5 }


-- ------------------------------------------------------------------------------
--
-- apexRfConfigBlade4SubBlockFreqTable
--

apexRfConfigBlade4SubBlockFreqTable OBJECT-TYPE
    SYNTAX SEQUENCE OF ApexRfConfigBlade4SubBlockFreqEntry
    MAX-ACCESS not-accessible
    STATUS current
    DESCRIPTION
        "TABLE NOT SUPPORTED.
         
         Table of RF Port Sub Block Frequency configuration for QAM Blade4.
         
         **** NOTE: This table is currently unsupported in APEX3000.
         ****       APEX3000 will set values consistent with settings
         ****       in blade Super Block Frequency Table.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade4 5 }

apexRfConfigBlade4SubBlockFreqEntry OBJECT-TYPE
    SYNTAX ApexRfConfigBlade4SubBlockFreqEntry
    MAX-ACCESS not-accessible
    STATUS current
    DESCRIPTION
        "Blade4 RF Port Sub Block Frequency Configuration Table Entry."
    INDEX { apexRfConfigBlade4SubBlockFreqRfPortNum,
            apexRfConfigBlade4SubBlockFreqBlockNum }
::= { apexRfConfigBlade4SubBlockFreqTable 1 }

ApexRfConfigBlade4SubBlockFreqEntry ::= SEQUENCE
    {
     apexRfConfigBlade4SubBlockFreqRfPortNum      Integer32,
     apexRfConfigBlade4SubBlockFreqBlockNum       Integer32,
     apexRfConfigBlade4SubBlockFreqAnnexB         Integer32,
     apexRfConfigBlade4SubBlockFreqAnnexC         Integer32,
     apexRfConfigBlade4SubBlockFreqAnnexA         Integer32,
     apexRfConfigBlade4SubBlockChanSpacingAnnexA  Integer32
    }

apexRfConfigBlade4SubBlockFreqRfPortNum OBJECT-TYPE
    SYNTAX Integer32(1..4)
    MAX-ACCESS not-accessible
    STATUS current
    DESCRIPTION
        "RF Port number on QAM Blade.
        "
::= { apexRfConfigBlade4SubBlockFreqEntry 1 }

apexRfConfigBlade4SubBlockFreqBlockNum OBJECT-TYPE
    SYNTAX Integer32(1..16)
    MAX-ACCESS not-accessible
    STATUS current
    DESCRIPTION
        "Sub-block number on RF Port.
        "
::= { apexRfConfigBlade4SubBlockFreqEntry 2 }

apexRfConfigBlade4SubBlockFreqAnnexB OBJECT-TYPE
    SYNTAX Integer32(57000000..999000000)
    MAX-ACCESS read-write
    STATUS current
    DESCRIPTION
        "Center frequency of first channel of sub-block for Annex B.
         This value must be in Hz in the range 57,000,000 Hz to 999,000,000 Hz
         in 125,000 Hz steps.
         Used only when apexRfStatusTransmissionMode 'annexB-ATSC-DCII'.

         @Range(step=125000)
        "
::= { apexRfConfigBlade4SubBlockFreqEntry 3 }

apexRfConfigBlade4SubBlockFreqAnnexC OBJECT-TYPE
    SYNTAX Integer32(57000000..999000000)
    MAX-ACCESS read-write
    STATUS current
    DESCRIPTION
        "Center frequency of first channel of sub-block for Annex C.
         This value must be in Hz in the range 57,000,000 Hz to 999,000,000 Hz
         in 125,000 Hz steps.
         Used only when apexRfStatusTransmissionMode 'annexC-Asia-Pacific'.

         @Range(step=125000)
        "
::= { apexRfConfigBlade4SubBlockFreqEntry 4 }

apexRfConfigBlade4SubBlockFreqAnnexA OBJECT-TYPE
    SYNTAX Integer32(85000000..999000000)
    MAX-ACCESS read-write
    STATUS current
    DESCRIPTION
        "Center frequency of first channel of sub-block for Annex A.
         This value must be in Hz in the range 85,000,000 Hz to 999,000,000 Hz
         in 125,000 Hz steps.
         Used only when apexRfStatusTransmissionMode 'annexA-DVB'.

         @Range(step=125000)
        "
::= { apexRfConfigBlade4SubBlockFreqEntry 5 }

apexRfConfigBlade4SubBlockChanSpacingAnnexA OBJECT-TYPE
    SYNTAX Integer32(1000000..8000000)
    MAX-ACCESS read-write
    STATUS current
    DESCRIPTION
        "*** This entry is not supported. ***
         
         Channel spacing of sub-block for Annex A.
         This value must be in Hz in the range 1,000,000 Hz to 8,000,000 Hz
         in 500,000 Hz steps.
         Used only when apexRfStatusTransmissionMode 'annexA-DVB'.

         @Range(step=500000)
        "
::= { apexRfConfigBlade4SubBlockFreqEntry 6 }


-- ------------------------------------------------------------------------------
--
-- apexRfConfigBlade4ChannelTable
--

apexRfConfigBlade4ChannelTable OBJECT-TYPE
    SYNTAX SEQUENCE OF ApexRfConfigBlade4ChannelEntry
    MAX-ACCESS not-accessible
    STATUS current
    DESCRIPTION
        "Table of QAM Channel configuration for QAM Blade4.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade4 6 }

apexRfConfigBlade4ChannelEntry OBJECT-TYPE
    SYNTAX ApexRfConfigBlade4ChannelEntry
    MAX-ACCESS not-accessible
    STATUS current
    DESCRIPTION
        "Blade4 QAM Channel Configuration Table Entry."
    INDEX { apexRfConfigBlade4ChannelRfPortNum,
            apexRfConfigBlade4ChannelChanNum }
::= { apexRfConfigBlade4ChannelTable 1 }

ApexRfConfigBlade4ChannelEntry ::= SEQUENCE
    {
     apexRfConfigBlade4ChannelRfPortNum              Integer32,
     apexRfConfigBlade4ChannelChanNum                Integer32,
     apexRfConfigBlade4ChannelFrequencyGridSelect    Integer32,
     apexRfConfigBlade4ChannelModeComboSelectAnnexA  Integer32,
     apexRfConfigBlade4ChannelModeComboSelectAnnexB  Integer32,
     apexRfConfigBlade4ChannelModeComboSelectAnnexC  Integer32,
     apexRfConfigBlade4ChannelRfLevelAdjust          Integer32,
     apexRfConfigBlade4ChannelTestMode               QamChannelTestModeTYPE,
     apexRfConfigBlade4ChannelMute                   QamRfMuteTYPE
    }

apexRfConfigBlade4ChannelRfPortNum OBJECT-TYPE
    SYNTAX Integer32(1..4)
    MAX-ACCESS not-accessible
    STATUS current
    DESCRIPTION
        "RF Port number on QAM Blade.
        "
::= { apexRfConfigBlade4ChannelEntry 1 }

apexRfConfigBlade4ChannelChanNum OBJECT-TYPE
    SYNTAX Integer32(1..64)
    MAX-ACCESS not-accessible
    STATUS current
    DESCRIPTION
        "QAM channel number on RF Port.
        "
::= { apexRfConfigBlade4ChannelEntry 2 }

apexRfConfigBlade4ChannelFrequencyGridSelect OBJECT-TYPE
    SYNTAX Integer32(0..128)
    MAX-ACCESS read-write
    STATUS current
    DESCRIPTION
        "RF Port frequency grid slot selection for this channel.
         Zero indicates the channel is not in use (disabled).
         
         The frequency is selected from a grid of 128 total frequency assignment
         selections (or 'slots').  The grid is divided into 4 super blocks (192
         MHz wide) with 32 assignment slots each.  Each super block is divided
         into 4 sub blocks (48 MHz wide) with 8 assignment slots each.  Using 'B'
         for super blocks and 'b' sub blocks numbering of super and sub blocks is
         B1..B4 and b1..b16 respectively.  The sub blocks are contained in
         superblocks as follows:
            B1[b1..b4],
            B2[b5..b8],
            B3[b9..b12], and
            B4[b13..b16].
         Numbering of the slots within the blocks is as follows:
            B1[b1(1..8), b2(9..16), b3(17..24), b4(25..32)],
            B2[b5(33..40), b6(41..48), b7(49..56), b8(57..64)],
            B3[b9(65..72), b10(73..80), b11(81..88), b12(89..96)], and
            B4[b13(97..105), b14(106..112), b15(113..120), b16(121..128)].

         Annex B/C: For apexRfStatusTransmissionMode of 'annexB-ATSC-DCII' or
         'annexC-Asia-Pacific' the full range of slots [1..128] may be selected.

         Annex A: For apexRfStatusTransmissionMode of 'annexA-DVB' not all slots
         may be selected.  Since a sub block represents a 48 MHz wide band and
         'annexA-DVB' channel spacing is currently a fixed 8 MHz, only the first
         6 slots in each sub block can be assigned.  Therefore, the 'annexA-DVB'
         assignments may be as follows:
            B1[b1(1..6), b2(9..14), b3(17..22), b4(25..30)],
            B2[b5(33..38), b6(41..46), b7(49..54), b8(57..62)],
            B3[b9(65..70), b10(73..78), b11(81..86), b12(89..94)], and
            B4[b13(97..102), b14(105..110), b15(113..118), b16(121..126)].
         The APEX3000 will automatically clear any assignments to the following
         slots:
            B1[b1(7, 8), b2(15, 16), b3(23, 24), b4(31, 32)],
            B2[b5(39, 40), b6(47, 48), b7(55, 56), b8(63, 64)],
            B3[b9(71, 72), b10(79, 80), b11(87, 88), b12(95, 96)], and
            B4[b13(103, 104), b14(111, 112), b15(119, 120), b16(127, 128)].
        "
::= { apexRfConfigBlade4ChannelEntry 3 }

apexRfConfigBlade4ChannelModeComboSelectAnnexA OBJECT-TYPE
    SYNTAX Integer32(1..4)
    MAX-ACCESS read-write
    STATUS current
    DESCRIPTION
        "QAM Mode Combination selection for Annex A.
         Mode combinations are configured in apexRfConfigBlade4ModesTable.
         Used only when apexRfStatusTransmissionMode 'annexA-DVB'.
        "
::= { apexRfConfigBlade4ChannelEntry 4 }

apexRfConfigBlade4ChannelModeComboSelectAnnexB OBJECT-TYPE
    SYNTAX Integer32(1..4)
    MAX-ACCESS read-write
    STATUS current
    DESCRIPTION
        "QAM Mode Combination selection for Annex B.
         Mode combinations are configured in apexRfConfigBlade4ModesTable.
         Used only when apexRfStatusTransmissionMode 'annexB-ATSC-DCII'.
        "
::= { apexRfConfigBlade4ChannelEntry 5 }

apexRfConfigBlade4ChannelModeComboSelectAnnexC OBJECT-TYPE
    SYNTAX Integer32(1..4)
    MAX-ACCESS read-write
    STATUS current
    DESCRIPTION
        "QAM Mode Combination selection for Annex C.
         Mode combinations are configured in apexRfConfigBlade4ModesTable.
         Used only when apexRfStatusTransmissionMode 'annexC-Asia-Pacific'.
        "
::= { apexRfConfigBlade4ChannelEntry 6 }

apexRfConfigBlade4ChannelRfLevelAdjust OBJECT-TYPE
    SYNTAX Integer32(-20..0)
    MAX-ACCESS read-write
    STATUS current
    DESCRIPTION
        "RF Level adjustment for the channel.
         
         Range is -2.0 dB to 0.0 dB relative to apexRfConfigBlade4RfPortRfLevel.
         Value is in 0.1 dB steps.
         
         Final RF Level after adjustment applied must be within >= -8.00 dB below
         and <= 4.00 dB above DRFI nominal for the number of channels in-use(*)
         based on max 48 channel output.
         
         (*) In-use = assigned a frequency, unmuted, and not suppressed.
        "
::= { apexRfConfigBlade4ChannelEntry 7 }

apexRfConfigBlade4ChannelTestMode OBJECT-TYPE
    SYNTAX QamChannelTestModeTYPE
    MAX-ACCESS read-write
    STATUS current
    DESCRIPTION
        "Test mode for the channel.
         
         RF Port diagnostic suppression configuration will override
         this setting.  (apexRfConfigBlade4RfPortDiagSuppressMode and
         apexRfConfigBlade4RfPortDiagSuppressChannel)
         
         Test mode status is reflected in apexRfStatusChannelOutputMode.
         
         noTest     - Test mode is off.  Channel is in normal operation.
         suppress   - Suppress the channel.
         cwtest     - CW test.
         prbs23m    - PRBS-23 with MPEG Sync.
         prbsUnique - Unique PRBS. Multiple channels configured in this
                      mode will transmit uncorrelated data. Pattern is
                      generated in the APEX.
         mpegNull   - MPEG Null packets.
         biPhase    - Bi-phase Mode (alternating symbols).
        "
::= { apexRfConfigBlade4ChannelEntry 8 }

apexRfConfigBlade4ChannelMute OBJECT-TYPE
    SYNTAX QamRfMuteTYPE
    MAX-ACCESS read-write
    STATUS current
    DESCRIPTION
        "Mute the QAM Channel.
        "
::= { apexRfConfigBlade4ChannelEntry 9 }


-- ------------------------------------------------------------------------------
--
-- apexRfConfigBlade5
--
-- apexRfConfigBlade5General
--

-- none


-- ------------------------------------------------------------------------------
--
-- apexRfConfigBlade5ModesTable
--

apexRfConfigBlade5ModesTable OBJECT-TYPE
    SYNTAX SEQUENCE OF ApexRfConfigBlade5ModesEntry
    MAX-ACCESS not-accessible
    STATUS current
    DESCRIPTION
        "Table of RF Mode Combinations for QAM Blade5.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade5 2 }

apexRfConfigBlade5ModesEntry OBJECT-TYPE
    SYNTAX ApexRfConfigBlade5ModesEntry
    MAX-ACCESS not-accessible
    STATUS current
    DESCRIPTION
        "RF Configuration Blade5 RF Mode Combinations Table Entry."
    INDEX { apexRfConfigBlade5ModesIndex }
::= { apexRfConfigBlade5ModesTable 1 }

ApexRfConfigBlade5ModesEntry ::= SEQUENCE
    {
     apexRfConfigBlade5ModesIndex                   Integer32,
     apexRfConfigBlade5ModesModulationModeAnnexB    QamRfModulationModeTYPE,
     apexRfConfigBlade5ModesInterleaverDepthAnnexB  QamRfInterleaverDepthAnnexBTYPE,
     apexRfConfigBlade5ModesModulationModeAnnexA    QamRfModulationModeTYPE,
     apexRfConfigBlade5ModesSymbolRateAnnexA        Integer32,
     apexRfConfigBlade5ModesModulationModeAnnexC    QamRfModulationModeTYPE,
     apexRfConfigBlade5ModesSymbolRateAnnexC        Integer32
    }

apexRfConfigBlade5ModesIndex OBJECT-TYPE
    SYNTAX Integer32(1..4)
    MAX-ACCESS not-accessible
    STATUS current
    DESCRIPTION
        "Index for RF Configuration Blade5 RF Mode Combinations Table.
        "
::= { apexRfConfigBlade5ModesEntry 1 }

apexRfConfigBlade5ModesModulationModeAnnexB OBJECT-TYPE
    SYNTAX QamRfModulationModeTYPE
    MAX-ACCESS read-write
    STATUS current
    DESCRIPTION
        "QAM RF Modulation mode for Annex B.
         Used only when apexRfStatusTransmissionMode 'annexB-ATSC-DCII'.
        "
::= { apexRfConfigBlade5ModesEntry 2 }

apexRfConfigBlade5ModesInterleaverDepthAnnexB OBJECT-TYPE
    SYNTAX QamRfInterleaverDepthAnnexBTYPE
    MAX-ACCESS read-write
    STATUS current
    DESCRIPTION
        "QAM RF Interleaver setting for Annex B.
         Used only when apexRfStatusTransmissionMode 'annexB-ATSC-DCII'.
        "
::= { apexRfConfigBlade5ModesEntry 3 }

apexRfConfigBlade5ModesModulationModeAnnexA OBJECT-TYPE
    SYNTAX QamRfModulationModeTYPE
    MAX-ACCESS read-write
    STATUS current
    DESCRIPTION
        "QAM RF Modulation mode for Annex A.
         Only used when apexRfStatusTransmissionMode is 'annexA-DVB'.
        "
::= { apexRfConfigBlade5ModesEntry 4 }

apexRfConfigBlade5ModesSymbolRateAnnexA OBJECT-TYPE
    SYNTAX Integer32(1000000..6980000)
    MAX-ACCESS read-write
    STATUS current
    DESCRIPTION
        "QAM RF Symbol Rate for Annex A.
         Only used when apexRfStatusTransmissionMode is 'annexA-DVB'.
         It is in symbols per second (sps) in 1000 sps steps.

         @Range(step=1000)
        "
::= { apexRfConfigBlade5ModesEntry 5 }

apexRfConfigBlade5ModesModulationModeAnnexC OBJECT-TYPE
    SYNTAX QamRfModulationModeTYPE
    MAX-ACCESS read-write
    STATUS current
    DESCRIPTION
        "QAM RF Modulation mode for Annex C.
         Used only when apexRfStatusTransmissionMode 'annexC-Asia-Pacific'.
        "
::= { apexRfConfigBlade5ModesEntry 6 }

apexRfConfigBlade5ModesSymbolRateAnnexC OBJECT-TYPE
    SYNTAX Integer32(800000..5310000)
    MAX-ACCESS read-write
    STATUS current
    DESCRIPTION
        "QAM RF Symbol Rate for Annex C.
         Only used when apexRfStatusTransmissionMode is 'annexC-Asia-Pacific'.
         It is in symbols per second (sps) in 1000 sps steps.

         @Range(step=1000)
        "
::= { apexRfConfigBlade5ModesEntry 7 }


-- ------------------------------------------------------------------------------
--
-- apexRfConfigBlade5RfPortTable
--

apexRfConfigBlade5RfPortTable OBJECT-TYPE
    SYNTAX SEQUENCE OF ApexRfConfigBlade5RfPortEntry
    MAX-ACCESS not-accessible
    STATUS current
    DESCRIPTION
        "Table of RF Port configuration for QAM Blade5.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade5 3 }

apexRfConfigBlade5RfPortEntry OBJECT-TYPE
    SYNTAX ApexRfConfigBlade5RfPortEntry
    MAX-ACCESS not-accessible
    STATUS current
    DESCRIPTION
        "Blade5 RF Port Configuration Table Entry."
    INDEX { apexRfConfigBlade5RfPortNum }
::= { apexRfConfigBlade5RfPortTable 1 }

ApexRfConfigBlade5RfPortEntry ::= SEQUENCE
    {
     apexRfConfigBlade5RfPortNum                   Integer32,
     apexRfConfigBlade5RfPortSpectrumInversion     QamRfSpectrumInversionTYPE,
     apexRfConfigBlade5RfPortMute                  QamRfMuteTYPE,
     apexRfConfigBlade5RfPortRfLevel               Integer32,
     apexRfConfigBlade5RfPortDiagSuppressMode      QamRfDiagSuppressModeTYPE,
     apexRfConfigBlade5RfPortDiagSuppressChannel   Integer32,
     apexRfConfigBlade5RfPortNprimeMax             Integer32,
     apexRfConfigBlade5RfPortNprimeMaxMode         AutomaticManualTYPE
    }

apexRfConfigBlade5RfPortNum OBJECT-TYPE
    SYNTAX Integer32(1..4)
    MAX-ACCESS not-accessible
    STATUS current
    DESCRIPTION
        "RF Port number on QAM Blade.
        "
::= { apexRfConfigBlade5RfPortEntry 1 }

apexRfConfigBlade5RfPortSpectrumInversion OBJECT-TYPE
    SYNTAX QamRfSpectrumInversionTYPE
    MAX-ACCESS read-write
    STATUS current
    DESCRIPTION
        "The Spectrum Inversion Setting of the QAM Channels
         on the RF Port.
        "
::= { apexRfConfigBlade5RfPortEntry 2 }

apexRfConfigBlade5RfPortMute OBJECT-TYPE
    SYNTAX QamRfMuteTYPE
    MAX-ACCESS read-write
    STATUS current
    DESCRIPTION
        "Mute the RF Port.  This will mute all QAM channels on the
         RF Port.
        "
::= { apexRfConfigBlade5RfPortEntry 3 }

apexRfConfigBlade5RfPortRfLevel OBJECT-TYPE
    SYNTAX Integer32(3000..5600)
    MAX-ACCESS read-write
    STATUS current
    DESCRIPTION
        "The RF level setting of each channel in-use(*) on the RF Port.
         
         Range is 30.00 to 56.00 dBmV per channel in 0.01 dBmV steps.
         
         Value must be within >= -8.00 dBmV below and <= 4.00 dBmV above DRFI nominal 
         for the number of channels in-use(*) based on max 48 channel output.
         
         (*) In-use = assigned a frequency, unmuted, and not suppressed.
        "
::= { apexRfConfigBlade5RfPortEntry 4 }

apexRfConfigBlade5RfPortDiagSuppressMode OBJECT-TYPE
    SYNTAX QamRfDiagSuppressModeTYPE
    MAX-ACCESS read-write
    STATUS current
    DESCRIPTION
        "Diagnostic Suppression Mode of the RF Port.
                 
         none               - No suppression.
         oneChannel         - One channel suppressed
         allChannelsButOne  - All channels suppressed except one
         allChannels        - All channels suppressed
         
         Use apexRfConfigBlade5RfPortDiagSuppressChannel to define the 'one'
         channel for 'oneChannel' and 'allChannelsButOne' modes.
         
         This setting will override apexRfConfigBlade5ChannelTestMode.
         
         Test mode status is reflected in apexRfStatusChannelOutputMode.
        "
::= { apexRfConfigBlade5RfPortEntry 5 }

apexRfConfigBlade5RfPortDiagSuppressChannel OBJECT-TYPE
    SYNTAX Integer32(1..64)
    MAX-ACCESS read-write
    STATUS current
    DESCRIPTION
        "Channel defined for Diagnostic Suppression.
         
         Used to define the 'one' channel for the 'oneChannel' and
         'allChannelsButOne' modes of apexRfConfigBlade5RfPortDiagSuppressMode.
         
         This setting will override apexRfConfigBlade5ChannelTestMode.
         
         Test mode status is reflected in apexRfStatusChannelOutputMode.
        "
::= { apexRfConfigBlade5RfPortEntry 6 }

apexRfConfigBlade5RfPortNprimeMax OBJECT-TYPE
    SYNTAX Integer32(0..64)
    MAX-ACCESS read-write
    STATUS current
    DESCRIPTION
        "User defined DRFI N'max value used by APEX when RfPortNprimeMaxMode
         is 'manual'.  This parameter is ignored when RfPortNprimeMaxMode
         is 'automatic'.
         
         N'max must be greater than or equal to the number of channels
         in-use (assigned a frequency, unmuted, and not suppressed).
         
         Using the RfPortNprimeMax value guarantees glitchless RF port
         reconfiguration as per the DRFI specification described below.
         
         NOTE: RF performance will be degraded for large differences
               between the number of channels in-use and the user selected
               N'max value.
         
         The N'max value in use by the APEX is reflected in apexRfStatusRfPortNprimeMax.
         
         From CM-SP-DRFI-I10-100611:
         A CMTS or EQAM capable of generating more than eight channels per
         physical RF port MUST be capable of glitchless reconfiguration over
         a range of active channels from ceiling[7*N'max/8] to N'max. Channels
         which are undergoing configuration changes are referred to as the
         'changed channels.' The channels which are active and are not being
         reconfigured are referred to as the 'continuous channels'. Each DRFI
         modulator capable of generating more than eight channels per physical
         RF port MUST accept a command setting N'max. Glitchless reconfiguration
         consists of any of the following actions while introducing no
         discontinuity or detriment to the continuous channels, where the
         modulator is operating in a valid DRFI-required mode both before and
         after the reconfiguration with an active number of channels staying in
         the range {ceiling[7*N'max/8], N'max}: adding and/or deleting one or
         more channels, and/or moving some channels to new RF carrier
         frequencies, and/or changing the interleaver depth, modulation, power
         level, or frequency on one or more channels. Any change in the
         modulation characteristics (power level, modulation density, interleaver
         parameters, center frequency) of a channel excuses that channel from
         being required to operate in a glitchless manner. For example, changing
         the power per channel of a given channel means that channel is not
         considered a continuous channel for the purposes of the glitchless
         modulation requirements. Glitchless operation is not required when N'max
         is changed, even if no reconfigurations accompany the change in N'max.
        "
::= { apexRfConfigBlade5RfPortEntry 7 }

apexRfConfigBlade5RfPortNprimeMaxMode OBJECT-TYPE
    SYNTAX AutomaticManualTYPE
    MAX-ACCESS read-write
    STATUS current
    DESCRIPTION
        "DRFI N'max configuration mode.
        
         'automatic' - In this mode the APEX is responsible for selecting the N'max
                       and will automatically set N'max to the number of channels in-use
                       (assigned a frequency, unmuted, and not suppressed).  This guarantees
                       optimal RF performance for the number of channels in-use but
                       reconfiguration of the RF port may cause RF glitches.  If,
                       after testing, the user determines reconfiguration of RF ports
                       in 'standard' mode causes unacceptable RF interruption, the
                       'advanced' mode may be used.  
         
         'manual'    - In this advanced mode the user is responsible for manually setting
                       N'max in the RfPortNprimeMax parameter.  The APEX will use the value
                       in the RfPortNprimeMax parameter.  This will guarantee glitchless RF
                       port reconfiguration as per the DRFI specification described below.
                       NOTE: RF performance will be degraded for large differences
                             between the number of channels in-use and the user selected
                             N'max value.
         
         The N'max value in use by the APEX is reflected in apexRfStatusRfPortNprimeMax.
         
         From CM-SP-DRFI-I10-100611:
         A CMTS or EQAM capable of generating more than eight channels per
         physical RF port MUST be capable of glitchless reconfiguration over
         a range of active channels from ceiling[7*N'max/8] to N'max. Channels
         which are undergoing configuration changes are referred to as the
         'changed channels.' The channels which are active and are not being
         reconfigured are referred to as the 'continuous channels'. Each DRFI
         modulator capable of generating more than eight channels per physical
         RF port MUST accept a command setting N'max. Glitchless reconfiguration
         consists of any of the following actions while introducing no
         discontinuity or detriment to the continuous channels, where the
         modulator is operating in a valid DRFI-required mode both before and
         after the reconfiguration with an active number of channels staying in
         the range {ceiling[7*N'max/8], N'max}: adding and/or deleting one or
         more channels, and/or moving some channels to new RF carrier
         frequencies, and/or changing the interleaver depth, modulation, power
         level, or frequency on one or more channels. Any change in the
         modulation characteristics (power level, modulation density, interleaver
         parameters, center frequency) of a channel excuses that channel from
         being required to operate in a glitchless manner. For example, changing
         the power per channel of a given channel means that channel is not
         considered a continuous channel for the purposes of the glitchless
         modulation requirements. Glitchless operation is not required when N'max
         is changed, even if no reconfigurations accompany the change in N'max.
        "
::= { apexRfConfigBlade5RfPortEntry 8 }


-- ------------------------------------------------------------------------------
--
-- apexRfConfigBlade5SuperBlockFreqTable
--

apexRfConfigBlade5SuperBlockFreqTable OBJECT-TYPE
    SYNTAX SEQUENCE OF ApexRfConfigBlade5SuperBlockFreqEntry
    MAX-ACCESS not-accessible
    STATUS current
    DESCRIPTION
        "Table of RF Port Super Block Frequency configuration for QAM Blade5.
         
         **** NOTE: Super Block Frequency configuration is currently limited:
         ****       - Super blocks cannot overlap.
         ****       - Super blocks must be in order 1..4 from low to high frequency.
         ****       - Super block 4 frequency must be selected such that the center
         ****         frequency of the last channel of the block is no greater than
         ****         the MAX frequency range (i.e., SB 4 freq <= 813000000 Hz).
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade5 4 }

apexRfConfigBlade5SuperBlockFreqEntry OBJECT-TYPE
    SYNTAX ApexRfConfigBlade5SuperBlockFreqEntry
    MAX-ACCESS not-accessible
    STATUS current
    DESCRIPTION
        "Blade5 RF Port Super Block Frequency Configuration Table Entry."
    INDEX { apexRfConfigBlade5SuperBlockFreqRfPortNum,
            apexRfConfigBlade5SuperBlockFreqBlockNum }
::= { apexRfConfigBlade5SuperBlockFreqTable 1 }

ApexRfConfigBlade5SuperBlockFreqEntry ::= SEQUENCE
    {
     apexRfConfigBlade5SuperBlockFreqRfPortNum  Integer32,
     apexRfConfigBlade5SuperBlockFreqBlockNum   Integer32,
     apexRfConfigBlade5SuperBlockFreqAnnexB     Integer32,
     apexRfConfigBlade5SuperBlockFreqAnnexC     Integer32,
     apexRfConfigBlade5SuperBlockFreqAnnexA     Integer32
    }

apexRfConfigBlade5SuperBlockFreqRfPortNum OBJECT-TYPE
    SYNTAX Integer32(1..4)
    MAX-ACCESS not-accessible
    STATUS current
    DESCRIPTION
        "RF Port number on QAM Blade.
        "
::= { apexRfConfigBlade5SuperBlockFreqEntry 1 }

apexRfConfigBlade5SuperBlockFreqBlockNum OBJECT-TYPE
    SYNTAX Integer32(1..4)
    MAX-ACCESS not-accessible
    STATUS current
    DESCRIPTION
        "Super-block number on RF Port.
        "
::= { apexRfConfigBlade5SuperBlockFreqEntry 2 }

apexRfConfigBlade5SuperBlockFreqAnnexB OBJECT-TYPE
    SYNTAX Integer32(57000000..999000000)
    MAX-ACCESS read-write
    STATUS current
    DESCRIPTION
        "Center frequency of first channel of super-block for Annex B.
         This value must be in Hz in the range 57,000,000 Hz to 999,000,000 Hz
         in 125,000 Hz steps.
         Used only when apexRfStatusTransmissionMode 'annexB-ATSC-DCII'.

         @Range(step=125000)
        "
::= { apexRfConfigBlade5SuperBlockFreqEntry 3 }

apexRfConfigBlade5SuperBlockFreqAnnexC OBJECT-TYPE
    SYNTAX Integer32(57000000..999000000)
    MAX-ACCESS read-write
    STATUS current
    DESCRIPTION
        "Center frequency of first channel of super-block for Annex C.
         This value must be in Hz in the range 57,000,000 Hz to 999,000,000 Hz
         in 125,000 Hz steps.
         Used only when apexRfStatusTransmissionMode 'annexC-Asia-Pacific'.

         @Range(step=125000)
        "
::= { apexRfConfigBlade5SuperBlockFreqEntry 4 }

apexRfConfigBlade5SuperBlockFreqAnnexA OBJECT-TYPE
    SYNTAX Integer32(85000000..999000000)
    MAX-ACCESS read-write
    STATUS current
    DESCRIPTION
        "Center frequency of first channel of super-block for Annex A.
         This value must be in Hz in the range 85,000,000 Hz to 999,000,000 Hz
         in 125,000 Hz steps.
         Used only when apexRfStatusTransmissionMode 'annexA-DVB'.

         @Range(step=125000)
        "
::= { apexRfConfigBlade5SuperBlockFreqEntry 5 }


-- ------------------------------------------------------------------------------
--
-- apexRfConfigBlade5SubBlockFreqTable
--

apexRfConfigBlade5SubBlockFreqTable OBJECT-TYPE
    SYNTAX SEQUENCE OF ApexRfConfigBlade5SubBlockFreqEntry
    MAX-ACCESS not-accessible
    STATUS current
    DESCRIPTION
        "TABLE NOT SUPPORTED.
         
         Table of RF Port Sub Block Frequency configuration for QAM Blade5.
         
         **** NOTE: This table is currently unsupported in APEX3000.
         ****       APEX3000 will set values consistent with settings
         ****       in blade Super Block Frequency Table.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade5 5 }

apexRfConfigBlade5SubBlockFreqEntry OBJECT-TYPE
    SYNTAX ApexRfConfigBlade5SubBlockFreqEntry
    MAX-ACCESS not-accessible
    STATUS current
    DESCRIPTION
        "Blade5 RF Port Sub Block Frequency Configuration Table Entry."
    INDEX { apexRfConfigBlade5SubBlockFreqRfPortNum,
            apexRfConfigBlade5SubBlockFreqBlockNum }
::= { apexRfConfigBlade5SubBlockFreqTable 1 }

ApexRfConfigBlade5SubBlockFreqEntry ::= SEQUENCE
    {
     apexRfConfigBlade5SubBlockFreqRfPortNum      Integer32,
     apexRfConfigBlade5SubBlockFreqBlockNum       Integer32,
     apexRfConfigBlade5SubBlockFreqAnnexB         Integer32,
     apexRfConfigBlade5SubBlockFreqAnnexC         Integer32,
     apexRfConfigBlade5SubBlockFreqAnnexA         Integer32,
     apexRfConfigBlade5SubBlockChanSpacingAnnexA  Integer32
    }

apexRfConfigBlade5SubBlockFreqRfPortNum OBJECT-TYPE
    SYNTAX Integer32(1..4)
    MAX-ACCESS not-accessible
    STATUS current
    DESCRIPTION
        "RF Port number on QAM Blade.
        "
::= { apexRfConfigBlade5SubBlockFreqEntry 1 }

apexRfConfigBlade5SubBlockFreqBlockNum OBJECT-TYPE
    SYNTAX Integer32(1..16)
    MAX-ACCESS not-accessible
    STATUS current
    DESCRIPTION
        "Sub-block number on RF Port.
        "
::= { apexRfConfigBlade5SubBlockFreqEntry 2 }

apexRfConfigBlade5SubBlockFreqAnnexB OBJECT-TYPE
    SYNTAX Integer32(57000000..999000000)
    MAX-ACCESS read-write
    STATUS current
    DESCRIPTION
        "Center frequency of first channel of sub-block for Annex B.
         This value must be in Hz in the range 57,000,000 Hz to 999,000,000 Hz
         in 125,000 Hz steps.
         Used only when apexRfStatusTransmissionMode 'annexB-ATSC-DCII'.

         @Range(step=125000)
        "
::= { apexRfConfigBlade5SubBlockFreqEntry 3 }

apexRfConfigBlade5SubBlockFreqAnnexC OBJECT-TYPE
    SYNTAX Integer32(57000000..999000000)
    MAX-ACCESS read-write
    STATUS current
    DESCRIPTION
        "Center frequency of first channel of sub-block for Annex C.
         This value must be in Hz in the range 57,000,000 Hz to 999,000,000 Hz
         in 125,000 Hz steps.
         Used only when apexRfStatusTransmissionMode 'annexC-Asia-Pacific'.

         @Range(step=125000)
        "
::= { apexRfConfigBlade5SubBlockFreqEntry 4 }

apexRfConfigBlade5SubBlockFreqAnnexA OBJECT-TYPE
    SYNTAX Integer32(85000000..999000000)
    MAX-ACCESS read-write
    STATUS current
    DESCRIPTION
        "Center frequency of first channel of sub-block for Annex A.
         This value must be in Hz in the range 85,000,000 Hz to 999,000,000 Hz
         in 125,000 Hz steps.
         Used only when apexRfStatusTransmissionMode 'annexA-DVB'.

         @Range(step=125000)
        "
::= { apexRfConfigBlade5SubBlockFreqEntry 5 }

apexRfConfigBlade5SubBlockChanSpacingAnnexA OBJECT-TYPE
    SYNTAX Integer32(1000000..8000000)
    MAX-ACCESS read-write
    STATUS current
    DESCRIPTION
        "*** This entry is not supported. ***
         
         Channel spacing of sub-block for Annex A.
         This value must be in Hz in the range 1,000,000 Hz to 8,000,000 Hz
         in 500,000 Hz steps.
         Used only when apexRfStatusTransmissionMode 'annexA-DVB'.

         @Range(step=500000)
        "
::= { apexRfConfigBlade5SubBlockFreqEntry 6 }


-- ------------------------------------------------------------------------------
--
-- apexRfConfigBlade5ChannelTable
--

apexRfConfigBlade5ChannelTable OBJECT-TYPE
    SYNTAX SEQUENCE OF ApexRfConfigBlade5ChannelEntry
    MAX-ACCESS not-accessible
    STATUS current
    DESCRIPTION
        "Table of QAM Channel configuration for QAM Blade5.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade5 6 }

apexRfConfigBlade5ChannelEntry OBJECT-TYPE
    SYNTAX ApexRfConfigBlade5ChannelEntry
    MAX-ACCESS not-accessible
    STATUS current
    DESCRIPTION
        "Blade5 QAM Channel Configuration Table Entry."
    INDEX { apexRfConfigBlade5ChannelRfPortNum,
            apexRfConfigBlade5ChannelChanNum }
::= { apexRfConfigBlade5ChannelTable 1 }

ApexRfConfigBlade5ChannelEntry ::= SEQUENCE
    {
     apexRfConfigBlade5ChannelRfPortNum              Integer32,
     apexRfConfigBlade5ChannelChanNum                Integer32,
     apexRfConfigBlade5ChannelFrequencyGridSelect    Integer32,
     apexRfConfigBlade5ChannelModeComboSelectAnnexA  Integer32,
     apexRfConfigBlade5ChannelModeComboSelectAnnexB  Integer32,
     apexRfConfigBlade5ChannelModeComboSelectAnnexC  Integer32,
     apexRfConfigBlade5ChannelRfLevelAdjust          Integer32,
     apexRfConfigBlade5ChannelTestMode               QamChannelTestModeTYPE,
     apexRfConfigBlade5ChannelMute                   QamRfMuteTYPE
    }

apexRfConfigBlade5ChannelRfPortNum OBJECT-TYPE
    SYNTAX Integer32(1..4)
    MAX-ACCESS not-accessible
    STATUS current
    DESCRIPTION
        "RF Port number on QAM Blade.
        "
::= { apexRfConfigBlade5ChannelEntry 1 }

apexRfConfigBlade5ChannelChanNum OBJECT-TYPE
    SYNTAX Integer32(1..64)
    MAX-ACCESS not-accessible
    STATUS current
    DESCRIPTION
        "QAM channel number on RF Port.
        "
::= { apexRfConfigBlade5ChannelEntry 2 }

apexRfConfigBlade5ChannelFrequencyGridSelect OBJECT-TYPE
    SYNTAX Integer32(0..128)
    MAX-ACCESS read-write
    STATUS current
    DESCRIPTION
        "RF Port frequency grid slot selection for this channel.
         Zero indicates the channel is not in use (disabled).
         
         The frequency is selected from a grid of 128 total frequency assignment
         selections (or 'slots').  The grid is divided into 4 super blocks (192
         MHz wide) with 32 assignment slots each.  Each super block is divided
         into 4 sub blocks (48 MHz wide) with 8 assignment slots each.  Using 'B'
         for super blocks and 'b' sub blocks numbering of super and sub blocks is
         B1..B4 and b1..b16 respectively.  The sub blocks are contained in
         superblocks as follows:
            B1[b1..b4],
            B2[b5..b8],
            B3[b9..b12], and
            B4[b13..b16].
         Numbering of the slots within the blocks is as follows:
            B1[b1(1..8), b2(9..16), b3(17..24), b4(25..32)],
            B2[b5(33..40), b6(41..48), b7(49..56), b8(57..64)],
            B3[b9(65..72), b10(73..80), b11(81..88), b12(89..96)], and
            B4[b13(97..105), b14(106..112), b15(113..120), b16(121..128)].

         Annex B/C: For apexRfStatusTransmissionMode of 'annexB-ATSC-DCII' or
         'annexC-Asia-Pacific' the full range of slots [1..128] may be selected.

         Annex A: For apexRfStatusTransmissionMode of 'annexA-DVB' not all slots
         may be selected.  Since a sub block represents a 48 MHz wide band and
         'annexA-DVB' channel spacing is currently a fixed 8 MHz, only the first
         6 slots in each sub block can be assigned.  Therefore, the 'annexA-DVB'
         assignments may be as follows:
            B1[b1(1..6), b2(9..14), b3(17..22), b4(25..30)],
            B2[b5(33..38), b6(41..46), b7(49..54), b8(57..62)],
            B3[b9(65..70), b10(73..78), b11(81..86), b12(89..94)], and
            B4[b13(97..102), b14(105..110), b15(113..118), b16(121..126)].
         The APEX3000 will automatically clear any assignments to the following
         slots:
            B1[b1(7, 8), b2(15, 16), b3(23, 24), b4(31, 32)],
            B2[b5(39, 40), b6(47, 48), b7(55, 56), b8(63, 64)],
            B3[b9(71, 72), b10(79, 80), b11(87, 88), b12(95, 96)], and
            B4[b13(103, 104), b14(111, 112), b15(119, 120), b16(127, 128)].
        "
::= { apexRfConfigBlade5ChannelEntry 3 }

apexRfConfigBlade5ChannelModeComboSelectAnnexA OBJECT-TYPE
    SYNTAX Integer32(1..4)
    MAX-ACCESS read-write
    STATUS current
    DESCRIPTION
        "QAM Mode Combination selection for Annex A.
         Mode combinations are configured in apexRfConfigBlade5ModesTable.
         Used only when apexRfStatusTransmissionMode 'annexA-DVB'.
        "
::= { apexRfConfigBlade5ChannelEntry 4 }

apexRfConfigBlade5ChannelModeComboSelectAnnexB OBJECT-TYPE
    SYNTAX Integer32(1..4)
    MAX-ACCESS read-write
    STATUS current
    DESCRIPTION
        "QAM Mode Combination selection for Annex B.
         Mode combinations are configured in apexRfConfigBlade5ModesTable.
         Used only when apexRfStatusTransmissionMode 'annexB-ATSC-DCII'.
        "
::= { apexRfConfigBlade5ChannelEntry 5 }

apexRfConfigBlade5ChannelModeComboSelectAnnexC OBJECT-TYPE
    SYNTAX Integer32(1..4)
    MAX-ACCESS read-write
    STATUS current
    DESCRIPTION
        "QAM Mode Combination selection for Annex C.
         Mode combinations are configured in apexRfConfigBlade5ModesTable.
         Used only when apexRfStatusTransmissionMode 'annexC-Asia-Pacific'.
        "
::= { apexRfConfigBlade5ChannelEntry 6 }

apexRfConfigBlade5ChannelRfLevelAdjust OBJECT-TYPE
    SYNTAX Integer32(-20..0)
    MAX-ACCESS read-write
    STATUS current
    DESCRIPTION
        "RF Level adjustment for the channel.
         
         Range is -2.0 dB to 0.0 dB relative to apexRfConfigBlade5RfPortRfLevel.
         Value is in 0.1 dB steps.
         
         Final RF Level after adjustment applied must be within >= -8.00 dB below
         and <= 4.00 dB above DRFI nominal for the number of channels in-use(*)
         based on max 48 channel output.
         
         (*) In-use = assigned a frequency, unmuted, and not suppressed.
        "
::= { apexRfConfigBlade5ChannelEntry 7 }

apexRfConfigBlade5ChannelTestMode OBJECT-TYPE
    SYNTAX QamChannelTestModeTYPE
    MAX-ACCESS read-write
    STATUS current
    DESCRIPTION
        "Test mode for the channel.
         
         RF Port diagnostic suppression configuration will override
         this setting.  (apexRfConfigBlade5RfPortDiagSuppressMode and
         apexRfConfigBlade5RfPortDiagSuppressChannel)
         
         Test mode status is reflected in apexRfStatusChannelOutputMode.
         
         noTest     - Test mode is off.  Channel is in normal operation.
         suppress   - Suppress the channel.
         cwtest     - CW test.
         prbs23m    - PRBS-23 with MPEG Sync.
         prbsUnique - Unique PRBS. Multiple channels configured in this
                      mode will transmit uncorrelated data. Pattern is
                      generated in the APEX.
         mpegNull   - MPEG Null packets.
         biPhase    - Bi-phase Mode (alternating symbols).
        "
::= { apexRfConfigBlade5ChannelEntry 8 }

apexRfConfigBlade5ChannelMute OBJECT-TYPE
    SYNTAX QamRfMuteTYPE
    MAX-ACCESS read-write
    STATUS current
    DESCRIPTION
        "Mute the QAM Channel.
        "
::= { apexRfConfigBlade5ChannelEntry 9 }


-- ------------------------------------------------------------------------------
--
-- apexRfConfigBlade6
--
-- apexRfConfigBlade6General
--

-- none


-- ------------------------------------------------------------------------------
--
-- apexRfConfigBlade6ModesTable
--

apexRfConfigBlade6ModesTable OBJECT-TYPE
    SYNTAX SEQUENCE OF ApexRfConfigBlade6ModesEntry
    MAX-ACCESS not-accessible
    STATUS current
    DESCRIPTION
        "Table of RF Mode Combinations for QAM Blade6.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade6 2 }

apexRfConfigBlade6ModesEntry OBJECT-TYPE
    SYNTAX ApexRfConfigBlade6ModesEntry
    MAX-ACCESS not-accessible
    STATUS current
    DESCRIPTION
        "RF Configuration Blade6 RF Mode Combinations Table Entry."
    INDEX { apexRfConfigBlade6ModesIndex }
::= { apexRfConfigBlade6ModesTable 1 }

ApexRfConfigBlade6ModesEntry ::= SEQUENCE
    {
     apexRfConfigBlade6ModesIndex                   Integer32,
     apexRfConfigBlade6ModesModulationModeAnnexB    QamRfModulationModeTYPE,
     apexRfConfigBlade6ModesInterleaverDepthAnnexB  QamRfInterleaverDepthAnnexBTYPE,
     apexRfConfigBlade6ModesModulationModeAnnexA    QamRfModulationModeTYPE,
     apexRfConfigBlade6ModesSymbolRateAnnexA        Integer32,
     apexRfConfigBlade6ModesModulationModeAnnexC    QamRfModulationModeTYPE,
     apexRfConfigBlade6ModesSymbolRateAnnexC        Integer32
    }

apexRfConfigBlade6ModesIndex OBJECT-TYPE
    SYNTAX Integer32(1..4)
    MAX-ACCESS not-accessible
    STATUS current
    DESCRIPTION
        "Index for RF Configuration Blade6 RF Mode Combinations Table.
        "
::= { apexRfConfigBlade6ModesEntry 1 }

apexRfConfigBlade6ModesModulationModeAnnexB OBJECT-TYPE
    SYNTAX QamRfModulationModeTYPE
    MAX-ACCESS read-write
    STATUS current
    DESCRIPTION
        "QAM RF Modulation mode for Annex B.
         Used only when apexRfStatusTransmissionMode 'annexB-ATSC-DCII'.
        "
::= { apexRfConfigBlade6ModesEntry 2 }

apexRfConfigBlade6ModesInterleaverDepthAnnexB OBJECT-TYPE
    SYNTAX QamRfInterleaverDepthAnnexBTYPE
    MAX-ACCESS read-write
    STATUS current
    DESCRIPTION
        "QAM RF Interleaver setting for Annex B.
         Used only when apexRfStatusTransmissionMode 'annexB-ATSC-DCII'.
        "
::= { apexRfConfigBlade6ModesEntry 3 }

apexRfConfigBlade6ModesModulationModeAnnexA OBJECT-TYPE
    SYNTAX QamRfModulationModeTYPE
    MAX-ACCESS read-write
    STATUS current
    DESCRIPTION
        "QAM RF Modulation mode for Annex A.
         Only used when apexRfStatusTransmissionMode is 'annexA-DVB'.
        "
::= { apexRfConfigBlade6ModesEntry 4 }

apexRfConfigBlade6ModesSymbolRateAnnexA OBJECT-TYPE
    SYNTAX Integer32(1000000..6980000)
    MAX-ACCESS read-write
    STATUS current
    DESCRIPTION
        "QAM RF Symbol Rate for Annex A.
         Only used when apexRfStatusTransmissionMode is 'annexA-DVB'.
         It is in symbols per second (sps) in 1000 sps steps.

         @Range(step=1000)
        "
::= { apexRfConfigBlade6ModesEntry 5 }

apexRfConfigBlade6ModesModulationModeAnnexC OBJECT-TYPE
    SYNTAX QamRfModulationModeTYPE
    MAX-ACCESS read-write
    STATUS current
    DESCRIPTION
        "QAM RF Modulation mode for Annex C.
         Used only when apexRfStatusTransmissionMode 'annexC-Asia-Pacific'.
        "
::= { apexRfConfigBlade6ModesEntry 6 }

apexRfConfigBlade6ModesSymbolRateAnnexC OBJECT-TYPE
    SYNTAX Integer32(800000..5310000)
    MAX-ACCESS read-write
    STATUS current
    DESCRIPTION
        "QAM RF Symbol Rate for Annex C.
         Only used when apexRfStatusTransmissionMode is 'annexC-Asia-Pacific'.
         It is in symbols per second (sps) in 1000 sps steps.

         @Range(step=1000)
        "
::= { apexRfConfigBlade6ModesEntry 7 }


-- ------------------------------------------------------------------------------
--
-- apexRfConfigBlade6RfPortTable
--

apexRfConfigBlade6RfPortTable OBJECT-TYPE
    SYNTAX SEQUENCE OF ApexRfConfigBlade6RfPortEntry
    MAX-ACCESS not-accessible
    STATUS current
    DESCRIPTION
        "Table of RF Port configuration for QAM Blade6.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade6 3 }

apexRfConfigBlade6RfPortEntry OBJECT-TYPE
    SYNTAX ApexRfConfigBlade6RfPortEntry
    MAX-ACCESS not-accessible
    STATUS current
    DESCRIPTION
        "Blade6 RF Port Configuration Table Entry."
    INDEX { apexRfConfigBlade6RfPortNum }
::= { apexRfConfigBlade6RfPortTable 1 }

ApexRfConfigBlade6RfPortEntry ::= SEQUENCE
    {
     apexRfConfigBlade6RfPortNum                   Integer32,
     apexRfConfigBlade6RfPortSpectrumInversion     QamRfSpectrumInversionTYPE,
     apexRfConfigBlade6RfPortMute                  QamRfMuteTYPE,
     apexRfConfigBlade6RfPortRfLevel               Integer32,
     apexRfConfigBlade6RfPortDiagSuppressMode      QamRfDiagSuppressModeTYPE,
     apexRfConfigBlade6RfPortDiagSuppressChannel   Integer32,
     apexRfConfigBlade6RfPortNprimeMax             Integer32,
     apexRfConfigBlade6RfPortNprimeMaxMode         AutomaticManualTYPE
    }

apexRfConfigBlade6RfPortNum OBJECT-TYPE
    SYNTAX Integer32(1..4)
    MAX-ACCESS not-accessible
    STATUS current
    DESCRIPTION
        "RF Port number on QAM Blade.
        "
::= { apexRfConfigBlade6RfPortEntry 1 }

apexRfConfigBlade6RfPortSpectrumInversion OBJECT-TYPE
    SYNTAX QamRfSpectrumInversionTYPE
    MAX-ACCESS read-write
    STATUS current
    DESCRIPTION
        "The Spectrum Inversion Setting of the QAM Channels
         on the RF Port.
        "
::= { apexRfConfigBlade6RfPortEntry 2 }

apexRfConfigBlade6RfPortMute OBJECT-TYPE
    SYNTAX QamRfMuteTYPE
    MAX-ACCESS read-write
    STATUS current
    DESCRIPTION
        "Mute the RF Port.  This will mute all QAM channels on the
         RF Port.
        "
::= { apexRfConfigBlade6RfPortEntry 3 }

apexRfConfigBlade6RfPortRfLevel OBJECT-TYPE
    SYNTAX Integer32(3000..5600)
    MAX-ACCESS read-write
    STATUS current
    DESCRIPTION
        "The RF level setting of each channel in-use(*) on the RF Port.
         
         Range is 30.00 to 56.00 dBmV per channel in 0.01 dBmV steps.
         
         Value must be within >= -8.00 dBmV below and <= 4.00 dBmV above DRFI nominal 
         for the number of channels in-use(*) based on max 48 channel output.
         
         (*) In-use = assigned a frequency, unmuted, and not suppressed.
        "
::= { apexRfConfigBlade6RfPortEntry 4 }

apexRfConfigBlade6RfPortDiagSuppressMode OBJECT-TYPE
    SYNTAX QamRfDiagSuppressModeTYPE
    MAX-ACCESS read-write
    STATUS current
    DESCRIPTION
        "Diagnostic Suppression Mode of the RF Port.
                 
         none               - No suppression.
         oneChannel         - One channel suppressed
         allChannelsButOne  - All channels suppressed except one
         allChannels        - All channels suppressed
         
         Use apexRfConfigBlade6RfPortDiagSuppressChannel to define the 'one'
         channel for 'oneChannel' and 'allChannelsButOne' modes.
         
         This setting will override apexRfConfigBlade6ChannelTestMode.
         
         Test mode status is reflected in apexRfStatusChannelOutputMode.
        "
::= { apexRfConfigBlade6RfPortEntry 5 }

apexRfConfigBlade6RfPortDiagSuppressChannel OBJECT-TYPE
    SYNTAX Integer32(1..64)
    MAX-ACCESS read-write
    STATUS current
    DESCRIPTION
        "Channel defined for Diagnostic Suppression.
         
         Used to define the 'one' channel for the 'oneChannel' and
         'allChannelsButOne' modes of apexRfConfigBlade6RfPortDiagSuppressMode.
         
         This setting will override apexRfConfigBlade6ChannelTestMode.
         
         Test mode status is reflected in apexRfStatusChannelOutputMode.
        "
::= { apexRfConfigBlade6RfPortEntry 6 }

apexRfConfigBlade6RfPortNprimeMax OBJECT-TYPE
    SYNTAX Integer32(0..64)
    MAX-ACCESS read-write
    STATUS current
    DESCRIPTION
        "User defined DRFI N'max value used by APEX when RfPortNprimeMaxMode
         is 'manual'.  This parameter is ignored when RfPortNprimeMaxMode
         is 'automatic'.
         
         N'max must be greater than or equal to the number of channels
         in-use (assigned a frequency, unmuted, and not suppressed).
         
         Using the RfPortNprimeMax value guarantees glitchless RF port
         reconfiguration as per the DRFI specification described below.
         
         NOTE: RF performance will be degraded for large differences
               between the number of channels in-use and the user selected
               N'max value.
         
         The N'max value in use by the APEX is reflected in apexRfStatusRfPortNprimeMax.
         
         From CM-SP-DRFI-I10-100611:
         A CMTS or EQAM capable of generating more than eight channels per
         physical RF port MUST be capable of glitchless reconfiguration over
         a range of active channels from ceiling[7*N'max/8] to N'max. Channels
         which are undergoing configuration changes are referred to as the
         'changed channels.' The channels which are active and are not being
         reconfigured are referred to as the 'continuous channels'. Each DRFI
         modulator capable of generating more than eight channels per physical
         RF port MUST accept a command setting N'max. Glitchless reconfiguration
         consists of any of the following actions while introducing no
         discontinuity or detriment to the continuous channels, where the
         modulator is operating in a valid DRFI-required mode both before and
         after the reconfiguration with an active number of channels staying in
         the range {ceiling[7*N'max/8], N'max}: adding and/or deleting one or
         more channels, and/or moving some channels to new RF carrier
         frequencies, and/or changing the interleaver depth, modulation, power
         level, or frequency on one or more channels. Any change in the
         modulation characteristics (power level, modulation density, interleaver
         parameters, center frequency) of a channel excuses that channel from
         being required to operate in a glitchless manner. For example, changing
         the power per channel of a given channel means that channel is not
         considered a continuous channel for the purposes of the glitchless
         modulation requirements. Glitchless operation is not required when N'max
         is changed, even if no reconfigurations accompany the change in N'max.
        "
::= { apexRfConfigBlade6RfPortEntry 7 }

apexRfConfigBlade6RfPortNprimeMaxMode OBJECT-TYPE
    SYNTAX AutomaticManualTYPE
    MAX-ACCESS read-write
    STATUS current
    DESCRIPTION
        "DRFI N'max configuration mode.
        
         'automatic' - In this mode the APEX is responsible for selecting the N'max
                       and will automatically set N'max to the number of channels in-use
                       (assigned a frequency, unmuted, and not suppressed).  This guarantees
                       optimal RF performance for the number of channels in-use but
                       reconfiguration of the RF port may cause RF glitches.  If,
                       after testing, the user determines reconfiguration of RF ports
                       in 'standard' mode causes unacceptable RF interruption, the
                       'advanced' mode may be used.  
         
         'manual'    - In this advanced mode the user is responsible for manually setting
                       N'max in the RfPortNprimeMax parameter.  The APEX will use the value
                       in the RfPortNprimeMax parameter.  This will guarantee glitchless RF
                       port reconfiguration as per the DRFI specification described below.
                       NOTE: RF performance will be degraded for large differences
                             between the number of channels in-use and the user selected
                             N'max value.
         
         The N'max value in use by the APEX is reflected in apexRfStatusRfPortNprimeMax.
         
         From CM-SP-DRFI-I10-100611:
         A CMTS or EQAM capable of generating more than eight channels per
         physical RF port MUST be capable of glitchless reconfiguration over
         a range of active channels from ceiling[7*N'max/8] to N'max. Channels
         which are undergoing configuration changes are referred to as the
         'changed channels.' The channels which are active and are not being
         reconfigured are referred to as the 'continuous channels'. Each DRFI
         modulator capable of generating more than eight channels per physical
         RF port MUST accept a command setting N'max. Glitchless reconfiguration
         consists of any of the following actions while introducing no
         discontinuity or detriment to the continuous channels, where the
         modulator is operating in a valid DRFI-required mode both before and
         after the reconfiguration with an active number of channels staying in
         the range {ceiling[7*N'max/8], N'max}: adding and/or deleting one or
         more channels, and/or moving some channels to new RF carrier
         frequencies, and/or changing the interleaver depth, modulation, power
         level, or frequency on one or more channels. Any change in the
         modulation characteristics (power level, modulation density, interleaver
         parameters, center frequency) of a channel excuses that channel from
         being required to operate in a glitchless manner. For example, changing
         the power per channel of a given channel means that channel is not
         considered a continuous channel for the purposes of the glitchless
         modulation requirements. Glitchless operation is not required when N'max
         is changed, even if no reconfigurations accompany the change in N'max.
        "
::= { apexRfConfigBlade6RfPortEntry 8 }


-- ------------------------------------------------------------------------------
--
-- apexRfConfigBlade6SuperBlockFreqTable
--

apexRfConfigBlade6SuperBlockFreqTable OBJECT-TYPE
    SYNTAX SEQUENCE OF ApexRfConfigBlade6SuperBlockFreqEntry
    MAX-ACCESS not-accessible
    STATUS current
    DESCRIPTION
        "Table of RF Port Super Block Frequency configuration for QAM Blade6.
         
         **** NOTE: Super Block Frequency configuration is currently limited:
         ****       - Super blocks cannot overlap.
         ****       - Super blocks must be in order 1..4 from low to high frequency.
         ****       - Super block 4 frequency must be selected such that the center
         ****         frequency of the last channel of the block is no greater than
         ****         the MAX frequency range (i.e., SB 4 freq <= 813000000 Hz).
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade6 4 }

apexRfConfigBlade6SuperBlockFreqEntry OBJECT-TYPE
    SYNTAX ApexRfConfigBlade6SuperBlockFreqEntry
    MAX-ACCESS not-accessible
    STATUS current
    DESCRIPTION
        "Blade6 RF Port Super Block Frequency Configuration Table Entry."
    INDEX { apexRfConfigBlade6SuperBlockFreqRfPortNum,
            apexRfConfigBlade6SuperBlockFreqBlockNum }
::= { apexRfConfigBlade6SuperBlockFreqTable 1 }

ApexRfConfigBlade6SuperBlockFreqEntry ::= SEQUENCE
    {
     apexRfConfigBlade6SuperBlockFreqRfPortNum  Integer32,
     apexRfConfigBlade6SuperBlockFreqBlockNum   Integer32,
     apexRfConfigBlade6SuperBlockFreqAnnexB     Integer32,
     apexRfConfigBlade6SuperBlockFreqAnnexC     Integer32,
     apexRfConfigBlade6SuperBlockFreqAnnexA     Integer32
    }

apexRfConfigBlade6SuperBlockFreqRfPortNum OBJECT-TYPE
    SYNTAX Integer32(1..4)
    MAX-ACCESS not-accessible
    STATUS current
    DESCRIPTION
        "RF Port number on QAM Blade.
        "
::= { apexRfConfigBlade6SuperBlockFreqEntry 1 }

apexRfConfigBlade6SuperBlockFreqBlockNum OBJECT-TYPE
    SYNTAX Integer32(1..4)
    MAX-ACCESS not-accessible
    STATUS current
    DESCRIPTION
        "Super-block number on RF Port.
        "
::= { apexRfConfigBlade6SuperBlockFreqEntry 2 }

apexRfConfigBlade6SuperBlockFreqAnnexB OBJECT-TYPE
    SYNTAX Integer32(57000000..999000000)
    MAX-ACCESS read-write
    STATUS current
    DESCRIPTION
        "Center frequency of first channel of super-block for Annex B.
         This value must be in Hz in the range 57,000,000 Hz to 999,000,000 Hz
         in 125,000 Hz steps.
         Used only when apexRfStatusTransmissionMode 'annexB-ATSC-DCII'.

         @Range(step=125000)
        "
::= { apexRfConfigBlade6SuperBlockFreqEntry 3 }

apexRfConfigBlade6SuperBlockFreqAnnexC OBJECT-TYPE
    SYNTAX Integer32(57000000..999000000)
    MAX-ACCESS read-write
    STATUS current
    DESCRIPTION
        "Center frequency of first channel of super-block for Annex C.
         This value must be in Hz in the range 57,000,000 Hz to 999,000,000 Hz
         in 125,000 Hz steps.
         Used only when apexRfStatusTransmissionMode 'annexC-Asia-Pacific'.

         @Range(step=125000)
        "
::= { apexRfConfigBlade6SuperBlockFreqEntry 4 }

apexRfConfigBlade6SuperBlockFreqAnnexA OBJECT-TYPE
    SYNTAX Integer32(85000000..999000000)
    MAX-ACCESS read-write
    STATUS current
    DESCRIPTION
        "Center frequency of first channel of super-block for Annex A.
         This value must be in Hz in the range 85,000,000 Hz to 999,000,000 Hz
         in 125,000 Hz steps.
         Used only when apexRfStatusTransmissionMode 'annexA-DVB'.

         @Range(step=125000)
        "
::= { apexRfConfigBlade6SuperBlockFreqEntry 5 }


-- ------------------------------------------------------------------------------
--
-- apexRfConfigBlade6SubBlockFreqTable
--

apexRfConfigBlade6SubBlockFreqTable OBJECT-TYPE
    SYNTAX SEQUENCE OF ApexRfConfigBlade6SubBlockFreqEntry
    MAX-ACCESS not-accessible
    STATUS current
    DESCRIPTION
        "TABLE NOT SUPPORTED.
         
         Table of RF Port Sub Block Frequency configuration for QAM Blade6.
         
         **** NOTE: This table is currently unsupported in APEX3000.
         ****       APEX3000 will set values consistent with settings
         ****       in blade Super Block Frequency Table.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade6 5 }

apexRfConfigBlade6SubBlockFreqEntry OBJECT-TYPE
    SYNTAX ApexRfConfigBlade6SubBlockFreqEntry
    MAX-ACCESS not-accessible
    STATUS current
    DESCRIPTION
        "Blade6 RF Port Sub Block Frequency Configuration Table Entry."
    INDEX { apexRfConfigBlade6SubBlockFreqRfPortNum,
            apexRfConfigBlade6SubBlockFreqBlockNum }
::= { apexRfConfigBlade6SubBlockFreqTable 1 }

ApexRfConfigBlade6SubBlockFreqEntry ::= SEQUENCE
    {
     apexRfConfigBlade6SubBlockFreqRfPortNum      Integer32,
     apexRfConfigBlade6SubBlockFreqBlockNum       Integer32,
     apexRfConfigBlade6SubBlockFreqAnnexB         Integer32,
     apexRfConfigBlade6SubBlockFreqAnnexC         Integer32,
     apexRfConfigBlade6SubBlockFreqAnnexA         Integer32,
     apexRfConfigBlade6SubBlockChanSpacingAnnexA  Integer32
    }

apexRfConfigBlade6SubBlockFreqRfPortNum OBJECT-TYPE
    SYNTAX Integer32(1..4)
    MAX-ACCESS not-accessible
    STATUS current
    DESCRIPTION
        "RF Port number on QAM Blade.
        "
::= { apexRfConfigBlade6SubBlockFreqEntry 1 }

apexRfConfigBlade6SubBlockFreqBlockNum OBJECT-TYPE
    SYNTAX Integer32(1..16)
    MAX-ACCESS not-accessible
    STATUS current
    DESCRIPTION
        "Sub-block number on RF Port.
        "
::= { apexRfConfigBlade6SubBlockFreqEntry 2 }

apexRfConfigBlade6SubBlockFreqAnnexB OBJECT-TYPE
    SYNTAX Integer32(57000000..999000000)
    MAX-ACCESS read-write
    STATUS current
    DESCRIPTION
        "Center frequency of first channel of sub-block for Annex B.
         This value must be in Hz in the range 57,000,000 Hz to 999,000,000 Hz
         in 125,000 Hz steps.
         Used only when apexRfStatusTransmissionMode 'annexB-ATSC-DCII'.

         @Range(step=125000)
        "
::= { apexRfConfigBlade6SubBlockFreqEntry 3 }

apexRfConfigBlade6SubBlockFreqAnnexC OBJECT-TYPE
    SYNTAX Integer32(57000000..999000000)
    MAX-ACCESS read-write
    STATUS current
    DESCRIPTION
        "Center frequency of first channel of sub-block for Annex C.
         This value must be in Hz in the range 57,000,000 Hz to 999,000,000 Hz
         in 125,000 Hz steps.
         Used only when apexRfStatusTransmissionMode 'annexC-Asia-Pacific'.

         @Range(step=125000)
        "
::= { apexRfConfigBlade6SubBlockFreqEntry 4 }

apexRfConfigBlade6SubBlockFreqAnnexA OBJECT-TYPE
    SYNTAX Integer32(85000000..999000000)
    MAX-ACCESS read-write
    STATUS current
    DESCRIPTION
        "Center frequency of first channel of sub-block for Annex A.
         This value must be in Hz in the range 85,000,000 Hz to 999,000,000 Hz
         in 125,000 Hz steps.
         Used only when apexRfStatusTransmissionMode 'annexA-DVB'.

         @Range(step=125000)
        "
::= { apexRfConfigBlade6SubBlockFreqEntry 5 }

apexRfConfigBlade6SubBlockChanSpacingAnnexA OBJECT-TYPE
    SYNTAX Integer32(1000000..8000000)
    MAX-ACCESS read-write
    STATUS current
    DESCRIPTION
        "*** This entry is not supported. ***
         
         Channel spacing of sub-block for Annex A.
         This value must be in Hz in the range 1,000,000 Hz to 8,000,000 Hz
         in 500,000 Hz steps.
         Used only when apexRfStatusTransmissionMode 'annexA-DVB'.

         @Range(step=500000)
        "
::= { apexRfConfigBlade6SubBlockFreqEntry 6 }


-- ------------------------------------------------------------------------------
--
-- apexRfConfigBlade6ChannelTable
--

apexRfConfigBlade6ChannelTable OBJECT-TYPE
    SYNTAX SEQUENCE OF ApexRfConfigBlade6ChannelEntry
    MAX-ACCESS not-accessible
    STATUS current
    DESCRIPTION
        "Table of QAM Channel configuration for QAM Blade6.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade6 6 }

apexRfConfigBlade6ChannelEntry OBJECT-TYPE
    SYNTAX ApexRfConfigBlade6ChannelEntry
    MAX-ACCESS not-accessible
    STATUS current
    DESCRIPTION
        "Blade6 QAM Channel Configuration Table Entry."
    INDEX { apexRfConfigBlade6ChannelRfPortNum,
            apexRfConfigBlade6ChannelChanNum }
::= { apexRfConfigBlade6ChannelTable 1 }

ApexRfConfigBlade6ChannelEntry ::= SEQUENCE
    {
     apexRfConfigBlade6ChannelRfPortNum              Integer32,
     apexRfConfigBlade6ChannelChanNum                Integer32,
     apexRfConfigBlade6ChannelFrequencyGridSelect    Integer32,
     apexRfConfigBlade6ChannelModeComboSelectAnnexA  Integer32,
     apexRfConfigBlade6ChannelModeComboSelectAnnexB  Integer32,
     apexRfConfigBlade6ChannelModeComboSelectAnnexC  Integer32,
     apexRfConfigBlade6ChannelRfLevelAdjust          Integer32,
     apexRfConfigBlade6ChannelTestMode               QamChannelTestModeTYPE,
     apexRfConfigBlade6ChannelMute                   QamRfMuteTYPE
    }

apexRfConfigBlade6ChannelRfPortNum OBJECT-TYPE
    SYNTAX Integer32(1..4)
    MAX-ACCESS not-accessible
    STATUS current
    DESCRIPTION
        "RF Port number on QAM Blade.
        "
::= { apexRfConfigBlade6ChannelEntry 1 }

apexRfConfigBlade6ChannelChanNum OBJECT-TYPE
    SYNTAX Integer32(1..64)
    MAX-ACCESS not-accessible
    STATUS current
    DESCRIPTION
        "QAM channel number on RF Port.
        "
::= { apexRfConfigBlade6ChannelEntry 2 }

apexRfConfigBlade6ChannelFrequencyGridSelect OBJECT-TYPE
    SYNTAX Integer32(0..128)
    MAX-ACCESS read-write
    STATUS current
    DESCRIPTION
        "RF Port frequency grid slot selection for this channel.
         Zero indicates the channel is not in use (disabled).
         
         The frequency is selected from a grid of 128 total frequency assignment
         selections (or 'slots').  The grid is divided into 4 super blocks (192
         MHz wide) with 32 assignment slots each.  Each super block is divided
         into 4 sub blocks (48 MHz wide) with 8 assignment slots each.  Using 'B'
         for super blocks and 'b' sub blocks numbering of super and sub blocks is
         B1..B4 and b1..b16 respectively.  The sub blocks are contained in
         superblocks as follows:
            B1[b1..b4],
            B2[b5..b8],
            B3[b9..b12], and
            B4[b13..b16].
         Numbering of the slots within the blocks is as follows:
            B1[b1(1..8), b2(9..16), b3(17..24), b4(25..32)],
            B2[b5(33..40), b6(41..48), b7(49..56), b8(57..64)],
            B3[b9(65..72), b10(73..80), b11(81..88), b12(89..96)], and
            B4[b13(97..105), b14(106..112), b15(113..120), b16(121..128)].

         Annex B/C: For apexRfStatusTransmissionMode of 'annexB-ATSC-DCII' or
         'annexC-Asia-Pacific' the full range of slots [1..128] may be selected.

         Annex A: For apexRfStatusTransmissionMode of 'annexA-DVB' not all slots
         may be selected.  Since a sub block represents a 48 MHz wide band and
         'annexA-DVB' channel spacing is currently a fixed 8 MHz, only the first
         6 slots in each sub block can be assigned.  Therefore, the 'annexA-DVB'
         assignments may be as follows:
            B1[b1(1..6), b2(9..14), b3(17..22), b4(25..30)],
            B2[b5(33..38), b6(41..46), b7(49..54), b8(57..62)],
            B3[b9(65..70), b10(73..78), b11(81..86), b12(89..94)], and
            B4[b13(97..102), b14(105..110), b15(113..118), b16(121..126)].
         The APEX3000 will automatically clear any assignments to the following
         slots:
            B1[b1(7, 8), b2(15, 16), b3(23, 24), b4(31, 32)],
            B2[b5(39, 40), b6(47, 48), b7(55, 56), b8(63, 64)],
            B3[b9(71, 72), b10(79, 80), b11(87, 88), b12(95, 96)], and
            B4[b13(103, 104), b14(111, 112), b15(119, 120), b16(127, 128)].
        "
::= { apexRfConfigBlade6ChannelEntry 3 }

apexRfConfigBlade6ChannelModeComboSelectAnnexA OBJECT-TYPE
    SYNTAX Integer32(1..4)
    MAX-ACCESS read-write
    STATUS current
    DESCRIPTION
        "QAM Mode Combination selection for Annex A.
         Mode combinations are configured in apexRfConfigBlade6ModesTable.
         Used only when apexRfStatusTransmissionMode 'annexA-DVB'.
        "
::= { apexRfConfigBlade6ChannelEntry 4 }

apexRfConfigBlade6ChannelModeComboSelectAnnexB OBJECT-TYPE
    SYNTAX Integer32(1..4)
    MAX-ACCESS read-write
    STATUS current
    DESCRIPTION
        "QAM Mode Combination selection for Annex B.
         Mode combinations are configured in apexRfConfigBlade6ModesTable.
         Used only when apexRfStatusTransmissionMode 'annexB-ATSC-DCII'.
        "
::= { apexRfConfigBlade6ChannelEntry 5 }

apexRfConfigBlade6ChannelModeComboSelectAnnexC OBJECT-TYPE
    SYNTAX Integer32(1..4)
    MAX-ACCESS read-write
    STATUS current
    DESCRIPTION
        "QAM Mode Combination selection for Annex C.
         Mode combinations are configured in apexRfConfigBlade6ModesTable.
         Used only when apexRfStatusTransmissionMode 'annexC-Asia-Pacific'.
        "
::= { apexRfConfigBlade6ChannelEntry 6 }

apexRfConfigBlade6ChannelRfLevelAdjust OBJECT-TYPE
    SYNTAX Integer32(-20..0)
    MAX-ACCESS read-write
    STATUS current
    DESCRIPTION
        "RF Level adjustment for the channel.
         
         Range is -2.0 dB to 0.0 dB relative to apexRfConfigBlade6RfPortRfLevel.
         Value is in 0.1 dB steps.
         
         Final RF Level after adjustment applied must be within >= -8.00 dB below
         and <= 4.00 dB above DRFI nominal for the number of channels in-use(*)
         based on max 48 channel output.
         
         (*) In-use = assigned a frequency, unmuted, and not suppressed.
        "
::= { apexRfConfigBlade6ChannelEntry 7 }

apexRfConfigBlade6ChannelTestMode OBJECT-TYPE
    SYNTAX QamChannelTestModeTYPE
    MAX-ACCESS read-write
    STATUS current
    DESCRIPTION
        "Test mode for the channel.
         
         RF Port diagnostic suppression configuration will override
         this setting.  (apexRfConfigBlade6RfPortDiagSuppressMode and
         apexRfConfigBlade6RfPortDiagSuppressChannel)
         
         Test mode status is reflected in apexRfStatusChannelOutputMode.
         
         noTest     - Test mode is off.  Channel is in normal operation.
         suppress   - Suppress the channel.
         cwtest     - CW test.
         prbs23m    - PRBS-23 with MPEG Sync.
         prbsUnique - Unique PRBS. Multiple channels configured in this
                      mode will transmit uncorrelated data. Pattern is
                      generated in the APEX.
         mpegNull   - MPEG Null packets.
         biPhase    - Bi-phase Mode (alternating symbols).
        "
::= { apexRfConfigBlade6ChannelEntry 8 }

apexRfConfigBlade6ChannelMute OBJECT-TYPE
    SYNTAX QamRfMuteTYPE
    MAX-ACCESS read-write
    STATUS current
    DESCRIPTION
        "Mute the QAM Channel.
        "
::= { apexRfConfigBlade6ChannelEntry 9 }


-- ------------------------------------------------------------------------------
--
-- apexRfConfigBlade7
--
-- apexRfConfigBlade7General
--

-- none


-- ------------------------------------------------------------------------------
--
-- apexRfConfigBlade7ModesTable
--

apexRfConfigBlade7ModesTable OBJECT-TYPE
    SYNTAX SEQUENCE OF ApexRfConfigBlade7ModesEntry
    MAX-ACCESS not-accessible
    STATUS current
    DESCRIPTION
        "Table of RF Mode Combinations for QAM Blade7.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade7 2 }

apexRfConfigBlade7ModesEntry OBJECT-TYPE
    SYNTAX ApexRfConfigBlade7ModesEntry
    MAX-ACCESS not-accessible
    STATUS current
    DESCRIPTION
        "RF Configuration Blade7 RF Mode Combinations Table Entry."
    INDEX { apexRfConfigBlade7ModesIndex }
::= { apexRfConfigBlade7ModesTable 1 }

ApexRfConfigBlade7ModesEntry ::= SEQUENCE
    {
     apexRfConfigBlade7ModesIndex                   Integer32,
     apexRfConfigBlade7ModesModulationModeAnnexB    QamRfModulationModeTYPE,
     apexRfConfigBlade7ModesInterleaverDepthAnnexB  QamRfInterleaverDepthAnnexBTYPE,
     apexRfConfigBlade7ModesModulationModeAnnexA    QamRfModulationModeTYPE,
     apexRfConfigBlade7ModesSymbolRateAnnexA        Integer32,
     apexRfConfigBlade7ModesModulationModeAnnexC    QamRfModulationModeTYPE,
     apexRfConfigBlade7ModesSymbolRateAnnexC        Integer32
    }

apexRfConfigBlade7ModesIndex OBJECT-TYPE
    SYNTAX Integer32(1..4)
    MAX-ACCESS not-accessible
    STATUS current
    DESCRIPTION
        "Index for RF Configuration Blade7 RF Mode Combinations Table.
        "
::= { apexRfConfigBlade7ModesEntry 1 }

apexRfConfigBlade7ModesModulationModeAnnexB OBJECT-TYPE
    SYNTAX QamRfModulationModeTYPE
    MAX-ACCESS read-write
    STATUS current
    DESCRIPTION
        "QAM RF Modulation mode for Annex B.
         Used only when apexRfStatusTransmissionMode 'annexB-ATSC-DCII'.
        "
::= { apexRfConfigBlade7ModesEntry 2 }

apexRfConfigBlade7ModesInterleaverDepthAnnexB OBJECT-TYPE
    SYNTAX QamRfInterleaverDepthAnnexBTYPE
    MAX-ACCESS read-write
    STATUS current
    DESCRIPTION
        "QAM RF Interleaver setting for Annex B.

         Used only when apexRfStatusTransmissionMode 'annexB-ATSC-DCII'.
        "
::= { apexRfConfigBlade7ModesEntry 3 }

apexRfConfigBlade7ModesModulationModeAnnexA OBJECT-TYPE
    SYNTAX QamRfModulationModeTYPE
    MAX-ACCESS read-write
    STATUS current
    DESCRIPTION
        "QAM RF Modulation mode for Annex A.
         Only used when apexRfStatusTransmissionMode is 'annexA-DVB'.
        "
::= { apexRfConfigBlade7ModesEntry 4 }

apexRfConfigBlade7ModesSymbolRateAnnexA OBJECT-TYPE
    SYNTAX Integer32(1000000..6980000)
    MAX-ACCESS read-write
    STATUS current
    DESCRIPTION
        "QAM RF Symbol Rate for Annex A.
         Only used when apexRfStatusTransmissionMode is 'annexA-DVB'.
         It is in symbols per second (sps) in 1000 sps steps.

         @Range(step=1000)
        "
::= { apexRfConfigBlade7ModesEntry 5 }

apexRfConfigBlade7ModesModulationModeAnnexC OBJECT-TYPE
    SYNTAX QamRfModulationModeTYPE
    MAX-ACCESS read-write
    STATUS current
    DESCRIPTION
        "QAM RF Modulation mode for Annex C.
         Used only when apexRfStatusTransmissionMode 'annexC-Asia-Pacific'.
        "
::= { apexRfConfigBlade7ModesEntry 6 }

apexRfConfigBlade7ModesSymbolRateAnnexC OBJECT-TYPE
    SYNTAX Integer32(800000..5310000)
    MAX-ACCESS read-write
    STATUS current
    DESCRIPTION
        "QAM RF Symbol Rate for Annex C.
         Only used when apexRfStatusTransmissionMode is 'annexC-Asia-Pacific'.
         It is in symbols per second (sps) in 1000 sps steps.

         @Range(step=1000)
        "
::= { apexRfConfigBlade7ModesEntry 7 }


-- ------------------------------------------------------------------------------
--
-- apexRfConfigBlade7RfPortTable
--

apexRfConfigBlade7RfPortTable OBJECT-TYPE
    SYNTAX SEQUENCE OF ApexRfConfigBlade7RfPortEntry
    MAX-ACCESS not-accessible
    STATUS current
    DESCRIPTION
        "Table of RF Port configuration for QAM Blade7.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade7 3 }

apexRfConfigBlade7RfPortEntry OBJECT-TYPE
    SYNTAX ApexRfConfigBlade7RfPortEntry
    MAX-ACCESS not-accessible
    STATUS current
    DESCRIPTION
        "Blade7 RF Port Configuration Table Entry."
    INDEX { apexRfConfigBlade7RfPortNum }
::= { apexRfConfigBlade7RfPortTable 1 }

ApexRfConfigBlade7RfPortEntry ::= SEQUENCE
    {
     apexRfConfigBlade7RfPortNum                   Integer32,
     apexRfConfigBlade7RfPortSpectrumInversion     QamRfSpectrumInversionTYPE,
     apexRfConfigBlade7RfPortMute                  QamRfMuteTYPE,
     apexRfConfigBlade7RfPortRfLevel               Integer32,
     apexRfConfigBlade7RfPortDiagSuppressMode      QamRfDiagSuppressModeTYPE,
     apexRfConfigBlade7RfPortDiagSuppressChannel   Integer32,
     apexRfConfigBlade7RfPortNprimeMax             Integer32,
     apexRfConfigBlade7RfPortNprimeMaxMode         AutomaticManualTYPE
    }

apexRfConfigBlade7RfPortNum OBJECT-TYPE
    SYNTAX Integer32(1..4)
    MAX-ACCESS not-accessible
    STATUS current
    DESCRIPTION
        "RF Port number on QAM Blade.
        "
::= { apexRfConfigBlade7RfPortEntry 1 }

apexRfConfigBlade7RfPortSpectrumInversion OBJECT-TYPE
    SYNTAX QamRfSpectrumInversionTYPE
    MAX-ACCESS read-write
    STATUS current
    DESCRIPTION
        "The Spectrum Inversion Setting of the QAM Channels
         on the RF Port.
        "
::= { apexRfConfigBlade7RfPortEntry 2 }

apexRfConfigBlade7RfPortMute OBJECT-TYPE
    SYNTAX QamRfMuteTYPE
    MAX-ACCESS read-write
    STATUS current
    DESCRIPTION
        "Mute the RF Port.  This will mute all QAM channels on the
         RF Port.
        "
::= { apexRfConfigBlade7RfPortEntry 3 }

apexRfConfigBlade7RfPortRfLevel OBJECT-TYPE
    SYNTAX Integer32(3000..5600)
    MAX-ACCESS read-write
    STATUS current
    DESCRIPTION
        "The RF level setting of each channel in-use(*) on the RF Port.
         
         Range is 30.00 to 56.00 dBmV per channel in 0.01 dBmV steps.
         
         Value must be within >= -8.00 dBmV below and <= 4.00 dBmV above DRFI nominal 
         for the number of channels in-use(*) based on max 48 channel output.
         
         (*) In-use = assigned a frequency, unmuted, and not suppressed.
        "
::= { apexRfConfigBlade7RfPortEntry 4 }

apexRfConfigBlade7RfPortDiagSuppressMode OBJECT-TYPE
    SYNTAX QamRfDiagSuppressModeTYPE
    MAX-ACCESS read-write
    STATUS current
    DESCRIPTION
        "Diagnostic Suppression Mode of the RF Port.
                 
         none               - No suppression.
         oneChannel         - One channel suppressed
         allChannelsButOne  - All channels suppressed except one
         allChannels        - All channels suppressed
         
         Use apexRfConfigBlade7RfPortDiagSuppressChannel to define the 'one'
         channel for 'oneChannel' and 'allChannelsButOne' modes.
         
         This setting will override apexRfConfigBlade7ChannelTestMode.
         
         Test mode status is reflected in apexRfStatusChannelOutputMode.
        "
::= { apexRfConfigBlade7RfPortEntry 5 }

apexRfConfigBlade7RfPortDiagSuppressChannel OBJECT-TYPE
    SYNTAX Integer32(1..64)
    MAX-ACCESS read-write
    STATUS current
    DESCRIPTION
        "Channel defined for Diagnostic Suppression.
         
         Used to define the 'one' channel for the 'oneChannel' and
         'allChannelsButOne' modes of apexRfConfigBlade7RfPortDiagSuppressMode.
         
         This setting will override apexRfConfigBlade7ChannelTestMode.
         
         Test mode status is reflected in apexRfStatusChannelOutputMode.
        "
::= { apexRfConfigBlade7RfPortEntry 6 }

apexRfConfigBlade7RfPortNprimeMax OBJECT-TYPE
    SYNTAX Integer32(0..64)
    MAX-ACCESS read-write
    STATUS current
    DESCRIPTION
        "User defined DRFI N'max value used by APEX when RfPortNprimeMaxMode
         is 'manual'.  This parameter is ignored when RfPortNprimeMaxMode
         is 'automatic'.
         
         N'max must be greater than or equal to the number of channels
         in-use (assigned a frequency, unmuted, and not suppressed).
         
         Using the RfPortNprimeMax value guarantees glitchless RF port
         reconfiguration as per the DRFI specification described below.
         
         NOTE: RF performance will be degraded for large differences
               between the number of channels in-use and the user selected
               N'max value.
         
         The N'max value in use by the APEX is reflected in apexRfStatusRfPortNprimeMax.
         
         From CM-SP-DRFI-I10-100611:
         A CMTS or EQAM capable of generating more than eight channels per
         physical RF port MUST be capable of glitchless reconfiguration over
         a range of active channels from ceiling[7*N'max/8] to N'max. Channels
         which are undergoing configuration changes are referred to as the
         'changed channels.' The channels which are active and are not being
         reconfigured are referred to as the 'continuous channels'. Each DRFI
         modulator capable of generating more than eight channels per physical
         RF port MUST accept a command setting N'max. Glitchless reconfiguration
         consists of any of the following actions while introducing no
         discontinuity or detriment to the continuous channels, where the
         modulator is operating in a valid DRFI-required mode both before and
         after the reconfiguration with an active number of channels staying in
         the range {ceiling[7*N'max/8], N'max}: adding and/or deleting one or
         more channels, and/or moving some channels to new RF carrier
         frequencies, and/or changing the interleaver depth, modulation, power
         level, or frequency on one or more channels. Any change in the
         modulation characteristics (power level, modulation density, interleaver
         parameters, center frequency) of a channel excuses that channel from
         being required to operate in a glitchless manner. For example, changing
         the power per channel of a given channel means that channel is not
         considered a continuous channel for the purposes of the glitchless
         modulation requirements. Glitchless operation is not required when N'max
         is changed, even if no reconfigurations accompany the change in N'max.
        "
::= { apexRfConfigBlade7RfPortEntry 7 }

apexRfConfigBlade7RfPortNprimeMaxMode OBJECT-TYPE
    SYNTAX AutomaticManualTYPE
    MAX-ACCESS read-write
    STATUS current
    DESCRIPTION
        "DRFI N'max configuration mode.
        
         'automatic' - In this mode the APEX is responsible for selecting the N'max
                       and will automatically set N'max to the number of channels in-use
                       (assigned a frequency, unmuted, and not suppressed).  This guarantees
                       optimal RF performance for the number of channels in-use but
                       reconfiguration of the RF port may cause RF glitches.  If,
                       after testing, the user determines reconfiguration of RF ports
                       in 'standard' mode causes unacceptable RF interruption, the
                       'advanced' mode may be used.  
         
         'manual'    - In this advanced mode the user is responsible for manually setting
                       N'max in the RfPortNprimeMax parameter.  The APEX will use the value
                       in the RfPortNprimeMax parameter.  This will guarantee glitchless RF
                       port reconfiguration as per the DRFI specification described below.
                       NOTE: RF performance will be degraded for large differences
                             between the number of channels in-use and the user selected
                             N'max value.
         
         The N'max value in use by the APEX is reflected in apexRfStatusRfPortNprimeMax.
         
         From CM-SP-DRFI-I10-100611:
         A CMTS or EQAM capable of generating more than eight channels per
         physical RF port MUST be capable of glitchless reconfiguration over
         a range of active channels from ceiling[7*N'max/8] to N'max. Channels
         which are undergoing configuration changes are referred to as the
         'changed channels.' The channels which are active and are not being
         reconfigured are referred to as the 'continuous channels'. Each DRFI
         modulator capable of generating more than eight channels per physical
         RF port MUST accept a command setting N'max. Glitchless reconfiguration
         consists of any of the following actions while introducing no
         discontinuity or detriment to the continuous channels, where the
         modulator is operating in a valid DRFI-required mode both before and
         after the reconfiguration with an active number of channels staying in
         the range {ceiling[7*N'max/8], N'max}: adding and/or deleting one or
         more channels, and/or moving some channels to new RF carrier
         frequencies, and/or changing the interleaver depth, modulation, power
         level, or frequency on one or more channels. Any change in the
         modulation characteristics (power level, modulation density, interleaver
         parameters, center frequency) of a channel excuses that channel from
         being required to operate in a glitchless manner. For example, changing
         the power per channel of a given channel means that channel is not
         considered a continuous channel for the purposes of the glitchless
         modulation requirements. Glitchless operation is not required when N'max
         is changed, even if no reconfigurations accompany the change in N'max.
        "
::= { apexRfConfigBlade7RfPortEntry 8 }


-- ------------------------------------------------------------------------------
--
-- apexRfConfigBlade7SuperBlockFreqTable
--

apexRfConfigBlade7SuperBlockFreqTable OBJECT-TYPE
    SYNTAX SEQUENCE OF ApexRfConfigBlade7SuperBlockFreqEntry
    MAX-ACCESS not-accessible
    STATUS current
    DESCRIPTION
        "Table of RF Port Super Block Frequency configuration for QAM Blade7.
         
         **** NOTE: Super Block Frequency configuration is currently limited:
         ****       - Super blocks cannot overlap.
         ****       - Super blocks must be in order 1..4 from low to high frequency.
         ****       - Super block 4 frequency must be selected such that the center
         ****         frequency of the last channel of the block is no greater than
         ****         the MAX frequency range (i.e., SB 4 freq <= 813000000 Hz).
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade7 4 }

apexRfConfigBlade7SuperBlockFreqEntry OBJECT-TYPE
    SYNTAX ApexRfConfigBlade7SuperBlockFreqEntry
    MAX-ACCESS not-accessible
    STATUS current
    DESCRIPTION
        "Blade7 RF Port Super Block Frequency Configuration Table Entry."
    INDEX { apexRfConfigBlade7SuperBlockFreqRfPortNum,
            apexRfConfigBlade7SuperBlockFreqBlockNum }
::= { apexRfConfigBlade7SuperBlockFreqTable 1 }

ApexRfConfigBlade7SuperBlockFreqEntry ::= SEQUENCE
    {
     apexRfConfigBlade7SuperBlockFreqRfPortNum  Integer32,
     apexRfConfigBlade7SuperBlockFreqBlockNum   Integer32,
     apexRfConfigBlade7SuperBlockFreqAnnexB     Integer32,
     apexRfConfigBlade7SuperBlockFreqAnnexC     Integer32,
     apexRfConfigBlade7SuperBlockFreqAnnexA     Integer32
    }

apexRfConfigBlade7SuperBlockFreqRfPortNum OBJECT-TYPE
    SYNTAX Integer32(1..4)
    MAX-ACCESS not-accessible
    STATUS current
    DESCRIPTION
        "RF Port number on QAM Blade.
        "
::= { apexRfConfigBlade7SuperBlockFreqEntry 1 }

apexRfConfigBlade7SuperBlockFreqBlockNum OBJECT-TYPE
    SYNTAX Integer32(1..4)
    MAX-ACCESS not-accessible
    STATUS current
    DESCRIPTION
        "Super-block number on RF Port.
        "
::= { apexRfConfigBlade7SuperBlockFreqEntry 2 }

apexRfConfigBlade7SuperBlockFreqAnnexB OBJECT-TYPE
    SYNTAX Integer32(57000000..999000000)
    MAX-ACCESS read-write
    STATUS current
    DESCRIPTION
        "Center frequency of first channel of super-block for Annex B.
         This value must be in Hz in the range 57,000,000 Hz to 999,000,000 Hz
         in 125,000 Hz steps.
         Used only when apexRfStatusTransmissionMode 'annexB-ATSC-DCII'.

         @Range(step=125000)
        "
::= { apexRfConfigBlade7SuperBlockFreqEntry 3 }

apexRfConfigBlade7SuperBlockFreqAnnexC OBJECT-TYPE
    SYNTAX Integer32(57000000..999000000)
    MAX-ACCESS read-write
    STATUS current
    DESCRIPTION
        "Center frequency of first channel of super-block for Annex C.
         This value must be in Hz in the range 57,000,000 Hz to 999,000,000 Hz
         in 125,000 Hz steps.
         Used only when apexRfStatusTransmissionMode 'annexC-Asia-Pacific'.

         @Range(step=125000)
        "
::= { apexRfConfigBlade7SuperBlockFreqEntry 4 }

apexRfConfigBlade7SuperBlockFreqAnnexA OBJECT-TYPE
    SYNTAX Integer32(85000000..999000000)
    MAX-ACCESS read-write
    STATUS current
    DESCRIPTION
        "Center frequency of first channel of super-block for Annex A.
         This value must be in Hz in the range 85,000,000 Hz to 999,000,000 Hz
         in 125,000 Hz steps.
         Used only when apexRfStatusTransmissionMode 'annexA-DVB'.

         @Range(step=125000)
        "
::= { apexRfConfigBlade7SuperBlockFreqEntry 5 }


-- ------------------------------------------------------------------------------
--
-- apexRfConfigBlade7SubBlockFreqTable
--

apexRfConfigBlade7SubBlockFreqTable OBJECT-TYPE
    SYNTAX SEQUENCE OF ApexRfConfigBlade7SubBlockFreqEntry
    MAX-ACCESS not-accessible
    STATUS current
    DESCRIPTION
        "TABLE NOT SUPPORTED.
         
         Table of RF Port Sub Block Frequency configuration for QAM Blade7.
         
         **** NOTE: This table is currently unsupported in APEX3000.
         ****       APEX3000 will set values consistent with settings
         ****       in blade Super Block Frequency Table.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade7 5 }

apexRfConfigBlade7SubBlockFreqEntry OBJECT-TYPE
    SYNTAX ApexRfConfigBlade7SubBlockFreqEntry
    MAX-ACCESS not-accessible
    STATUS current
    DESCRIPTION
        "Blade7 RF Port Sub Block Frequency Configuration Table Entry."
    INDEX { apexRfConfigBlade7SubBlockFreqRfPortNum,
            apexRfConfigBlade7SubBlockFreqBlockNum }
::= { apexRfConfigBlade7SubBlockFreqTable 1 }

ApexRfConfigBlade7SubBlockFreqEntry ::= SEQUENCE
    {
     apexRfConfigBlade7SubBlockFreqRfPortNum      Integer32,
     apexRfConfigBlade7SubBlockFreqBlockNum       Integer32,
     apexRfConfigBlade7SubBlockFreqAnnexB         Integer32,
     apexRfConfigBlade7SubBlockFreqAnnexC         Integer32,
     apexRfConfigBlade7SubBlockFreqAnnexA         Integer32,
     apexRfConfigBlade7SubBlockChanSpacingAnnexA  Integer32
    }

apexRfConfigBlade7SubBlockFreqRfPortNum OBJECT-TYPE
    SYNTAX Integer32(1..4)
    MAX-ACCESS not-accessible
    STATUS current
    DESCRIPTION
        "RF Port number on QAM Blade.
        "
::= { apexRfConfigBlade7SubBlockFreqEntry 1 }

apexRfConfigBlade7SubBlockFreqBlockNum OBJECT-TYPE
    SYNTAX Integer32(1..16)
    MAX-ACCESS not-accessible
    STATUS current
    DESCRIPTION
        "Sub-block number on RF Port.
        "
::= { apexRfConfigBlade7SubBlockFreqEntry 2 }

apexRfConfigBlade7SubBlockFreqAnnexB OBJECT-TYPE
    SYNTAX Integer32(57000000..999000000)
    MAX-ACCESS read-write
    STATUS current
    DESCRIPTION
        "Center frequency of first channel of sub-block for Annex B.
         This value must be in Hz in the range 57,000,000 Hz to 999,000,000 Hz
         in 125,000 Hz steps.
         Used only when apexRfStatusTransmissionMode 'annexB-ATSC-DCII'.

         @Range(step=125000)
        "
::= { apexRfConfigBlade7SubBlockFreqEntry 3 }

apexRfConfigBlade7SubBlockFreqAnnexC OBJECT-TYPE
    SYNTAX Integer32(57000000..999000000)
    MAX-ACCESS read-write
    STATUS current
    DESCRIPTION
        "Center frequency of first channel of sub-block for Annex C.
         This value must be in Hz in the range 57,000,000 Hz to 999,000,000 Hz
         in 125,000 Hz steps.
         Used only when apexRfStatusTransmissionMode 'annexC-Asia-Pacific'.

         @Range(step=125000)
        "
::= { apexRfConfigBlade7SubBlockFreqEntry 4 }

apexRfConfigBlade7SubBlockFreqAnnexA OBJECT-TYPE
    SYNTAX Integer32(85000000..999000000)
    MAX-ACCESS read-write
    STATUS current
    DESCRIPTION
        "Center frequency of first channel of sub-block for Annex A.
         This value must be in Hz in the range 85,000,000 Hz to 999,000,000 Hz
         in 125,000 Hz steps.
         Used only when apexRfStatusTransmissionMode 'annexA-DVB'.

         @Range(step=125000)
        "
::= { apexRfConfigBlade7SubBlockFreqEntry 5 }

apexRfConfigBlade7SubBlockChanSpacingAnnexA OBJECT-TYPE
    SYNTAX Integer32(1000000..8000000)
    MAX-ACCESS read-write
    STATUS current
    DESCRIPTION
        "*** This entry is not supported. ***
         
         Channel spacing of sub-block for Annex A.
         This value must be in Hz in the range 1,000,000 Hz to 8,000,000 Hz
         in 500,000 Hz steps.
         Used only when apexRfStatusTransmissionMode 'annexA-DVB'.

         @Range(step=500000)
        "
::= { apexRfConfigBlade7SubBlockFreqEntry 6 }


-- ------------------------------------------------------------------------------
--
-- apexRfConfigBlade7ChannelTable
--

apexRfConfigBlade7ChannelTable OBJECT-TYPE
    SYNTAX SEQUENCE OF ApexRfConfigBlade7ChannelEntry
    MAX-ACCESS not-accessible
    STATUS current
    DESCRIPTION
        "Table of QAM Channel configuration for QAM Blade7.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade7 6 }

apexRfConfigBlade7ChannelEntry OBJECT-TYPE
    SYNTAX ApexRfConfigBlade7ChannelEntry
    MAX-ACCESS not-accessible
    STATUS current
    DESCRIPTION
        "Blade7 QAM Channel Configuration Table Entry."
    INDEX { apexRfConfigBlade7ChannelRfPortNum,
            apexRfConfigBlade7ChannelChanNum }
::= { apexRfConfigBlade7ChannelTable 1 }

ApexRfConfigBlade7ChannelEntry ::= SEQUENCE
    {
     apexRfConfigBlade7ChannelRfPortNum              Integer32,
     apexRfConfigBlade7ChannelChanNum                Integer32,
     apexRfConfigBlade7ChannelFrequencyGridSelect    Integer32,
     apexRfConfigBlade7ChannelModeComboSelectAnnexA  Integer32,
     apexRfConfigBlade7ChannelModeComboSelectAnnexB  Integer32,
     apexRfConfigBlade7ChannelModeComboSelectAnnexC  Integer32,
     apexRfConfigBlade7ChannelRfLevelAdjust          Integer32,
     apexRfConfigBlade7ChannelTestMode               QamChannelTestModeTYPE,
     apexRfConfigBlade7ChannelMute                   QamRfMuteTYPE
    }

apexRfConfigBlade7ChannelRfPortNum OBJECT-TYPE
    SYNTAX Integer32(1..4)
    MAX-ACCESS not-accessible
    STATUS current
    DESCRIPTION
        "RF Port number on QAM Blade.
        "
::= { apexRfConfigBlade7ChannelEntry 1 }

apexRfConfigBlade7ChannelChanNum OBJECT-TYPE
    SYNTAX Integer32(1..64)
    MAX-ACCESS not-accessible
    STATUS current
    DESCRIPTION
        "QAM channel number on RF Port.
        "
::= { apexRfConfigBlade7ChannelEntry 2 }

apexRfConfigBlade7ChannelFrequencyGridSelect OBJECT-TYPE
    SYNTAX Integer32(0..128)
    MAX-ACCESS read-write
    STATUS current
    DESCRIPTION
        "RF Port frequency grid slot selection for this channel.
         Zero indicates the channel is not in use (disabled).
         
         The frequency is selected from a grid of 128 total frequency assignment
         selections (or 'slots').  The grid is divided into 4 super blocks (192
         MHz wide) with 32 assignment slots each.  Each super block is divided
         into 4 sub blocks (48 MHz wide) with 8 assignment slots each.  Using 'B'
         for super blocks and 'b' sub blocks numbering of super and sub blocks is
         B1..B4 and b1..b16 respectively.  The sub blocks are contained in
         superblocks as follows:
            B1[b1..b4],
            B2[b5..b8],
            B3[b9..b12], and
            B4[b13..b16].
         Numbering of the slots within the blocks is as follows:
            B1[b1(1..8), b2(9..16), b3(17..24), b4(25..32)],
            B2[b5(33..40), b6(41..48), b7(49..56), b8(57..64)],
            B3[b9(65..72), b10(73..80), b11(81..88), b12(89..96)], and
            B4[b13(97..105), b14(106..112), b15(113..120), b16(121..128)].

         Annex B/C: For apexRfStatusTransmissionMode of 'annexB-ATSC-DCII' or
         'annexC-Asia-Pacific' the full range of slots [1..128] may be selected.

         Annex A: For apexRfStatusTransmissionMode of 'annexA-DVB' not all slots
         may be selected.  Since a sub block represents a 48 MHz wide band and
         'annexA-DVB' channel spacing is currently a fixed 8 MHz, only the first
         6 slots in each sub block can be assigned.  Therefore, the 'annexA-DVB'
         assignments may be as follows:
            B1[b1(1..6), b2(9..14), b3(17..22), b4(25..30)],
            B2[b5(33..38), b6(41..46), b7(49..54), b8(57..62)],
            B3[b9(65..70), b10(73..78), b11(81..86), b12(89..94)], and
            B4[b13(97..102), b14(105..110), b15(113..118), b16(121..126)].
         The APEX3000 will automatically clear any assignments to the following
         slots:
            B1[b1(7, 8), b2(15, 16), b3(23, 24), b4(31, 32)],
            B2[b5(39, 40), b6(47, 48), b7(55, 56), b8(63, 64)],
            B3[b9(71, 72), b10(79, 80), b11(87, 88), b12(95, 96)], and
            B4[b13(103, 104), b14(111, 112), b15(119, 120), b16(127, 128)].
        "
::= { apexRfConfigBlade7ChannelEntry 3 }

apexRfConfigBlade7ChannelModeComboSelectAnnexA OBJECT-TYPE
    SYNTAX Integer32(1..4)
    MAX-ACCESS read-write
    STATUS current
    DESCRIPTION
        "QAM Mode Combination selection for Annex A.
         Mode combinations are configured in apexRfConfigBlade7ModesTable.
         Used only when apexRfStatusTransmissionMode 'annexA-DVB'.
        "
::= { apexRfConfigBlade7ChannelEntry 4 }

apexRfConfigBlade7ChannelModeComboSelectAnnexB OBJECT-TYPE
    SYNTAX Integer32(1..4)
    MAX-ACCESS read-write
    STATUS current
    DESCRIPTION
        "QAM Mode Combination selection for Annex B.
         Mode combinations are configured in apexRfConfigBlade7ModesTable.
         Used only when apexRfStatusTransmissionMode 'annexB-ATSC-DCII'.
        "
::= { apexRfConfigBlade7ChannelEntry 5 }

apexRfConfigBlade7ChannelModeComboSelectAnnexC OBJECT-TYPE
    SYNTAX Integer32(1..4)
    MAX-ACCESS read-write
    STATUS current
    DESCRIPTION
        "QAM Mode Combination selection for Annex C.
         Mode combinations are configured in apexRfConfigBlade7ModesTable.
         Used only when apexRfStatusTransmissionMode 'annexC-Asia-Pacific'.
        "
::= { apexRfConfigBlade7ChannelEntry 6 }

apexRfConfigBlade7ChannelRfLevelAdjust OBJECT-TYPE
    SYNTAX Integer32(-20..0)
    MAX-ACCESS read-write
    STATUS current
    DESCRIPTION
        "RF Level adjustment for the channel.
         
         Range is -2.0 dB to 0.0 dB relative to apexRfConfigBlade7RfPortRfLevel.
         Value is in 0.1 dB steps.
         
         Final RF Level after adjustment applied must be within >= -8.00 dB below
         and <= 4.00 dB above DRFI nominal for the number of channels in-use(*)
         based on max 48 channel output.
         
         (*) In-use = assigned a frequency, unmuted, and not suppressed.
        "
::= { apexRfConfigBlade7ChannelEntry 7 }

apexRfConfigBlade7ChannelTestMode OBJECT-TYPE
    SYNTAX QamChannelTestModeTYPE
    MAX-ACCESS read-write
    STATUS current
    DESCRIPTION
        "Test mode for the channel.
         
         RF Port diagnostic suppression configuration will override
         this setting.  (apexRfConfigBlade7RfPortDiagSuppressMode and
         apexRfConfigBlade7RfPortDiagSuppressChannel)
         
         Test mode status is reflected in apexRfStatusChannelOutputMode.
         
         noTest     - Test mode is off.  Channel is in normal operation.
         suppress   - Suppress the channel.
         cwtest     - CW test.
         prbs23m    - PRBS-23 with MPEG Sync.
         prbsUnique - Unique PRBS. Multiple channels configured in this
                      mode will transmit uncorrelated data. Pattern is
                      generated in the APEX.
         mpegNull   - MPEG Null packets.
         biPhase    - Bi-phase Mode (alternating symbols).
        "
::= { apexRfConfigBlade7ChannelEntry 8 }

apexRfConfigBlade7ChannelMute OBJECT-TYPE
    SYNTAX QamRfMuteTYPE
    MAX-ACCESS read-write
    STATUS current
    DESCRIPTION
        "Mute the QAM Channel.
        "
::= { apexRfConfigBlade7ChannelEntry 9 }


-- ------------------------------------------------------------------------------
--
-- apexRfConfigBlade8
--
-- apexRfConfigBlade8General
--

-- none


-- ------------------------------------------------------------------------------
--
-- apexRfConfigBlade8ModesTable
--

apexRfConfigBlade8ModesTable OBJECT-TYPE
    SYNTAX SEQUENCE OF ApexRfConfigBlade8ModesEntry
    MAX-ACCESS not-accessible
    STATUS current
    DESCRIPTION
        "Table of RF Mode Combinations for QAM Blade8.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade8 2 }

apexRfConfigBlade8ModesEntry OBJECT-TYPE
    SYNTAX ApexRfConfigBlade8ModesEntry
    MAX-ACCESS not-accessible
    STATUS current
    DESCRIPTION
        "RF Configuration Blade8 RF Mode Combinations Table Entry."
    INDEX { apexRfConfigBlade8ModesIndex }
::= { apexRfConfigBlade8ModesTable 1 }

ApexRfConfigBlade8ModesEntry ::= SEQUENCE
    {
     apexRfConfigBlade8ModesIndex                   Integer32,
     apexRfConfigBlade8ModesModulationModeAnnexB    QamRfModulationModeTYPE,
     apexRfConfigBlade8ModesInterleaverDepthAnnexB  QamRfInterleaverDepthAnnexBTYPE,
     apexRfConfigBlade8ModesModulationModeAnnexA    QamRfModulationModeTYPE,
     apexRfConfigBlade8ModesSymbolRateAnnexA        Integer32,
     apexRfConfigBlade8ModesModulationModeAnnexC    QamRfModulationModeTYPE,
     apexRfConfigBlade8ModesSymbolRateAnnexC        Integer32
    }

apexRfConfigBlade8ModesIndex OBJECT-TYPE
    SYNTAX Integer32(1..4)
    MAX-ACCESS not-accessible
    STATUS current
    DESCRIPTION
        "Index for RF Configuration Blade8 RF Mode Combinations Table.
        "
::= { apexRfConfigBlade8ModesEntry 1 }

apexRfConfigBlade8ModesModulationModeAnnexB OBJECT-TYPE
    SYNTAX QamRfModulationModeTYPE
    MAX-ACCESS read-write
    STATUS current
    DESCRIPTION
        "QAM RF Modulation mode for Annex B.
         Used only when apexRfStatusTransmissionMode 'annexB-ATSC-DCII'.
        "
::= { apexRfConfigBlade8ModesEntry 2 }

apexRfConfigBlade8ModesInterleaverDepthAnnexB OBJECT-TYPE
    SYNTAX QamRfInterleaverDepthAnnexBTYPE
    MAX-ACCESS read-write
    STATUS current
    DESCRIPTION
        "QAM RF Interleaver setting for Annex B.
         Used only when apexRfStatusTransmissionMode 'annexB-ATSC-DCII'.
        "
::= { apexRfConfigBlade8ModesEntry 3 }

apexRfConfigBlade8ModesModulationModeAnnexA OBJECT-TYPE
    SYNTAX QamRfModulationModeTYPE
    MAX-ACCESS read-write
    STATUS current
    DESCRIPTION
        "QAM RF Modulation mode for Annex A.
         Only used when apexRfStatusTransmissionMode is 'annexA-DVB'.
        "
::= { apexRfConfigBlade8ModesEntry 4 }

apexRfConfigBlade8ModesSymbolRateAnnexA OBJECT-TYPE
    SYNTAX Integer32(1000000..6980000)
    MAX-ACCESS read-write
    STATUS current
    DESCRIPTION
        "QAM RF Symbol Rate for Annex A.
         Only used when apexRfStatusTransmissionMode is 'annexA-DVB'.
         It is in symbols per second (sps) in 1000 sps steps.

         @Range(step=1000)
        "
::= { apexRfConfigBlade8ModesEntry 5 }

apexRfConfigBlade8ModesModulationModeAnnexC OBJECT-TYPE
    SYNTAX QamRfModulationModeTYPE
    MAX-ACCESS read-write
    STATUS current
    DESCRIPTION
        "QAM RF Modulation mode for Annex C.
         Used only when apexRfStatusTransmissionMode 'annexC-Asia-Pacific'.
        "
::= { apexRfConfigBlade8ModesEntry 6 }

apexRfConfigBlade8ModesSymbolRateAnnexC OBJECT-TYPE
    SYNTAX Integer32(800000..5310000)
    MAX-ACCESS read-write
    STATUS current
    DESCRIPTION
        "QAM RF Symbol Rate for Annex C.
         Only used when apexRfStatusTransmissionMode is 'annexC-Asia-Pacific'.
         It is in symbols per second (sps) in 1000 sps steps.

         @Range(step=1000)
        "
::= { apexRfConfigBlade8ModesEntry 7 }


-- ------------------------------------------------------------------------------
--
-- apexRfConfigBlade8RfPortTable
--

apexRfConfigBlade8RfPortTable OBJECT-TYPE
    SYNTAX SEQUENCE OF ApexRfConfigBlade8RfPortEntry
    MAX-ACCESS not-accessible
    STATUS current
    DESCRIPTION
        "Table of RF Port configuration for QAM Blade8.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade8 3 }

apexRfConfigBlade8RfPortEntry OBJECT-TYPE
    SYNTAX ApexRfConfigBlade8RfPortEntry
    MAX-ACCESS not-accessible
    STATUS current
    DESCRIPTION
        "Blade8 RF Port Configuration Table Entry."
    INDEX { apexRfConfigBlade8RfPortNum }
::= { apexRfConfigBlade8RfPortTable 1 }

ApexRfConfigBlade8RfPortEntry ::= SEQUENCE
    {
     apexRfConfigBlade8RfPortNum                   Integer32,
     apexRfConfigBlade8RfPortSpectrumInversion     QamRfSpectrumInversionTYPE,
     apexRfConfigBlade8RfPortMute                  QamRfMuteTYPE,
     apexRfConfigBlade8RfPortRfLevel               Integer32,
     apexRfConfigBlade8RfPortDiagSuppressMode      QamRfDiagSuppressModeTYPE,
     apexRfConfigBlade8RfPortDiagSuppressChannel   Integer32,
     apexRfConfigBlade8RfPortNprimeMax             Integer32,
     apexRfConfigBlade8RfPortNprimeMaxMode         AutomaticManualTYPE
    }

apexRfConfigBlade8RfPortNum OBJECT-TYPE
    SYNTAX Integer32(1..4)
    MAX-ACCESS not-accessible
    STATUS current
    DESCRIPTION
        "RF Port number on QAM Blade.
        "
::= { apexRfConfigBlade8RfPortEntry 1 }

apexRfConfigBlade8RfPortSpectrumInversion OBJECT-TYPE
    SYNTAX QamRfSpectrumInversionTYPE
    MAX-ACCESS read-write
    STATUS current
    DESCRIPTION
        "The Spectrum Inversion Setting of the QAM Channels
         on the RF Port.
        "
::= { apexRfConfigBlade8RfPortEntry 2 }

apexRfConfigBlade8RfPortMute OBJECT-TYPE
    SYNTAX QamRfMuteTYPE
    MAX-ACCESS read-write
    STATUS current
    DESCRIPTION
        "Mute the RF Port.  This will mute all QAM channels on the
         RF Port.
        "
::= { apexRfConfigBlade8RfPortEntry 3 }

apexRfConfigBlade8RfPortRfLevel OBJECT-TYPE
    SYNTAX Integer32(3000..5600)
    MAX-ACCESS read-write
    STATUS current
    DESCRIPTION
        "The RF level setting of each channel in-use(*) on the RF Port.
         
         Range is 30.00 to 56.00 dBmV per channel in 0.01 dBmV steps.
         
         Value must be within >= -8.00 dBmV below and <= 4.00 dBmV above DRFI nominal 
         for the number of channels in-use(*) based on max 48 channel output.
         
         (*) In-use = assigned a frequency, unmuted, and not suppressed.
        "
::= { apexRfConfigBlade8RfPortEntry 4 }

apexRfConfigBlade8RfPortDiagSuppressMode OBJECT-TYPE
    SYNTAX QamRfDiagSuppressModeTYPE
    MAX-ACCESS read-write
    STATUS current
    DESCRIPTION
        "Diagnostic Suppression Mode of the RF Port.
                 
         none               - No suppression.
         oneChannel         - One channel suppressed
         allChannelsButOne  - All channels suppressed except one
         allChannels        - All channels suppressed
         
         Use apexRfConfigBlade8RfPortDiagSuppressChannel to define the 'one'
         channel for 'oneChannel' and 'allChannelsButOne' modes.
         
         This setting will override apexRfConfigBlade8ChannelTestMode.
         
         Test mode status is reflected in apexRfStatusChannelOutputMode.
        "
::= { apexRfConfigBlade8RfPortEntry 5 }

apexRfConfigBlade8RfPortDiagSuppressChannel OBJECT-TYPE
    SYNTAX Integer32(1..64)
    MAX-ACCESS read-write
    STATUS current
    DESCRIPTION
        "Channel defined for Diagnostic Suppression.
         
         Used to define the 'one' channel for the 'oneChannel' and
         'allChannelsButOne' modes of apexRfConfigBlade8RfPortDiagSuppressMode.
         
         This setting will override apexRfConfigBlade8ChannelTestMode.
         
         Test mode status is reflected in apexRfStatusChannelOutputMode.
        "
::= { apexRfConfigBlade8RfPortEntry 6 }

apexRfConfigBlade8RfPortNprimeMax OBJECT-TYPE
    SYNTAX Integer32(0..64)
    MAX-ACCESS read-write
    STATUS current
    DESCRIPTION
        "User defined DRFI N'max value used by APEX when RfPortNprimeMaxMode
         is 'manual'.  This parameter is ignored when RfPortNprimeMaxMode
         is 'automatic'.
         
         N'max must be greater than or equal to the number of channels
         in-use (assigned a frequency, unmuted, and not suppressed).
         
         Using the RfPortNprimeMax value guarantees glitchless RF port
         reconfiguration as per the DRFI specification described below.
         
         NOTE: RF performance will be degraded for large differences
               between the number of channels in-use and the user selected
               N'max value.
         
         The N'max value in use by the APEX is reflected in apexRfStatusRfPortNprimeMax.
         
         From CM-SP-DRFI-I10-100611:
         A CMTS or EQAM capable of generating more than eight channels per
         physical RF port MUST be capable of glitchless reconfiguration over
         a range of active channels from ceiling[7*N'max/8] to N'max. Channels
         which are undergoing configuration changes are referred to as the
         'changed channels.' The channels which are active and are not being
         reconfigured are referred to as the 'continuous channels'. Each DRFI
         modulator capable of generating more than eight channels per physical
         RF port MUST accept a command setting N'max. Glitchless reconfiguration
         consists of any of the following actions while introducing no
         discontinuity or detriment to the continuous channels, where the
         modulator is operating in a valid DRFI-required mode both before and
         after the reconfiguration with an active number of channels staying in
         the range {ceiling[7*N'max/8], N'max}: adding and/or deleting one or
         more channels, and/or moving some channels to new RF carrier
         frequencies, and/or changing the interleaver depth, modulation, power
         level, or frequency on one or more channels. Any change in the
         modulation characteristics (power level, modulation density, interleaver
         parameters, center frequency) of a channel excuses that channel from
         being required to operate in a glitchless manner. For example, changing
         the power per channel of a given channel means that channel is not
         considered a continuous channel for the purposes of the glitchless
         modulation requirements. Glitchless operation is not required when N'max
         is changed, even if no reconfigurations accompany the change in N'max.
        "
::= { apexRfConfigBlade8RfPortEntry 7 }

apexRfConfigBlade8RfPortNprimeMaxMode OBJECT-TYPE
    SYNTAX AutomaticManualTYPE
    MAX-ACCESS read-write
    STATUS current
    DESCRIPTION
        "DRFI N'max configuration mode.
        
         'automatic' - In this mode the APEX is responsible for selecting the N'max
                       and will automatically set N'max to the number of channels in-use
                       (assigned a frequency, unmuted, and not suppressed).  This guarantees
                       optimal RF performance for the number of channels in-use but
                       reconfiguration of the RF port may cause RF glitches.  If,
                       after testing, the user determines reconfiguration of RF ports
                       in 'standard' mode causes unacceptable RF interruption, the
                       'advanced' mode may be used.  
         
         'manual'    - In this advanced mode the user is responsible for manually setting
                       N'max in the RfPortNprimeMax parameter.  The APEX will use the value
                       in the RfPortNprimeMax parameter.  This will guarantee glitchless RF
                       port reconfiguration as per the DRFI specification described below.
                       NOTE: RF performance will be degraded for large differences
                             between the number of channels in-use and the user selected
                             N'max value.
         
         The N'max value in use by the APEX is reflected in apexRfStatusRfPortNprimeMax.
         
         From CM-SP-DRFI-I10-100611:
         A CMTS or EQAM capable of generating more than eight channels per
         physical RF port MUST be capable of glitchless reconfiguration over
         a range of active channels from ceiling[7*N'max/8] to N'max. Channels
         which are undergoing configuration changes are referred to as the
         'changed channels.' The channels which are active and are not being
         reconfigured are referred to as the 'continuous channels'. Each DRFI
         modulator capable of generating more than eight channels per physical
         RF port MUST accept a command setting N'max. Glitchless reconfiguration
         consists of any of the following actions while introducing no
         discontinuity or detriment to the continuous channels, where the
         modulator is operating in a valid DRFI-required mode both before and
         after the reconfiguration with an active number of channels staying in
         the range {ceiling[7*N'max/8], N'max}: adding and/or deleting one or
         more channels, and/or moving some channels to new RF carrier
         frequencies, and/or changing the interleaver depth, modulation, power
         level, or frequency on one or more channels. Any change in the
         modulation characteristics (power level, modulation density, interleaver
         parameters, center frequency) of a channel excuses that channel from
         being required to operate in a glitchless manner. For example, changing
         the power per channel of a given channel means that channel is not
         considered a continuous channel for the purposes of the glitchless
         modulation requirements. Glitchless operation is not required when N'max
         is changed, even if no reconfigurations accompany the change in N'max.
        "
::= { apexRfConfigBlade8RfPortEntry 8 }


-- ------------------------------------------------------------------------------
--
-- apexRfConfigBlade8SuperBlockFreqTable
--

apexRfConfigBlade8SuperBlockFreqTable OBJECT-TYPE
    SYNTAX SEQUENCE OF ApexRfConfigBlade8SuperBlockFreqEntry
    MAX-ACCESS not-accessible
    STATUS current
    DESCRIPTION
        "Table of RF Port Super Block Frequency configuration for QAM Blade8.
         
         **** NOTE: Super Block Frequency configuration is currently limited:
         ****       - Super blocks cannot overlap.
         ****       - Super blocks must be in order 1..4 from low to high frequency.
         ****       - Super block 4 frequency must be selected such that the center
         ****         frequency of the last channel of the block is no greater than
         ****         the MAX frequency range (i.e., SB 4 freq <= 813000000 Hz).
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade8 4 }

apexRfConfigBlade8SuperBlockFreqEntry OBJECT-TYPE
    SYNTAX ApexRfConfigBlade8SuperBlockFreqEntry
    MAX-ACCESS not-accessible
    STATUS current
    DESCRIPTION
        "Blade8 RF Port Super Block Frequency Configuration Table Entry."
    INDEX { apexRfConfigBlade8SuperBlockFreqRfPortNum,
            apexRfConfigBlade8SuperBlockFreqBlockNum }
::= { apexRfConfigBlade8SuperBlockFreqTable 1 }

ApexRfConfigBlade8SuperBlockFreqEntry ::= SEQUENCE
    {
     apexRfConfigBlade8SuperBlockFreqRfPortNum  Integer32,
     apexRfConfigBlade8SuperBlockFreqBlockNum   Integer32,
     apexRfConfigBlade8SuperBlockFreqAnnexB     Integer32,
     apexRfConfigBlade8SuperBlockFreqAnnexC     Integer32,
     apexRfConfigBlade8SuperBlockFreqAnnexA     Integer32
    }

apexRfConfigBlade8SuperBlockFreqRfPortNum OBJECT-TYPE
    SYNTAX Integer32(1..4)
    MAX-ACCESS not-accessible
    STATUS current
    DESCRIPTION
        "RF Port number on QAM Blade.
        "
::= { apexRfConfigBlade8SuperBlockFreqEntry 1 }

apexRfConfigBlade8SuperBlockFreqBlockNum OBJECT-TYPE
    SYNTAX Integer32(1..4)
    MAX-ACCESS not-accessible
    STATUS current
    DESCRIPTION
        "Super-block number on RF Port.
        "
::= { apexRfConfigBlade8SuperBlockFreqEntry 2 }

apexRfConfigBlade8SuperBlockFreqAnnexB OBJECT-TYPE
    SYNTAX Integer32(57000000..999000000)
    MAX-ACCESS read-write
    STATUS current
    DESCRIPTION
        "Center frequency of first channel of super-block for Annex B.
         This value must be in Hz in the range 57,000,000 Hz to 999,000,000 Hz
         in 125,000 Hz steps.
         Used only when apexRfStatusTransmissionMode 'annexB-ATSC-DCII'.

         @Range(step=125000)
        "
::= { apexRfConfigBlade8SuperBlockFreqEntry 3 }

apexRfConfigBlade8SuperBlockFreqAnnexC OBJECT-TYPE
    SYNTAX Integer32(57000000..999000000)
    MAX-ACCESS read-write
    STATUS current
    DESCRIPTION
        "Center frequency of first channel of super-block for Annex C.
         This value must be in Hz in the range 57,000,000 Hz to 999,000,000 Hz
         in 125,000 Hz steps.
         Used only when apexRfStatusTransmissionMode 'annexC-Asia-Pacific'.

         @Range(step=125000)
        "
::= { apexRfConfigBlade8SuperBlockFreqEntry 4 }

apexRfConfigBlade8SuperBlockFreqAnnexA OBJECT-TYPE
    SYNTAX Integer32(85000000..999000000)
    MAX-ACCESS read-write
    STATUS current
    DESCRIPTION
        "Center frequency of first channel of super-block for Annex A.
         This value must be in Hz in the range 85,000,000 Hz to 999,000,000 Hz
         in 125,000 Hz steps.
         Used only when apexRfStatusTransmissionMode 'annexA-DVB'.

         @Range(step=125000)
        "
::= { apexRfConfigBlade8SuperBlockFreqEntry 5 }


-- ------------------------------------------------------------------------------
--
-- apexRfConfigBlade8SubBlockFreqTable
--

apexRfConfigBlade8SubBlockFreqTable OBJECT-TYPE
    SYNTAX SEQUENCE OF ApexRfConfigBlade8SubBlockFreqEntry
    MAX-ACCESS not-accessible
    STATUS current
    DESCRIPTION
        "TABLE NOT SUPPORTED.
         
         Table of RF Port Sub Block Frequency configuration for QAM Blade8.
         
         **** NOTE: This table is currently unsupported in APEX3000.
         ****       APEX3000 will set values consistent with settings
         ****       in blade Super Block Frequency Table.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade8 5 }

apexRfConfigBlade8SubBlockFreqEntry OBJECT-TYPE
    SYNTAX ApexRfConfigBlade8SubBlockFreqEntry
    MAX-ACCESS not-accessible
    STATUS current
    DESCRIPTION
        "Blade8 RF Port Sub Block Frequency Configuration Table Entry."
    INDEX { apexRfConfigBlade8SubBlockFreqRfPortNum,
            apexRfConfigBlade8SubBlockFreqBlockNum }
::= { apexRfConfigBlade8SubBlockFreqTable 1 }

ApexRfConfigBlade8SubBlockFreqEntry ::= SEQUENCE
    {
     apexRfConfigBlade8SubBlockFreqRfPortNum      Integer32,
     apexRfConfigBlade8SubBlockFreqBlockNum       Integer32,
     apexRfConfigBlade8SubBlockFreqAnnexB         Integer32,
     apexRfConfigBlade8SubBlockFreqAnnexC         Integer32,
     apexRfConfigBlade8SubBlockFreqAnnexA         Integer32,
     apexRfConfigBlade8SubBlockChanSpacingAnnexA  Integer32
    }

apexRfConfigBlade8SubBlockFreqRfPortNum OBJECT-TYPE
    SYNTAX Integer32(1..4)
    MAX-ACCESS not-accessible
    STATUS current
    DESCRIPTION
        "RF Port number on QAM Blade.
        "
::= { apexRfConfigBlade8SubBlockFreqEntry 1 }

apexRfConfigBlade8SubBlockFreqBlockNum OBJECT-TYPE
    SYNTAX Integer32(1..16)
    MAX-ACCESS not-accessible
    STATUS current
    DESCRIPTION
        "Sub-block number on RF Port.
        "
::= { apexRfConfigBlade8SubBlockFreqEntry 2 }

apexRfConfigBlade8SubBlockFreqAnnexB OBJECT-TYPE
    SYNTAX Integer32(57000000..999000000)
    MAX-ACCESS read-write
    STATUS current
    DESCRIPTION
        "Center frequency of first channel of sub-block for Annex B.
         This value must be in Hz in the range 57,000,000 Hz to 999,000,000 Hz
         in 125,000 Hz steps.
         Used only when apexRfStatusTransmissionMode 'annexB-ATSC-DCII'.

         @Range(step=125000)
        "
::= { apexRfConfigBlade8SubBlockFreqEntry 3 }

apexRfConfigBlade8SubBlockFreqAnnexC OBJECT-TYPE
    SYNTAX Integer32(57000000..999000000)
    MAX-ACCESS read-write
    STATUS current
    DESCRIPTION
        "Center frequency of first channel of sub-block for Annex C.
         This value must be in Hz in the range 57,000,000 Hz to 999,000,000 Hz
         in 125,000 Hz steps.
         Used only when apexRfStatusTransmissionMode 'annexC-Asia-Pacific'.

         @Range(step=125000)
        "
::= { apexRfConfigBlade8SubBlockFreqEntry 4 }

apexRfConfigBlade8SubBlockFreqAnnexA OBJECT-TYPE
    SYNTAX Integer32(85000000..999000000)
    MAX-ACCESS read-write
    STATUS current
    DESCRIPTION
        "Center frequency of first channel of sub-block for Annex A.
         This value must be in Hz in the range 85,000,000 Hz to 999,000,000 Hz
         in 125,000 Hz steps.
         Used only when apexRfStatusTransmissionMode 'annexA-DVB'.

         @Range(step=125000)
        "
::= { apexRfConfigBlade8SubBlockFreqEntry 5 }

apexRfConfigBlade8SubBlockChanSpacingAnnexA OBJECT-TYPE
    SYNTAX Integer32(1000000..8000000)
    MAX-ACCESS read-write
    STATUS current
    DESCRIPTION
        "*** This entry is not supported. ***
         
         Channel spacing of sub-block for Annex A.
         This value must be in Hz in the range 1,000,000 Hz to 8,000,000 Hz
         in 500,000 Hz steps.
         Used only when apexRfStatusTransmissionMode 'annexA-DVB'.

         @Range(step=500000)
        "
::= { apexRfConfigBlade8SubBlockFreqEntry 6 }


-- ------------------------------------------------------------------------------
--
-- apexRfConfigBlade8ChannelTable
--

apexRfConfigBlade8ChannelTable OBJECT-TYPE
    SYNTAX SEQUENCE OF ApexRfConfigBlade8ChannelEntry
    MAX-ACCESS not-accessible
    STATUS current
    DESCRIPTION
        "Table of QAM Channel configuration for QAM Blade8.
         
         Once written, the change to this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfigBlade8 6 }

apexRfConfigBlade8ChannelEntry OBJECT-TYPE
    SYNTAX ApexRfConfigBlade8ChannelEntry
    MAX-ACCESS not-accessible
    STATUS current
    DESCRIPTION
        "Blade8 QAM Channel Configuration Table Entry."
    INDEX { apexRfConfigBlade8ChannelRfPortNum,
            apexRfConfigBlade8ChannelChanNum }
::= { apexRfConfigBlade8ChannelTable 1 }

ApexRfConfigBlade8ChannelEntry ::= SEQUENCE
    {
     apexRfConfigBlade8ChannelRfPortNum              Integer32,
     apexRfConfigBlade8ChannelChanNum                Integer32,
     apexRfConfigBlade8ChannelFrequencyGridSelect    Integer32,
     apexRfConfigBlade8ChannelModeComboSelectAnnexA  Integer32,
     apexRfConfigBlade8ChannelModeComboSelectAnnexB  Integer32,
     apexRfConfigBlade8ChannelModeComboSelectAnnexC  Integer32,
     apexRfConfigBlade8ChannelRfLevelAdjust          Integer32,
     apexRfConfigBlade8ChannelTestMode               QamChannelTestModeTYPE,
     apexRfConfigBlade8ChannelMute                   QamRfMuteTYPE
    }

apexRfConfigBlade8ChannelRfPortNum OBJECT-TYPE
    SYNTAX Integer32(1..4)
    MAX-ACCESS not-accessible
    STATUS current
    DESCRIPTION
        "RF Port number on QAM Blade.
        "
::= { apexRfConfigBlade8ChannelEntry 1 }

apexRfConfigBlade8ChannelChanNum OBJECT-TYPE
    SYNTAX Integer32(1..64)
    MAX-ACCESS not-accessible
    STATUS current
    DESCRIPTION
        "QAM channel number on RF Port.
        "
::= { apexRfConfigBlade8ChannelEntry 2 }

apexRfConfigBlade8ChannelFrequencyGridSelect OBJECT-TYPE
    SYNTAX Integer32(0..128)
    MAX-ACCESS read-write
    STATUS current
    DESCRIPTION
        "RF Port frequency grid slot selection for this channel.
         Zero indicates the channel is not in use (disabled).
         
         The frequency is selected from a grid of 128 total frequency assignment
         selections (or 'slots').  The grid is divided into 4 super blocks (192
         MHz wide) with 32 assignment slots each.  Each super block is divided
         into 4 sub blocks (48 MHz wide) with 8 assignment slots each.  Using 'B'
         for super blocks and 'b' sub blocks numbering of super and sub blocks is
         B1..B4 and b1..b16 respectively.  The sub blocks are contained in
         superblocks as follows:
            B1[b1..b4],
            B2[b5..b8],
            B3[b9..b12], and
            B4[b13..b16].
         Numbering of the slots within the blocks is as follows:
            B1[b1(1..8), b2(9..16), b3(17..24), b4(25..32)],
            B2[b5(33..40), b6(41..48), b7(49..56), b8(57..64)],
            B3[b9(65..72), b10(73..80), b11(81..88), b12(89..96)], and
            B4[b13(97..105), b14(106..112), b15(113..120), b16(121..128)].

         Annex B/C: For apexRfStatusTransmissionMode of 'annexB-ATSC-DCII' or
         'annexC-Asia-Pacific' the full range of slots [1..128] may be selected.

         Annex A: For apexRfStatusTransmissionMode of 'annexA-DVB' not all slots
         may be selected.  Since a sub block represents a 48 MHz wide band and
         'annexA-DVB' channel spacing is currently a fixed 8 MHz, only the first
         6 slots in each sub block can be assigned.  Therefore, the 'annexA-DVB'
         assignments may be as follows:
            B1[b1(1..6), b2(9..14), b3(17..22), b4(25..30)],
            B2[b5(33..38), b6(41..46), b7(49..54), b8(57..62)],
            B3[b9(65..70), b10(73..78), b11(81..86), b12(89..94)], and
            B4[b13(97..102), b14(105..110), b15(113..118), b16(121..126)].
         The APEX3000 will automatically clear any assignments to the following
         slots:
            B1[b1(7, 8), b2(15, 16), b3(23, 24), b4(31, 32)],
            B2[b5(39, 40), b6(47, 48), b7(55, 56), b8(63, 64)],
            B3[b9(71, 72), b10(79, 80), b11(87, 88), b12(95, 96)], and
            B4[b13(103, 104), b14(111, 112), b15(119, 120), b16(127, 128)].
        "
::= { apexRfConfigBlade8ChannelEntry 3 }

apexRfConfigBlade8ChannelModeComboSelectAnnexA OBJECT-TYPE
    SYNTAX Integer32(1..4)
    MAX-ACCESS read-write
    STATUS current
    DESCRIPTION
        "QAM Mode Combination selection for Annex A.
         Mode combinations are configured in apexRfConfigBlade8ModesTable.
         Used only when apexRfStatusTransmissionMode 'annexA-DVB'.
        "
::= { apexRfConfigBlade8ChannelEntry 4 }

apexRfConfigBlade8ChannelModeComboSelectAnnexB OBJECT-TYPE
    SYNTAX Integer32(1..4)
    MAX-ACCESS read-write
    STATUS current
    DESCRIPTION
        "QAM Mode Combination selection for Annex B.
         Mode combinations are configured in apexRfConfigBlade8ModesTable.
         Used only when apexRfStatusTransmissionMode 'annexB-ATSC-DCII'.
        "
::= { apexRfConfigBlade8ChannelEntry 5 }

apexRfConfigBlade8ChannelModeComboSelectAnnexC OBJECT-TYPE
    SYNTAX Integer32(1..4)
    MAX-ACCESS read-write
    STATUS current
    DESCRIPTION
        "QAM Mode Combination selection for Annex C.
         Mode combinations are configured in apexRfConfigBlade8ModesTable.
         Used only when apexRfStatusTransmissionMode 'annexC-Asia-Pacific'.
        "
::= { apexRfConfigBlade8ChannelEntry 6 }

apexRfConfigBlade8ChannelRfLevelAdjust OBJECT-TYPE
    SYNTAX Integer32(-20..0)
    MAX-ACCESS read-write
    STATUS current
    DESCRIPTION
        "RF Level adjustment for the channel.
         
         Range is -2.0 dB to 0.0 dB relative to apexRfConfigBlade8RfPortRfLevel.
         Value is in 0.1 dB steps.
         
         Final RF Level after adjustment applied must be within >= -8.00 dB below
         and <= 4.00 dB above DRFI nominal for the number of channels in-use(*)
         based on max 48 channel output.
         
         (*) In-use = assigned a frequency, unmuted, and not suppressed.
        "
::= { apexRfConfigBlade8ChannelEntry 7 }

apexRfConfigBlade8ChannelTestMode OBJECT-TYPE
    SYNTAX QamChannelTestModeTYPE
    MAX-ACCESS read-write
    STATUS current
    DESCRIPTION
        "Test mode for the channel.
         
         RF Port diagnostic suppression configuration will override
         this setting.  (apexRfConfigBlade8RfPortDiagSuppressMode and
         apexRfConfigBlade8RfPortDiagSuppressChannel)
         
         Test mode status is reflected in apexRfStatusChannelOutputMode.
         
         noTest     - Test mode is off.  Channel is in normal operation.
         suppress   - Suppress the channel.
         cwtest     - CW test.
         prbs23m    - PRBS-23 with MPEG Sync.
         prbsUnique - Unique PRBS. Multiple channels configured in this
                      mode will transmit uncorrelated data. Pattern is
                      generated in the APEX.
         mpegNull   - MPEG Null packets.
         biPhase    - Bi-phase Mode (alternating symbols).
        "
::= { apexRfConfigBlade8ChannelEntry 8 }

apexRfConfigBlade8ChannelMute OBJECT-TYPE
    SYNTAX QamRfMuteTYPE
    MAX-ACCESS read-write
    STATUS current
    DESCRIPTION
        "Mute the QAM Channel.
        "
::= { apexRfConfigBlade8ChannelEntry 9 }


-- ------------------------------------------------------------------------------
--
-- apexRfConfigRfLevelThresholdTable
--

apexRfConfigRfLevelThresholdTable OBJECT-TYPE
    SYNTAX SEQUENCE OF ApexRfConfigRfLevelThresholdEntry
    MAX-ACCESS not-accessible
    STATUS current
    DESCRIPTION
        "Table of RF Level Thresholds Configuration.

         A row in this table corresponds to a blade.
         
         Once written, the change to a row of this table will only take immediate
         effect after apexRfConfigBladeApplyChange is set to 'apply'.  In
         order for the change to persist through subsequent reboots or power
         cycles, the change must be saved via the apexSaveConfig parameter.

         @Config(config=yes, reboot=no)
         @Commit(param=apexRfConfigBladeApplyChange, value=2)
         @Save(apexSaveConfig, value=2)
         @File(qamcfg.ini, type='ini')
        "
::= { apexRfConfig 11 }

apexRfConfigRfLevelThresholdEntry OBJECT-TYPE
    SYNTAX ApexRfConfigRfLevelThresholdEntry
    MAX-ACCESS not-accessible
    STATUS current
    DESCRIPTION
        "RF Level Thresholds Configuration Table Entry."
    INDEX { apexRfConfigRfLevelThresholdBladeNum }
::= { apexRfConfigRfLevelThresholdTable 1 }

ApexRfConfigRfLevelThresholdEntry ::= SEQUENCE
    {
     apexRfConfigRfLevelThresholdBladeNum  Integer32,
     apexRfConfigRfLevelThresholdLow       Integer32,
     apexRfConfigRfLevelThresholdHigh      Integer32
    }

apexRfConfigRfLevelThresholdBladeNum OBJECT-TYPE
    SYNTAX Integer32(1..8)
    MAX-ACCESS not-accessible
    STATUS current
    DESCRIPTION
        "Blade number."
::= { apexRfConfigRfLevelThresholdEntry 1 }

apexRfConfigRfLevelThresholdLow OBJECT-TYPE
    SYNTAX Integer32(0..100)
    MAX-ACCESS read-write
    STATUS current
    DESCRIPTION
        "The threshold delta relative to the configured RF level that will
         indicate an RF Low condition.  The measured output must drop this
         amount for RF Low condition.

         Range is 0 to 100 representing 0 to 10 dB in 0.1 dB steps.
        "
::= { apexRfConfigRfLevelThresholdEntry 2 }

apexRfConfigRfLevelThresholdHigh OBJECT-TYPE
    SYNTAX Integer32(0..100)
    MAX-ACCESS read-write
    STATUS current
    DESCRIPTION
        "The threshold delta relative to the configured RF level that will
         indicate an RF High condition. The measured output must rise this
         amount for RF High condition.

         Range is 0 to 100 representing 0 to 10 dB in 0.1 dB steps.
        "
::= { apexRfConfigRfLevelThresholdEntry 3 }


-- ------------------------------------------------------------------------------
--
-- apexRfStatus
--
-- apexRfStatusGeneral
--

apexRfStatusTransmissionMode OBJECT-TYPE
    SYNTAX QamRfTransmissionModeTYPE
    MAX-ACCESS read-only
    STATUS current
    DESCRIPTION
        "This is the in use QAM RF Transmission Mode as defined in:
         Series J: Transmission of Television, Sound Programme
         and other Multimedia Signals, ITU-T J.83.
        "
::= { apexRfStatusGeneral 1 }


-- ------------------------------------------------------------------------------
--
-- apexRfStatusFrequencyGridTable
--

apexRfStatusFrequencyGridTable OBJECT-TYPE
    SYNTAX SEQUENCE OF ApexRfStatusFrequencyGridEntry
    MAX-ACCESS not-accessible
    STATUS current
    DESCRIPTION
        "QAM RF Frequency Grid Table.
        "
::= { apexRfStatus 2 }

apexRfStatusFrequencyGridEntry OBJECT-TYPE
    SYNTAX ApexRfStatusFrequencyGridEntry
    MAX-ACCESS not-accessible
    STATUS current
    DESCRIPTION
        "QAM RF Frequency Grid Table Entry."
    INDEX { apexRfStatusFrequencyGridBladeNum,
            apexRfStatusFrequencyGridRfPortNum,
            apexRfStatusFrequencyGridIndex }
::= { apexRfStatusFrequencyGridTable 1 }

ApexRfStatusFrequencyGridEntry ::= SEQUENCE
    {
     apexRfStatusFrequencyGridBladeNum   Integer32,
     apexRfStatusFrequencyGridRfPortNum  Integer32,
     apexRfStatusFrequencyGridIndex      Integer32,
     apexRfStatusFrequencyGridFrequency  Integer32
    }

apexRfStatusFrequencyGridBladeNum OBJECT-TYPE
    SYNTAX Integer32(1..8)
    MAX-ACCESS not-accessible
    STATUS current
    DESCRIPTION
        "QAM Blade Number.
        "
::= { apexRfStatusFrequencyGridEntry 1 }

apexRfStatusFrequencyGridRfPortNum OBJECT-TYPE
    SYNTAX Integer32(1..4)
    MAX-ACCESS not-accessible
    STATUS current
    DESCRIPTION
        "RF Port Number.
        "
::= { apexRfStatusFrequencyGridEntry 2 }

apexRfStatusFrequencyGridIndex OBJECT-TYPE
    SYNTAX Integer32(1..128)
    MAX-ACCESS not-accessible
    STATUS current
    DESCRIPTION
        "Frequency slot number.
        "
::= { apexRfStatusFrequencyGridEntry 3 }

apexRfStatusFrequencyGridFrequency OBJECT-TYPE
    SYNTAX Integer32(57000000..999000000)
    MAX-ACCESS read-only
    STATUS current
    DESCRIPTION
        "Frequency for the grid slot in Hz.
        "
::= { apexRfStatusFrequencyGridEntry 4 }


-- ------------------------------------------------------------------------------
--
-- apexRfStatusRfPortTable
--

apexRfStatusRfPortTable OBJECT-TYPE
    SYNTAX SEQUENCE OF ApexRfStatusRfPortEntry
    MAX-ACCESS not-accessible
    STATUS current
    DESCRIPTION
        "QAM RF Port Status Table.
        "
::= { apexRfStatus 3 }

apexRfStatusRfPortEntry OBJECT-TYPE
    SYNTAX ApexRfStatusRfPortEntry
    MAX-ACCESS not-accessible
    STATUS current
    DESCRIPTION
        "QAM RF Port Status Table Entry."
    INDEX { apexRfStatusRfPortBladeNum,
            apexRfStatusRfPortNum }
::= { apexRfStatusRfPortTable 1 }

ApexRfStatusRfPortEntry ::= SEQUENCE
    {
     apexRfStatusRfPortBladeNum             Integer32,
     apexRfStatusRfPortNum                  Integer32,
     apexRfStatusRfPortMute                 QamRfMuteTYPE,
     apexRfStatusRfPortRfLevelNominal       Integer32,
     apexRfStatusRfPortRfLevelSet           Integer32,
     apexRfStatusRfPortSpectrumInversion    QamRfSpectrumInversionTYPE,
     apexRfStatusRfPortDiagSuppressMode     QamRfDiagSuppressModeTYPE,
     apexRfStatusRfPortDiagSuppressChannel  Integer32,
     apexRfStatusRfPortNprimeMax            Integer32
    }

apexRfStatusRfPortBladeNum OBJECT-TYPE
    SYNTAX Integer32(1..8)
    MAX-ACCESS not-accessible
    STATUS current
    DESCRIPTION
        "QAM Blade Number.
        "
::= { apexRfStatusRfPortEntry 1 }

apexRfStatusRfPortNum OBJECT-TYPE
    SYNTAX Integer32(1..4)
    MAX-ACCESS not-accessible
    STATUS current
    DESCRIPTION
        "RF Port Number.
        "
::= { apexRfStatusRfPortEntry 2 }

apexRfStatusRfPortMute OBJECT-TYPE
    SYNTAX QamRfMuteTYPE
    MAX-ACCESS read-only
    STATUS current
    DESCRIPTION
        "Mute status.
        "
::= { apexRfStatusRfPortEntry 3 }

apexRfStatusRfPortRfLevelNominal OBJECT-TYPE
    SYNTAX Integer32
    MAX-ACCESS read-only
    STATUS current
    DESCRIPTION
        "DRFI nominal per channel RF level for the number of channels
         in-use(*) based on max 48 channel output.
         
         Value is dBmV in 0.01 dB steps.
         
         (*) In-use = assigned a frequency, unmuted, and not suppressed.
        "
::= { apexRfStatusRfPortEntry 4 }

apexRfStatusRfPortRfLevelSet OBJECT-TYPE
    SYNTAX Integer32
    MAX-ACCESS read-only
    STATUS current
    DESCRIPTION
        "Per channel RF level setting status.
         Value is dBmV in 0.01 dB steps.
        "
::= { apexRfStatusRfPortEntry 5 }

apexRfStatusRfPortSpectrumInversion OBJECT-TYPE
    SYNTAX QamRfSpectrumInversionTYPE
    MAX-ACCESS read-only
    STATUS current
    DESCRIPTION
        "Spectrum inversion status.
        "
::= { apexRfStatusRfPortEntry 6 }

apexRfStatusRfPortDiagSuppressMode OBJECT-TYPE
    SYNTAX QamRfDiagSuppressModeTYPE
    MAX-ACCESS read-only
    STATUS current
    DESCRIPTION
        "Diagnostic suppression mode status.
        "
::= { apexRfStatusRfPortEntry 7 }

apexRfStatusRfPortDiagSuppressChannel OBJECT-TYPE
    SYNTAX Integer32
    MAX-ACCESS read-only
    STATUS current
    DESCRIPTION
        "Diagnostic suppression channel status.
        "
::= { apexRfStatusRfPortEntry 8 }

apexRfStatusRfPortNprimeMax OBJECT-TYPE
    SYNTAX Integer32
    MAX-ACCESS read-only
    STATUS current
    DESCRIPTION
        "DRFI N'max value in use by APEX.
        "
::= { apexRfStatusRfPortEntry 9 }


-- ------------------------------------------------------------------------------
--
-- apexRfStatusChannelTable
--

apexRfStatusChannelTable OBJECT-TYPE
    SYNTAX SEQUENCE OF ApexRfStatusChannelEntry
    MAX-ACCESS not-accessible
    STATUS current
    DESCRIPTION
        "QAM Channel Status Table.
        "
::= { apexRfStatus 4 }

apexRfStatusChannelEntry OBJECT-TYPE
    SYNTAX ApexRfStatusChannelEntry
    MAX-ACCESS not-accessible
    STATUS current
    DESCRIPTION
        "QAM Channel Status Table Entry."
    INDEX { apexRfStatusChannelBladeNum,
            apexRfStatusChannelRfPortNum,
            apexRfStatusChannelChanNum }
::= { apexRfStatusChannelTable 1 }

ApexRfStatusChannelEntry ::= SEQUENCE
    {
     apexRfStatusChannelBladeNum          Integer32,
     apexRfStatusChannelRfPortNum         Integer32,
     apexRfStatusChannelChanNum           Integer32,
     apexRfStatusChannelFrequency         Integer32,
     apexRfStatusChannelModulationMode    QamRfModulationModeTYPE,
     apexRfStatusChannelSymbolRate        Integer32,
     apexRfStatusChannelInformationRate   Integer32,
     apexRfStatusChannelInterleaverDepth  INTEGER,
     apexRfStatusChannelRfLevelSet        Integer32,
     apexRfStatusChannelOutputMode        INTEGER
    }
apexRfStatusChannelBladeNum OBJECT-TYPE
    SYNTAX Integer32(1..8)
    MAX-ACCESS not-accessible
    STATUS current
    DESCRIPTION
        "QAM Blade Number.
        "
::= { apexRfStatusChannelEntry 1 }

apexRfStatusChannelRfPortNum OBJECT-TYPE
    SYNTAX Integer32(1..4)
    MAX-ACCESS not-accessible
    STATUS current
    DESCRIPTION
        "RF Port Number.
        "
::= { apexRfStatusChannelEntry 2 }

apexRfStatusChannelChanNum OBJECT-TYPE
    SYNTAX Integer32(1..64)
    MAX-ACCESS not-accessible
    STATUS current
    DESCRIPTION
        "Channel Number.
        "
::= { apexRfStatusChannelEntry 3 }

apexRfStatusChannelFrequency OBJECT-TYPE
    SYNTAX Integer32
    MAX-ACCESS read-only
    STATUS current
    DESCRIPTION
        "Frequency in Hz.
         
         Will be zero when channel not in use.
        "
::= { apexRfStatusChannelEntry 4 }

apexRfStatusChannelModulationMode OBJECT-TYPE
    SYNTAX QamRfModulationModeTYPE
    MAX-ACCESS read-only
    STATUS current
    DESCRIPTION
        "Modulation mode.
        "
::= { apexRfStatusChannelEntry 5 }

apexRfStatusChannelSymbolRate OBJECT-TYPE
    SYNTAX Integer32
    MAX-ACCESS read-only
    STATUS current
    DESCRIPTION
        "Symbol rate in symbols per second (sps).
        "
::= { apexRfStatusChannelEntry 6 }

apexRfStatusChannelInformationRate OBJECT-TYPE
    SYNTAX Integer32
    MAX-ACCESS read-only
    STATUS current
    DESCRIPTION
        "Information rate in bits per second.
        "
::= { apexRfStatusChannelEntry 7 }

apexRfStatusChannelInterleaverDepth OBJECT-TYPE
    SYNTAX INTEGER
        {
         notApplicable (0),
         i64-j2        (1),
         i32-j4        (2),
         i16-j8        (3),
         i8-j16        (4),
         i128-j1       (5),
         i128-j2       (6),
         i128-j3       (7),
         i128-j4       (8),
         i128-j5       (9),
         i128-j6       (10),
         i128-j7       (11),
         i128-j8       (12),
         i12-j17       (13)
        }
    MAX-ACCESS read-only
    STATUS current
    DESCRIPTION
        "Interleaver depth.
        "
::= { apexRfStatusChannelEntry 8 }

apexRfStatusChannelRfLevelSet OBJECT-TYPE
    SYNTAX Integer32
    MAX-ACCESS read-only
    STATUS current
    DESCRIPTION
        "RF level set including channel adjustment.
         Value is dBmV in 0.01 dB steps.
        "
::= { apexRfStatusChannelEntry 9 }

apexRfStatusChannelOutputMode OBJECT-TYPE
    SYNTAX INTEGER
        {
         off        (0),
         normal     (1),
         muted      (2),
         suppressed (3),
         cwtest     (4),
         prbs23m    (5),
         prbsUnique (6),
         mpegNull   (7),
         biPhase    (8)
        }
    MAX-ACCESS read-only
    STATUS current
    DESCRIPTION
        "The current output mode of the channel.

         off        - Channel not in use.
         normal     - Normal operation, passing user routed data.
         muted      - Muted, RF Port is muted.
         suppressed - Suppressed, channel test mode or RF Port diagnostic suppression.
         cwtest     - CW test, channel test mode.
         prbs23m    - PRBS-23 with MPEG Sync, channel test mode.
         prbs23     - PRBS-23 no MPEG Sync, channel test mode.
         prbsLong   - Long PRBS, channel test mode.
         prbsUnique - Unique PRBS, channel test mode.
         mpegNull   - MPEG Null packets, channel test mode.
         biPhase    - Bi-phase, channel test mode.
        "
::= { apexRfStatusChannelEntry 10 }


-- ------------------------------------------------------------------------------
--
-- apexRfStatusChannelTable
--

apexRfStatusChannelActiveTable OBJECT-TYPE
    SYNTAX SEQUENCE OF ApexRfStatusChannelActiveEntry
    MAX-ACCESS not-accessible
    STATUS current
    DESCRIPTION
        "QAM Channel Active Status Table.
        "
::= { apexRfStatus 5 }

apexRfStatusChannelActiveEntry OBJECT-TYPE
    SYNTAX ApexRfStatusChannelActiveEntry
    MAX-ACCESS not-accessible
    STATUS current
    DESCRIPTION
        "QAM Channel Active Status Table Entry."
    INDEX { apexRfStatusChannelActiveBladeNum,
            apexRfStatusChannelActiveRfPortNum,
            apexRfStatusChannelActiveChanNum }
::= { apexRfStatusChannelActiveTable 1 }

ApexRfStatusChannelActiveEntry ::= SEQUENCE
    {
     apexRfStatusChannelActiveBladeNum   Integer32,
     apexRfStatusChannelActiveRfPortNum  Integer32,
     apexRfStatusChannelActiveChanNum    Integer32,
     apexRfStatusChannelActive           ActiveTYPE
    }
apexRfStatusChannelActiveBladeNum OBJECT-TYPE
    SYNTAX Integer32(1..8)
    MAX-ACCESS not-accessible
    STATUS current
    DESCRIPTION
        "QAM Blade Number.
        "
::= { apexRfStatusChannelActiveEntry 1 }

apexRfStatusChannelActiveRfPortNum OBJECT-TYPE
    SYNTAX Integer32(1..4)
    MAX-ACCESS not-accessible
    STATUS current
    DESCRIPTION
        "RF Port Number.
        "
::= { apexRfStatusChannelActiveEntry 2 }

apexRfStatusChannelActiveChanNum OBJECT-TYPE
    SYNTAX Integer32(1..64)
    MAX-ACCESS not-accessible
    STATUS current
    DESCRIPTION
        "Channel Number.
        "
::= { apexRfStatusChannelActiveEntry 3 }

apexRfStatusChannelActive OBJECT-TYPE
    SYNTAX ActiveTYPE
    MAX-ACCESS read-only
    STATUS current
    DESCRIPTION
        "Active status.
         
         'active' indicates that mappings can be made to the channel.
         The channel is present (QAM blade present and channel is assignable)
         and a frequency is assigned via apexRfConfigBladeXChannelFrequencyGridSelect.
         
         Notes:
         1) When QAM Blade Redundancy is enabled, backup blade active
            status is set to 'notActive'.
         2) When QAM Blade Redundancy is enabled, always refer to primary
            blade active status even when the primary has failed over
            to the backup blade.
        "
::= { apexRfStatusChannelActiveEntry 4 }


-- ------------------------------------------------------------------------------
--
-- apexRfStatusChannelAvailableTable
--

apexRfStatusChannelAvailableTable OBJECT-TYPE
    SYNTAX SEQUENCE OF ApexRfStatusChannelAvailableEntry
    MAX-ACCESS not-accessible
    STATUS current
    DESCRIPTION
        "QAM Channel Available Status Table.
        "
::= { apexRfStatus 6 }

apexRfStatusChannelAvailableEntry OBJECT-TYPE
    SYNTAX ApexRfStatusChannelAvailableEntry
    MAX-ACCESS not-accessible
    STATUS current
    DESCRIPTION
        "QAM Channel Available Status Table Entry."
    INDEX { apexRfStatusChannelAvailableBladeNum,
            apexRfStatusChannelAvailableRfPortNum,
            apexRfStatusChannelAvailableChanNum }
::= { apexRfStatusChannelAvailableTable 1 }

ApexRfStatusChannelAvailableEntry ::= SEQUENCE
    {
     apexRfStatusChannelAvailableBladeNum   Integer32,
     apexRfStatusChannelAvailableRfPortNum  Integer32,
     apexRfStatusChannelAvailableChanNum    Integer32,
     apexRfStatusChannelAvailable           INTEGER
    }
apexRfStatusChannelAvailableBladeNum OBJECT-TYPE
    SYNTAX Integer32(1..8)
    MAX-ACCESS not-accessible
    STATUS current
    DESCRIPTION
        "QAM Blade Number.
        "
::= { apexRfStatusChannelAvailableEntry 1 }

apexRfStatusChannelAvailableRfPortNum OBJECT-TYPE
    SYNTAX Integer32(1..4)
    MAX-ACCESS not-accessible
    STATUS current
    DESCRIPTION
        "RF Port Number.
        "
::= { apexRfStatusChannelAvailableEntry 2 }

apexRfStatusChannelAvailableChanNum OBJECT-TYPE
    SYNTAX Integer32(1..64)
    MAX-ACCESS not-accessible
    STATUS current
    DESCRIPTION
        "Channel Number.
        "
::= { apexRfStatusChannelAvailableEntry 3 }

apexRfStatusChannelAvailable OBJECT-TYPE
    SYNTAX INTEGER
        {
         notApplicable (0),
         notAvailable  (1),
         available     (2)
        }
    MAX-ACCESS read-only
    STATUS current
    DESCRIPTION
        "Available status for Edge Resource Manager.

         'available' indicates that the channel is active
         (apexRfStatusChannelActive), is not muted, is not in a
         test mode, and there are no errors preventing the channel
         from being used.
         
         Notes:
         1) When QAM Blade Redundancy is enabled, backup blade available
            status is set to 'notAvailable'.
         2) When QAM Blade Redundancy is enabled, always refer to primary
            blade available status even when the primary has failed over
            to the backup blade.
        "
::= { apexRfStatusChannelAvailableEntry 4 }


-- ------------------------------------------------------------------------------
--
-- apexRfErrorRfPortTable
--

apexRfErrorRfPortTable OBJECT-TYPE
    SYNTAX SEQUENCE OF ApexRfErrorRfPortEntry
    MAX-ACCESS not-accessible
    STATUS current
    DESCRIPTION
        "QAM RF Port Error Table.
        "
::= { apexRfStatus 7 }

apexRfErrorRfPortEntry OBJECT-TYPE
    SYNTAX ApexRfErrorRfPortEntry
    MAX-ACCESS not-accessible
    STATUS current
    DESCRIPTION
        "QAM RF Port Error Table Entry."
    INDEX { apexRfErrorRfPortBladeNum,
            apexRfErrorRfPortRfPortNum }
::= { apexRfErrorRfPortTable 1 }

ApexRfErrorRfPortEntry ::= SEQUENCE
    {
     apexRfErrorRfPortBladeNum             Integer32,
     apexRfErrorRfPortRfPortNum            Integer32,
     apexRfErrorRfPortFaultCondition       INTEGER,
     apexRfErrorRfPortChannelFaultSummary  INTEGER,
     apexRfErrorRfPortRfLevelBlade         LowHighErrorTYPE,
     apexRfErrorRfPortRfLevelSwitch        LowHighErrorTYPE,
     apexRfErrorRfPortDataError            ErrorTYPE,
     apexRfErrorRfPortChannelsInError      Integer32,
     apexRfErrorRfPortSwitchError          ErrorTYPE
    }

apexRfErrorRfPortBladeNum OBJECT-TYPE
    SYNTAX Integer32(1..8)
    MAX-ACCESS not-accessible
    STATUS current
    DESCRIPTION
        "QAM Blade Number.
        "
::= { apexRfErrorRfPortEntry 1 }

apexRfErrorRfPortRfPortNum OBJECT-TYPE
    SYNTAX Integer32(1..4)
    MAX-ACCESS not-accessible
    STATUS current
    DESCRIPTION
        "RF Port Number.
        "
::= { apexRfErrorRfPortEntry 2 }

apexRfErrorRfPortFaultCondition OBJECT-TYPE
    SYNTAX INTEGER
        {
         ok(1),
         indeterminate(2),
         warning(3),
         minor(4),
         major(5),
         critical(6)
        }
    MAX-ACCESS read-only
    STATUS current
    DESCRIPTION
        "Current fault condition of the RF port.
         
         Reflected in apexAlarmQamRfPortFault.
         
         Setting of this condition can cause a QAM blade redundancy failover.
        "
::= { apexRfErrorRfPortEntry 3 }

apexRfErrorRfPortChannelFaultSummary OBJECT-TYPE
    SYNTAX INTEGER
        {
         ok(1),
         indeterminate(2),
         warning(3),
         minor(4),
         major(5),
         critical(6)
        }
    MAX-ACCESS read-only
    STATUS current
    DESCRIPTION
        "Current highest fault condition of the QAM channels
         on the RF port.
        "
::= { apexRfErrorRfPortEntry 4 }

apexRfErrorRfPortRfLevelBlade OBJECT-TYPE
    SYNTAX LowHighErrorTYPE
    MAX-ACCESS read-only
    STATUS current
    DESCRIPTION
        "RF level error status of level read from RF Module on the QAM blade.
        "
::= { apexRfErrorRfPortEntry 5 }

apexRfErrorRfPortRfLevelSwitch OBJECT-TYPE
    SYNTAX LowHighErrorTYPE
    MAX-ACCESS read-only
    STATUS current
    DESCRIPTION
        "RF level error status of level read from RF Switch Module.
        "
::= { apexRfErrorRfPortEntry 6 }

apexRfErrorRfPortDataError OBJECT-TYPE
    SYNTAX ErrorTYPE
    MAX-ACCESS read-only
    STATUS current
    DESCRIPTION
        "There is an internal data processing error on the RF Port.
        "
::= { apexRfErrorRfPortEntry 7 }

apexRfErrorRfPortChannelsInError OBJECT-TYPE
    SYNTAX Integer32
    MAX-ACCESS read-only
    STATUS current
    DESCRIPTION
        "Number of channels on this RF Port that are in error.
         Refer to apexRfErrorChannelTable.
        "
::= { apexRfErrorRfPortEntry 8 }

apexRfErrorRfPortSwitchError OBJECT-TYPE
    SYNTAX ErrorTYPE
    MAX-ACCESS read-only
    STATUS current
    DESCRIPTION
        "There is an error on the RF Switch module that prevents
         RF from this QAM Blade RF Port from leaving the APEX.
         For example, if the RF Switch is removed from the APEX.
         
         Note: RF Level errors on the RF Switch are not included here but
               reported in the apexRfErrorRfPortRfLevelSwitch entry.
        "
::= { apexRfErrorRfPortEntry 9 }


-- ------------------------------------------------------------------------------
--
-- apexRfErrorChannelTable
--

apexRfErrorChannelTable OBJECT-TYPE
    SYNTAX SEQUENCE OF ApexRfErrorChannelEntry
    MAX-ACCESS not-accessible
    STATUS current
    DESCRIPTION
        "QAM Channel Error Table.
        "
::= { apexRfStatus 8 }

apexRfErrorChannelEntry OBJECT-TYPE
    SYNTAX ApexRfErrorChannelEntry
    MAX-ACCESS not-accessible
    STATUS current
    DESCRIPTION
        "QAM Channel Error Table Entry."
    INDEX { apexRfErrorChannelBladeNum,
            apexRfErrorChannelRfPortNum,
            apexRfErrorChannelChanNum }
::= { apexRfErrorChannelTable 1 }

ApexRfErrorChannelEntry ::= SEQUENCE
    {
     apexRfErrorChannelBladeNum        Integer32,
     apexRfErrorChannelRfPortNum       Integer32,
     apexRfErrorChannelChanNum         Integer32,
     apexRfErrorChannelFaultCondition  INTEGER,
     apexRfErrorChannelDataError       ErrorTYPE
    }
apexRfErrorChannelBladeNum OBJECT-TYPE
    SYNTAX Integer32(1..8)
    MAX-ACCESS not-accessible
    STATUS current
    DESCRIPTION
        "QAM Blade Number.
        "
::= { apexRfErrorChannelEntry 1 }

apexRfErrorChannelRfPortNum OBJECT-TYPE
    SYNTAX Integer32(1..4)
    MAX-ACCESS not-accessible
    STATUS current
    DESCRIPTION
        "RF Port Number.
        "
::= { apexRfErrorChannelEntry 2 }

apexRfErrorChannelChanNum OBJECT-TYPE
    SYNTAX Integer32(1..64)
    MAX-ACCESS not-accessible
    STATUS current
    DESCRIPTION
        "Channel Number.
        "
::= { apexRfErrorChannelEntry 3 }

apexRfErrorChannelFaultCondition OBJECT-TYPE
    SYNTAX INTEGER
        {
         ok(1),
         indeterminate(2),
         warning(3),
         minor(4),
         major(5),
         critical(6)
        }
    MAX-ACCESS read-only
    STATUS current
    DESCRIPTION
        "Current fault condition of the QAM Channel.
         
         Reflected in apexAlarmQamChannelFault.
         
         Setting of this condition can cause a QAM blade redundancy failover.
        "
::= { apexRfErrorChannelEntry 4 }

apexRfErrorChannelDataError OBJECT-TYPE
    SYNTAX ErrorTYPE
    MAX-ACCESS read-only
    STATUS current
    DESCRIPTION
        "Indication of MPEG data activity on the interface for this QAM channel.
         This includes MPEG null packets.
         
         *** This entry is not supported. ***
        "
::= { apexRfErrorChannelEntry 5 }


-- ------------------------------------------------------------------------------
--
-- apexRfStatusRfPortLevelTable
--

apexRfStatusRfPortLevelTable OBJECT-TYPE
    SYNTAX SEQUENCE OF ApexRfStatusRfPortLevelEntry
    MAX-ACCESS not-accessible
    STATUS current
    DESCRIPTION
        "QAM RF Port RF Level Readings Status Table.
        "
::= { apexRfStatus 9 }

apexRfStatusRfPortLevelEntry OBJECT-TYPE
    SYNTAX ApexRfStatusRfPortLevelEntry
    MAX-ACCESS not-accessible
    STATUS current
    DESCRIPTION
        "QAM RF Port Status Table Entry."
    INDEX { apexRfStatusRfPortLevelBladeNum,
            apexRfStatusRfPortLevelRfNum }
::= { apexRfStatusRfPortLevelTable 1 }

ApexRfStatusRfPortLevelEntry ::= SEQUENCE
    {
     apexRfStatusRfPortLevelBladeNum    Integer32,
     apexRfStatusRfPortLevelRfNum       Integer32,
     apexRfStatusRfPortLevelReadBlade   Integer32,
     apexRfStatusRfPortLevelReadSwitch  Integer32
    }

apexRfStatusRfPortLevelBladeNum OBJECT-TYPE
    SYNTAX Integer32(1..8)
    MAX-ACCESS not-accessible
    STATUS current
    DESCRIPTION
        "QAM Blade Number.
        "
::= { apexRfStatusRfPortLevelEntry 1 }

apexRfStatusRfPortLevelRfNum OBJECT-TYPE
    SYNTAX Integer32(1..4)
    MAX-ACCESS not-accessible
    STATUS current
    DESCRIPTION
        "RF Port Number.
        "
::= { apexRfStatusRfPortLevelEntry 2 }

apexRfStatusRfPortLevelReadBlade OBJECT-TYPE
    SYNTAX Integer32
    MAX-ACCESS read-only
    STATUS current
    DESCRIPTION
        "Total RF output level read from QAM blade RF module.
         Value is dBmV in 0.01 dB steps.
        "
::= { apexRfStatusRfPortLevelEntry 3 }

apexRfStatusRfPortLevelReadSwitch OBJECT-TYPE
    SYNTAX Integer32
    MAX-ACCESS read-only
    STATUS current
    DESCRIPTION
        "Total RF output level read from RF switch module.
         Value is dBmV in 0.01 dB steps.
        "
::= { apexRfStatusRfPortLevelEntry 4 }


-- ------------------------------------------------------------------------------
--
-- apexRfStatusRfCountsTable
--

apexRfStatusRfCountsTable OBJECT-TYPE
    SYNTAX SEQUENCE OF ApexRfStatusRfCountsEntry
    MAX-ACCESS not-accessible
    STATUS current
    DESCRIPTION
        "QAM RF Port RF Counts Table.
         
         Contains counts of various status on an RF
         Port basis.
        "
::= { apexRfStatus 10 }

apexRfStatusRfCountsEntry OBJECT-TYPE
    SYNTAX ApexRfStatusRfCountsEntry
    MAX-ACCESS not-accessible
    STATUS current
    DESCRIPTION
        "QAM RF Port Counts Table Entry."
    INDEX { apexRfStatusRfCountsBladeNum,
            apexRfStatusRfCountsRfNum }
::= { apexRfStatusRfCountsTable 1 }

ApexRfStatusRfCountsEntry ::= SEQUENCE
    {
     apexRfStatusRfCountsBladeNum           Integer32,
     apexRfStatusRfCountsRfNum              Integer32,
     apexRfStatusRfCountsChannelsAssignable Integer32,
     apexRfStatusRfCountsChannelsAssigned   Integer32,
     apexRfStatusRfCountsChannelsActive     Integer32,
     apexRfStatusRfCountsChannelsMuted      Integer32,
     apexRfStatusRfCountsChannelsTestMode   Integer32,
     apexRfStatusRfCountsChannelsAvailable  Integer32
    }

apexRfStatusRfCountsBladeNum OBJECT-TYPE
    SYNTAX Integer32(1..8)
    MAX-ACCESS not-accessible
    STATUS current
    DESCRIPTION
        "QAM Blade Number.
        "
::= { apexRfStatusRfCountsEntry 1 }

apexRfStatusRfCountsRfNum OBJECT-TYPE
    SYNTAX Integer32(1..4)
    MAX-ACCESS not-accessible
    STATUS current
    DESCRIPTION
        "RF Port Number.
        "
::= { apexRfStatusRfCountsEntry 2 }

apexRfStatusRfCountsChannelsAssignable OBJECT-TYPE
    SYNTAX Integer32
    MAX-ACCESS read-only
    STATUS current
    DESCRIPTION
        "Number of channels that can be assigned a frequency.
         
         This count is based on and/or limited by the following:
           - QAM blade present/available.
           - The number of channels the hardware can support.
           - Any applied chassis QAM channel entitlements.
           - Maximum channels supported by FW release.
           - Maximum channels supported by QAM Transmission Mode.
        "
::= { apexRfStatusRfCountsEntry 3 }

apexRfStatusRfCountsChannelsAssigned OBJECT-TYPE
    SYNTAX Integer32
    MAX-ACCESS read-only
    STATUS current
    DESCRIPTION
        "Number of channels that have been assigned a frequency.
         
         Count of channels assigned a frequency via apexRfConfigBladeXChannelFrequencyGridSelect.
        "
::= { apexRfStatusRfCountsEntry 4 }

apexRfStatusRfCountsChannelsActive OBJECT-TYPE
    SYNTAX Integer32
    MAX-ACCESS read-only
    STATUS current
    DESCRIPTION
        "Number of channels that are active.
         
         Refer to apexRfStatusChannelActive for additional details.
        "
::= { apexRfStatusRfCountsEntry 5 }

apexRfStatusRfCountsChannelsMuted OBJECT-TYPE
    SYNTAX Integer32
    MAX-ACCESS read-only
    STATUS current
    DESCRIPTION
        "Number of active channels that are configured as muted
         via apexRfConfigBladeXChannelMute.
         
         This count does not reflect RF Port mute setting
         (apexRfConfigBladeXRfPortMute).
        "
::= { apexRfStatusRfCountsEntry 6 }

apexRfStatusRfCountsChannelsTestMode OBJECT-TYPE
    SYNTAX Integer32
    MAX-ACCESS read-only
    STATUS current
    DESCRIPTION
        "Number of active channels that are configured in test mode
         via apexRfConfigBladeXChannelTestMode.
         
         This count does not reflect RF Port Diagnostic Suppression setting
         (apexRfConfigBladeXRfPortDiagSuppressMode).
        "
::= { apexRfStatusRfCountsEntry 7 }

apexRfStatusRfCountsChannelsAvailable OBJECT-TYPE
    SYNTAX Integer32
    MAX-ACCESS read-only
    STATUS current
    DESCRIPTION
        "Number of channels that are available.
         
         Refer to apexRfStatusChannelAvailable for additional details.
        "
::= { apexRfStatusRfCountsEntry 8 }


-- ------------------------------------------------------------------------------
--
-- apexSessionControl
--
-- apexSessionControlConfig
--
-- apexSessionControlConfigGeneral
--

apexSesContConfProtocol OBJECT-TYPE
    SYNTAX INTEGER
        {
         none      (0),
         rtsp-r6d6 (1),
         mha-ermi  (2)
        }
    MAX-ACCESS read-write
    STATUS current
    DESCRIPTION
        "The communication protocol for output streams in Session Control operating
         mode. This determines the type of protocol the APEX will use to communicate
         with an Edge Resource Manager/Switch Digital Video Manager. This parameter
         cannot be changed when there are any active Session Control mappings. All
         Session Control mappings must be removed prior to changing this protocol.

         Once written, a save must be performed via the apexSaveConfig
         parameter.

         @Config(config=yes, reboot=no)
         @Save(apexSaveConfig, value=2)
         @File(sdvcfg.ini, type='ini')
        "
::= { apexSessionControlConfigGeneral 1 }

apexSesContConfTableApplyChange OBJECT-TYPE
    SYNTAX ApplyDataToDeviceTYPE
    MAX-ACCESS read-write
    STATUS current
    DESCRIPTION
        "The Apply for the apexSesContConfTable. This parameter
         MUST be set to 'apply' in order for any of the data in the
         apexSesContConfTable to take effect.  This parameter
         MUST be set LAST after all other data in the apexSesContConfTable
         has been configured.

         @Config(config=no, reboot=no)
        "
::= { apexSessionControlConfigGeneral 2 }

apexSesContConfInputPreEncryptCheck OBJECT-TYPE
    SYNTAX EnableDisableTYPE
    MAX-ACCESS read-write
    STATUS current
    DESCRIPTION
        "Session Control Pre-Encryption Checking.

         Indicates if the APEX is to check if the input service is pre-encrypted or
         clear. Pre-encrypted is determined by examining the input PMT for a CA ECM
         descriptor (any CA ECM descriptor). If pre-encrypted, setting this flag will
         cause the APEX to pass through ECM PID for this service. For input services
         that have a GI CA ECM descriptor, the APEX will also pass through the PIT
         message (extract and re-insert the PIT). The output PMT for pre-encrypted
         services will contain a CA ECM descriptor (referencing the ECM
         PID). When PID Remapping is enabled, pre-encryption for a service is
         only valid when the input ECM PID is on a different PID than the
         associated PMT PID. If this flag is set to pre-encryption and the
         input service is not pre-encrypted, then the setting of this flag has
         no affect on the output service.

         Once written, the change to this parameter will take immediate effect.
         However, in order for the change to persist through subsequent reboots
         or power cycles, the change must be saved via the apexSaveConfig parameter.

         @Config(config=yes, reboot=no)
         @Save(apexSaveConfig, value=2)
         @File(sdvcfg.ini, type='ini')
        "
::= { apexSessionControlConfigGeneral 3 }

apexSesContConfFollowDtcp OBJECT-TYPE
    SYNTAX EnableDisableTYPE
    MAX-ACCESS read-write
    STATUS current
    DESCRIPTION
        "Determines how the copy protection settings (CCI, APS, and CIT) within 
         the PRK will be set.  All outputs in Session Control (SDV) mode will use  
         this setting for following input DTCP. 
           Disabled - Use ERM Configuration settings if encryption blob provided.
                      Use CTE settings when in CTE encryption mode and no ERM 
                      encryption blob provided.

           Enabled - Follow input DTCP
         
         Once written, the change to this parameter will take immediate effect.
         However, in order for the change to persist through subsequent reboots
         or power cycles, the change must be saved via the apexSaveConfig parameter.

         @Config(config=yes, reboot=no)
         @Save(apexSaveConfig, value=2)
         @File(sdvcfg.ini, type='ini')
        "
::= { apexSessionControlConfigGeneral 4 }

apexSesContConfReportUdpMappings OBJECT-TYPE
    SYNTAX EnableDisableTYPE
    MAX-ACCESS read-write
    STATUS current
    DESCRIPTION
        "Determines if the APEX will report UDP Port mappings via the RTSP
         D6 interface. UDP Port Mappings are only reported for an output channel
         that has been configured in UDP Port Mapping mode. 
         
           Disabled - UDP Port Mappings will not be reported for each QAM channel

           Enabled - UDP Port Mappings will be reported for each QAM channel. 
           
         To Enable this field, ALL outputs configured in UDP Port Mapping mode must
         have unique TS IDs assigned. The QAM channel names reported are derived from 
         the TS IDs and each must be unique. Therefore all outputs in RTSP mode and UDP 
         Port Mapping must have unique TS IDs assigned prior to enabling this field.
         
         Additionally, there cannot be any enabled UDP Port Mappings in the system and the
         UDP Port Mapping algorithm must be set to 10/6. 
         
         Once written, the change to this parameter will take immediate effect.
         However, in order for the change to persist through subsequent reboots
         or power cycles, the change must be saved via the apexSaveConfig parameter.

         @Config(config=yes, reboot=no)
         @Save(apexSaveConfig, value=2)
         @File(sdvcfg.ini, type='ini')
        "
::= { apexSessionControlConfigGeneral 5 }


-- ------------------------------------------------------------------------------
--
-- apexSesContBlade1ConfTable
--

apexSesContBlade1ConfTable OBJECT-TYPE
    SYNTAX SEQUENCE OF ApexSesContBlade1ConfEntry
    MAX-ACCESS not-accessible
    STATUS current
    DESCRIPTION
        "This is a table of Session Control configuration parameters for
         each output transport stream. This table defines the primary
         and secondary Gigabit Ethernet interfaces for each output stream
         in Session Control operating mode. The primary and secondary
         interfaces cannot be changed for an output stream when there are
         active Session Control mappings. All Session Control mappings on
         an output stream must be removed prior to changing the primary or
         secondary interface settings.

         Once written, the change to this table will only take immediate
         effect after apexSesContConfTableApplyChange is set to 'apply'.  In
         order for the change to persist through subsequent reboots or power
         cycles, the change must be saved via the apexSaveConfig parameter.

         @Config(config=yes, reboot=no)
         @Commit(param=apexSesContConfTableApplyChange, value=2)
         @Save(apexSaveConfig, value=2)
         @File(sdvcfg.ini, type='ini')
        "
::= { apexSessionControlConfig 2 }

apexSesContBlade1ConfEntry OBJECT-TYPE
    SYNTAX ApexSesContBlade1ConfEntry
    MAX-ACCESS not-accessible
    STATUS current
    DESCRIPTION
        "Session Control Configuration Table Entry."
    INDEX { apexSesContBlade1ConfOutputTsNum }
::= { apexSesContBlade1ConfTable 1 }

ApexSesContBlade1ConfEntry ::= SEQUENCE
    {
     apexSesContBlade1ConfOutputTsNum             Integer32,
     apexSesContBlade1ConfGbePrimaryInterface     Integer32,
     apexSesContBlade1ConfGbeSecondaryInterface   Integer32,
     apexSesContBlade1ConfQamDeviceIndex          Integer32,
     apexSesContBlade1ConfCmdOutputPort           Integer32
    }

apexSesContBlade1ConfOutputTsNum OBJECT-TYPE
    SYNTAX Integer32(1..256)
    MAX-ACCESS not-accessible
    STATUS current
    DESCRIPTION
        "Output transport stream number (index)."
::= { apexSesContBlade1ConfEntry 1 }

apexSesContBlade1ConfGbePrimaryInterface OBJECT-TYPE
    SYNTAX Integer32(0..12)
    MAX-ACCESS read-write
    STATUS current
    DESCRIPTION
        "The primary Gbe interface for Session Control.  Zero indicates not available.
         This parameter cannot be changed for any output stream if there is at
         least 1 active session control mapping.

         Not configurable for RTSP.
        "
::= { apexSesContBlade1ConfEntry 2 }

apexSesContBlade1ConfGbeSecondaryInterface OBJECT-TYPE
    SYNTAX Integer32(0..12)
    MAX-ACCESS read-write
    STATUS current
    DESCRIPTION
        "The secondary Gbe interface for RPC SDV.  Zero indicates not available.
         This parameter cannot be changed for any output stream if there is at
         least 1 active session control mapping.

         Not configurable for RTSP.
        "
::= { apexSesContBlade1ConfEntry 3 }

apexSesContBlade1ConfQamDeviceIndex OBJECT-TYPE
    SYNTAX Integer32(0..64)
    MAX-ACCESS read-write
    STATUS current
    DESCRIPTION
        "The index of the Generic QAM Device associated with this output TS. 
         Index of 0 indicates that this output is not associated with any specific
         device. RPC commands will be received on either ENET 1 or 2 interfaces
         using the Chassis IP addresses.
         Index 1 - 64 indicates RPC commands for this output will ONLY be received
         on that specific Ethernet address assigned to that QAM Device index. 
         
         Not configurable for RTSP.
        "
::= { apexSesContBlade1ConfEntry 4 }

apexSesContBlade1ConfCmdOutputPort OBJECT-TYPE
    SYNTAX Integer32(1..2048)
    MAX-ACCESS read-write
    STATUS current
    DESCRIPTION
        "The RPC command output port number associated with this output TS. This is
         a relative 1 command output port number. 0 is not valid and will result in
         a calculated default value for the command port to be used. 
         The command output port is the value in each received RPC command. Each  
         command output port is assigned to a specific QAM blade and output TS. 
         
         Not configurable for RTSP.
        "
::= { apexSesContBlade1ConfEntry 5 }


-- ------------------------------------------------------------------------------
--
-- apexSesContBlade2ConfTable
--

apexSesContBlade2ConfTable OBJECT-TYPE
    SYNTAX SEQUENCE OF ApexSesContBlade2ConfEntry
    MAX-ACCESS not-accessible
    STATUS current
    DESCRIPTION
        "This is a table of Session Control configuration parameters for
         each output transport stream. This table defines the primary
         and secondary Gigabit Ethernet interfaces for each output stream
         in Session Control operating mode. The primary and secondary
         interfaces cannot be changed for an output stream when there are
         active Session Control mappings. All Session Control mappings on
         an output stream must be removed prior to changing the primary or
         secondary interface settings.

         Once written, the change to this table will only take immediate
         effect after apexSesContConfTableApplyChange is set to 'apply'.  In
         order for the change to persist through subsequent reboots or power
         cycles, the change must be saved via the apexSaveConfig parameter.

         @Config(config=yes, reboot=no)
         @Commit(param=apexSesContConfTableApplyChange, value=2)
         @Save(apexSaveConfig, value=2)
         @File(sdvcfg.ini, type='ini')
        "
::= { apexSessionControlConfig 3 }

apexSesContBlade2ConfEntry OBJECT-TYPE
    SYNTAX ApexSesContBlade2ConfEntry
    MAX-ACCESS not-accessible
    STATUS current
    DESCRIPTION
        "Session Control Configuration Table Entry."
    INDEX { apexSesContBlade2ConfOutputTsNum }
::= { apexSesContBlade2ConfTable 1 }

ApexSesContBlade2ConfEntry ::= SEQUENCE
    {
     apexSesContBlade2ConfOutputTsNum             Integer32,
     apexSesContBlade2ConfGbePrimaryInterface     Integer32,
     apexSesContBlade2ConfGbeSecondaryInterface   Integer32,
     apexSesContBlade2ConfQamDeviceIndex          Integer32,
     apexSesContBlade2ConfCmdOutputPort           Integer32
    }

apexSesContBlade2ConfOutputTsNum OBJECT-TYPE
    SYNTAX Integer32(1..256)
    MAX-ACCESS not-accessible
    STATUS current
    DESCRIPTION
        "Output transport stream number (index)."
::= { apexSesContBlade2ConfEntry 1 }

apexSesContBlade2ConfGbePrimaryInterface OBJECT-TYPE
    SYNTAX Integer32(0..12)
    MAX-ACCESS read-write
    STATUS current
    DESCRIPTION
        "The primary Gbe interface for Session Control.  Zero indicates not available.
         This parameter cannot be changed for any output stream if there is at
         least 1 active session control mapping.

         Not configurable for RTSP.
        "
::= { apexSesContBlade2ConfEntry 2 }

apexSesContBlade2ConfGbeSecondaryInterface OBJECT-TYPE
    SYNTAX Integer32(0..12)
    MAX-ACCESS read-write
    STATUS current
    DESCRIPTION
        "The secondary Gbe interface for RPC SDV.  Zero indicates not available.
         This parameter cannot be changed for any output stream if there is at
         least 1 active session control mapping.

         Not configurable for RTSP.
        "
::= { apexSesContBlade2ConfEntry 3 }

apexSesContBlade2ConfQamDeviceIndex OBJECT-TYPE
    SYNTAX Integer32(0..64)
    MAX-ACCESS read-write
    STATUS current
    DESCRIPTION
        "The index of the Generic QAM Device associated with this output TS. 
         Index of 0 indicates that this output is not associated with any specific
         device. RPC commands will be received on either ENET 1 or 2 interfaces
         using the Chassis IP addresses.
         Index 1 - 64 indicates RPC commands for this output will ONLY be received
         on that specific Ethernet address assigned to that QAM Device index. 
         
         Not configurable for RTSP.
        "
::= { apexSesContBlade2ConfEntry 4 }

apexSesContBlade2ConfCmdOutputPort OBJECT-TYPE
    SYNTAX Integer32(1..2048)
    MAX-ACCESS read-write
    STATUS current
    DESCRIPTION
        "The RPC command output port number associated with this output TS. This is
         a relative 1 command output port number. 0 is not valid and will result in
         a calculated default value for the command port to be used. 
         The command output port is the value in each received RPC command. Each  
         command output port is assigned to a specific QAM blade and output TS. 
         
         Not configurable for RTSP.
        "
::= { apexSesContBlade2ConfEntry 5 }


-- ------------------------------------------------------------------------------
--
-- apexSesContBlade3ConfTable
--

apexSesContBlade3ConfTable OBJECT-TYPE
    SYNTAX SEQUENCE OF ApexSesContBlade3ConfEntry
    MAX-ACCESS not-accessible
    STATUS current
    DESCRIPTION
        "This is a table of Session Control configuration parameters for
         each output transport stream. This table defines the primary
         and secondary Gigabit Ethernet interfaces for each output stream
         in Session Control operating mode. The primary and secondary
         interfaces cannot be changed for an output stream when there are
         active Session Control mappings. All Session Control mappings on
         an output stream must be removed prior to changing the primary or
         secondary interface settings.

         Once written, the change to this table will only take immediate
         effect after apexSesContConfTableApplyChange is set to 'apply'.  In
         order for the change to persist through subsequent reboots or power
         cycles, the change must be saved via the apexSaveConfig parameter.

         @Config(config=yes, reboot=no)
         @Commit(param=apexSesContConfTableApplyChange, value=2)
         @Save(apexSaveConfig, value=2)
         @File(sdvcfg.ini, type='ini')
        "
::= { apexSessionControlConfig 4 }

apexSesContBlade3ConfEntry OBJECT-TYPE
    SYNTAX ApexSesContBlade3ConfEntry
    MAX-ACCESS not-accessible
    STATUS current
    DESCRIPTION
        "Session Control Configuration Table Entry."
    INDEX { apexSesContBlade3ConfOutputTsNum }
::= { apexSesContBlade3ConfTable 1 }

ApexSesContBlade3ConfEntry ::= SEQUENCE
    {
     apexSesContBlade3ConfOutputTsNum             Integer32,
     apexSesContBlade3ConfGbePrimaryInterface     Integer32,
     apexSesContBlade3ConfGbeSecondaryInterface   Integer32,
     apexSesContBlade3ConfQamDeviceIndex          Integer32,
     apexSesContBlade3ConfCmdOutputPort           Integer32
    }

apexSesContBlade3ConfOutputTsNum OBJECT-TYPE
    SYNTAX Integer32(1..256)
    MAX-ACCESS not-accessible
    STATUS current
    DESCRIPTION
        "Output transport stream number (index)."
::= { apexSesContBlade3ConfEntry 1 }

apexSesContBlade3ConfGbePrimaryInterface OBJECT-TYPE
    SYNTAX Integer32(0..12)
    MAX-ACCESS read-write
    STATUS current
    DESCRIPTION
        "The primary Gbe interface for Session Control.  Zero indicates not available.
         This parameter cannot be changed for any output stream if there is at
         least 1 active session control mapping.

         Not configurable for RTSP.
        "
::= { apexSesContBlade3ConfEntry 2 }

apexSesContBlade3ConfGbeSecondaryInterface OBJECT-TYPE
    SYNTAX Integer32(0..12)
    MAX-ACCESS read-write
    STATUS current
    DESCRIPTION
        "The secondary Gbe interface for RPC SDV.  Zero indicates not available.
         This parameter cannot be changed for any output stream if there is at
         least 1 active session control mapping.

         Not configurable for RTSP.
        "
::= { apexSesContBlade3ConfEntry 3 }

apexSesContBlade3ConfQamDeviceIndex OBJECT-TYPE
    SYNTAX Integer32(0..64)
    MAX-ACCESS read-write
    STATUS current
    DESCRIPTION
        "The index of the Generic QAM Device associated with this output TS. 
         Index of 0 indicates that this output is not associated with any specific
         device. RPC commands will be received on either ENET 1 or 2 interfaces
         using the Chassis IP addresses.
         Index 1 - 64 indicates RPC commands for this output will ONLY be received
         on that specific Ethernet address assigned to that QAM Device index. 
         
         Not configurable for RTSP.
        "
::= { apexSesContBlade3ConfEntry 4 }

apexSesContBlade3ConfCmdOutputPort OBJECT-TYPE
    SYNTAX Integer32(1..2048)
    MAX-ACCESS read-write
    STATUS current
    DESCRIPTION
        "The RPC command output port number associated with this output TS. This is
         a relative 1 command output port number. 0 is not valid and will result in
         a calculated default value for the command port to be used. 
         The command output port is the value in each received RPC command. Each  
         command output port is assigned to a specific QAM blade and output TS. 
         
         Not configurable for RTSP.
        "
::= { apexSesContBlade3ConfEntry 5 }


-- ------------------------------------------------------------------------------
--
-- apexSesContBlade4ConfTable
--

apexSesContBlade4ConfTable OBJECT-TYPE
    SYNTAX SEQUENCE OF ApexSesContBlade4ConfEntry
    MAX-ACCESS not-accessible
    STATUS current
    DESCRIPTION
        "This is a table of Session Control configuration parameters for
         each output transport stream. This table defines the primary
         and secondary Gigabit Ethernet interfaces for each output stream
         in Session Control operating mode. The primary and secondary
         interfaces cannot be changed for an output stream when there are
         active Session Control mappings. All Session Control mappings on
         an output stream must be removed prior to changing the primary or
         secondary interface settings.

         Once written, the change to this table will only take immediate
         effect after apexSesContConfTableApplyChange is set to 'apply'.  In
         order for the change to persist through subsequent reboots or power
         cycles, the change must be saved via the apexSaveConfig parameter.

         @Config(config=yes, reboot=no)
         @Commit(param=apexSesContConfTableApplyChange, value=2)
         @Save(apexSaveConfig, value=2)
         @File(sdvcfg.ini, type='ini')
        "
::= { apexSessionControlConfig 5 }

apexSesContBlade4ConfEntry OBJECT-TYPE
    SYNTAX ApexSesContBlade4ConfEntry
    MAX-ACCESS not-accessible
    STATUS current
    DESCRIPTION
        "Session Control Configuration Table Entry."
    INDEX { apexSesContBlade4ConfOutputTsNum }
::= { apexSesContBlade4ConfTable 1 }

ApexSesContBlade4ConfEntry ::= SEQUENCE
    {
     apexSesContBlade4ConfOutputTsNum             Integer32,
     apexSesContBlade4ConfGbePrimaryInterface     Integer32,
     apexSesContBlade4ConfGbeSecondaryInterface   Integer32,
     apexSesContBlade4ConfQamDeviceIndex          Integer32,
     apexSesContBlade4ConfCmdOutputPort           Integer32
    }

apexSesContBlade4ConfOutputTsNum OBJECT-TYPE
    SYNTAX Integer32(1..256)
    MAX-ACCESS not-accessible
    STATUS current
    DESCRIPTION
        "Output transport stream number (index)."
::= { apexSesContBlade4ConfEntry 1 }

apexSesContBlade4ConfGbePrimaryInterface OBJECT-TYPE
    SYNTAX Integer32(0..12)
    MAX-ACCESS read-write
    STATUS current
    DESCRIPTION
        "The primary Gbe interface for Session Control.  Zero indicates not available.
         This parameter cannot be changed for any output stream if there is at
         least 1 active session control mapping.

         Not configurable for RTSP.
        "
::= { apexSesContBlade4ConfEntry 2 }

apexSesContBlade4ConfGbeSecondaryInterface OBJECT-TYPE
    SYNTAX Integer32(0..12)
    MAX-ACCESS read-write
    STATUS current
    DESCRIPTION
        "The secondary Gbe interface for RPC SDV.  Zero indicates not available.
         This parameter cannot be changed for any output stream if there is at
         least 1 active session control mapping.

         Not configurable for RTSP.
        "
::= { apexSesContBlade4ConfEntry 3 }

apexSesContBlade4ConfQamDeviceIndex OBJECT-TYPE
    SYNTAX Integer32(0..64)
    MAX-ACCESS read-write
    STATUS current
    DESCRIPTION
        "The index of the Generic QAM Device associated with this output TS. 
         Index of 0 indicates that this output is not associated with any specific
         device. RPC commands will be received on either ENET 1 or 2 interfaces
         using the Chassis IP addresses.
         Index 1 - 64 indicates RPC commands for this output will ONLY be received
         on that specific Ethernet address assigned to that QAM Device index. 
         
         Not configurable for RTSP.
        "
::= { apexSesContBlade4ConfEntry 4 }

apexSesContBlade4ConfCmdOutputPort OBJECT-TYPE
    SYNTAX Integer32(1..2048)
    MAX-ACCESS read-write
    STATUS current
    DESCRIPTION
        "The RPC command output port number associated with this output TS. This is
         a relative 1 command output port number. 0 is not valid and will result in
         a calculated default value for the command port to be used. 
         The command output port is the value in each received RPC command. Each  
         command output port is assigned to a specific QAM blade and output TS. 
         
         Not configurable for RTSP.
        "
::= { apexSesContBlade4ConfEntry 5 }


-- ------------------------------------------------------------------------------
--
-- apexSesContBlade5ConfTable
--

apexSesContBlade5ConfTable OBJECT-TYPE
    SYNTAX SEQUENCE OF ApexSesContBlade5ConfEntry
    MAX-ACCESS not-accessible
    STATUS current
    DESCRIPTION
        "This is a table of Session Control configuration parameters for
         each output transport stream. This table defines the primary
         and secondary Gigabit Ethernet interfaces for each output stream
         in Session Control operating mode. The primary and secondary
         interfaces cannot be changed for an output stream when there are
         active Session Control mappings. All Session Control mappings on
         an output stream must be removed prior to changing the primary or
         secondary interface settings.

         Once written, the change to this table will only take immediate
         effect after apexSesContConfTableApplyChange is set to 'apply'.  In
         order for the change to persist through subsequent reboots or power
         cycles, the change must be saved via the apexSaveConfig parameter.

         @Config(config=yes, reboot=no)
         @Commit(param=apexSesContConfTableApplyChange, value=2)
         @Save(apexSaveConfig, value=2)
         @File(sdvcfg.ini, type='ini')
        "
::= { apexSessionControlConfig 6 }

apexSesContBlade5ConfEntry OBJECT-TYPE
    SYNTAX ApexSesContBlade5ConfEntry
    MAX-ACCESS not-accessible
    STATUS current
    DESCRIPTION
        "Session Control Configuration Table Entry."
    INDEX { apexSesContBlade5ConfOutputTsNum }
::= { apexSesContBlade5ConfTable 1 }

ApexSesContBlade5ConfEntry ::= SEQUENCE
    {
     apexSesContBlade5ConfOutputTsNum             Integer32,
     apexSesContBlade5ConfGbePrimaryInterface     Integer32,
     apexSesContBlade5ConfGbeSecondaryInterface   Integer32,
     apexSesContBlade5ConfQamDeviceIndex          Integer32,
     apexSesContBlade5ConfCmdOutputPort           Integer32
    }

apexSesContBlade5ConfOutputTsNum OBJECT-TYPE
    SYNTAX Integer32(1..256)
    MAX-ACCESS not-accessible
    STATUS current
    DESCRIPTION
        "Output transport stream number (index)."
::= { apexSesContBlade5ConfEntry 1 }

apexSesContBlade5ConfGbePrimaryInterface OBJECT-TYPE
    SYNTAX Integer32(0..12)
    MAX-ACCESS read-write
    STATUS current
    DESCRIPTION
        "The primary Gbe interface for Session Control.  Zero indicates not available.
         This parameter cannot be changed for any output stream if there is at
         least 1 active session control mapping.

         Not configurable for RTSP.
        "
::= { apexSesContBlade5ConfEntry 2 }

apexSesContBlade5ConfGbeSecondaryInterface OBJECT-TYPE
    SYNTAX Integer32(0..12)
    MAX-ACCESS read-write
    STATUS current
    DESCRIPTION
        "The secondary Gbe interface for RPC SDV.  Zero indicates not available.
         This parameter cannot be changed for any output stream if there is at
         least 1 active session control mapping.

         Not configurable for RTSP.
        "
::= { apexSesContBlade5ConfEntry 3 }

apexSesContBlade5ConfQamDeviceIndex OBJECT-TYPE
    SYNTAX Integer32(0..64)
    MAX-ACCESS read-write
    STATUS current
    DESCRIPTION
        "The index of the Generic QAM Device associated with this output TS. 
         Index of 0 indicates that this output is not associated with any specific
         device. RPC commands will be received on either ENET 1 or 2 interfaces
         using the Chassis IP addresses.
         Index 1 - 64 indicates RPC commands for this output will ONLY be received
         on that specific Ethernet address assigned to that QAM Device index. 
         
         Not configurable for RTSP.
        "
::= { apexSesContBlade5ConfEntry 4 }

apexSesContBlade5ConfCmdOutputPort OBJECT-TYPE
    SYNTAX Integer32(1..2048)
    MAX-ACCESS read-write
    STATUS current
    DESCRIPTION
        "The RPC command output port number associated with this output TS. This is
         a relative 1 command output port number. 0 is not valid and will result in
         a calculated default value for the command port to be used. 
         The command output port is the value in each received RPC command. Each  
         command output port is assigned to a specific QAM blade and output TS. 
         
         Not configurable for RTSP.
        "
::= { apexSesContBlade5ConfEntry 5 }


-- ------------------------------------------------------------------------------
--
-- apexSesContBlade6ConfTable
--

apexSesContBlade6ConfTable OBJECT-TYPE
    SYNTAX SEQUENCE OF ApexSesContBlade6ConfEntry
    MAX-ACCESS not-accessible
    STATUS current
    DESCRIPTION
        "This is a table of Session Control configuration parameters for
         each output transport stream. This table defines the primary
         and secondary Gigabit Ethernet interfaces for each output stream
         in Session Control operating mode. The primary and secondary
         interfaces cannot be changed for an output stream when there are
         active Session Control mappings. All Session Control mappings on
         an output stream must be removed prior to changing the primary or
         secondary interface settings.

         Once written, the change to this table will only take immediate
         effect after apexSesContConfTableApplyChange is set to 'apply'.  In
         order for the change to persist through subsequent reboots or power
         cycles, the change must be saved via the apexSaveConfig parameter.

         @Config(config=yes, reboot=no)
         @Commit(param=apexSesContConfTableApplyChange, value=2)
         @Save(apexSaveConfig, value=2)
         @File(sdvcfg.ini, type='ini')
        "
::= { apexSessionControlConfig 7 }

apexSesContBlade6ConfEntry OBJECT-TYPE
    SYNTAX ApexSesContBlade6ConfEntry
    MAX-ACCESS not-accessible
    STATUS current
    DESCRIPTION
        "Session Control Configuration Table Entry."
    INDEX { apexSesContBlade6ConfOutputTsNum }
::= { apexSesContBlade6ConfTable 1 }

ApexSesContBlade6ConfEntry ::= SEQUENCE
    {
     apexSesContBlade6ConfOutputTsNum             Integer32,
     apexSesContBlade6ConfGbePrimaryInterface     Integer32,
     apexSesContBlade6ConfGbeSecondaryInterface   Integer32,
     apexSesContBlade6ConfQamDeviceIndex          Integer32,
     apexSesContBlade6ConfCmdOutputPort           Integer32
    }

apexSesContBlade6ConfOutputTsNum OBJECT-TYPE
    SYNTAX Integer32(1..256)
    MAX-ACCESS not-accessible
    STATUS current
    DESCRIPTION
        "Output transport stream number (index)."
::= { apexSesContBlade6ConfEntry 1 }

apexSesContBlade6ConfGbePrimaryInterface OBJECT-TYPE
    SYNTAX Integer32(0..12)
    MAX-ACCESS read-write
    STATUS current
    DESCRIPTION
        "The primary Gbe interface for Session Control.  Zero indicates not available.
         This parameter cannot be changed for any output stream if there is at
         least 1 active session control mapping.

         Not configurable for RTSP.
        "
::= { apexSesContBlade6ConfEntry 2 }

apexSesContBlade6ConfGbeSecondaryInterface OBJECT-TYPE
    SYNTAX Integer32(0..12)
    MAX-ACCESS read-write
    STATUS current
    DESCRIPTION
        "The secondary Gbe interface for RPC SDV.  Zero indicates not available.
         This parameter cannot be changed for any output stream if there is at
         least 1 active session control mapping.

         Not configurable for RTSP.
        "
::= { apexSesContBlade6ConfEntry 3 }

apexSesContBlade6ConfQamDeviceIndex OBJECT-TYPE
    SYNTAX Integer32(0..64)
    MAX-ACCESS read-write
    STATUS current
    DESCRIPTION
        "The index of the Generic QAM Device associated with this output TS. 
         Index of 0 indicates that this output is not associated with any specific
         device. RPC commands will be received on either ENET 1 or 2 interfaces
         using the Chassis IP addresses.
         Index 1 - 64 indicates RPC commands for this output will ONLY be received
         on that specific Ethernet address assigned to that QAM Device index. 
         
         Not configurable for RTSP.
        "
::= { apexSesContBlade6ConfEntry 4 }

apexSesContBlade6ConfCmdOutputPort OBJECT-TYPE
    SYNTAX Integer32(1..2048)
    MAX-ACCESS read-write
    STATUS current
    DESCRIPTION
        "The RPC command output port number associated with this output TS. This is
         a relative 1 command output port number. 0 is not valid and will result in
         a calculated default value for the command port to be used. 
         The command output port is the value in each received RPC command. Each  
         command output port is assigned to a specific QAM blade and output TS. 
         
         Not configurable for RTSP.
        "
::= { apexSesContBlade6ConfEntry 5 }


-- ------------------------------------------------------------------------------
--
-- apexSesContBlade7ConfTable
--

apexSesContBlade7ConfTable OBJECT-TYPE
    SYNTAX SEQUENCE OF ApexSesContBlade7ConfEntry
    MAX-ACCESS not-accessible
    STATUS current
    DESCRIPTION
        "This is a table of Session Control configuration parameters for
         each output transport stream. This table defines the primary
         and secondary Gigabit Ethernet interfaces for each output stream
         in Session Control operating mode. The primary and secondary
         interfaces cannot be changed for an output stream when there are
         active Session Control mappings. All Session Control mappings on
         an output stream must be removed prior to changing the primary or
         secondary interface settings.

         Once written, the change to this table will only take immediate
         effect after apexSesContConfTableApplyChange is set to 'apply'.  In
         order for the change to persist through subsequent reboots or power
         cycles, the change must be saved via the apexSaveConfig parameter.

         @Config(config=yes, reboot=no)
         @Commit(param=apexSesContConfTableApplyChange, value=2)
         @Save(apexSaveConfig, value=2)
         @File(sdvcfg.ini, type='ini')
        "
::= { apexSessionControlConfig 8 }

apexSesContBlade7ConfEntry OBJECT-TYPE
    SYNTAX ApexSesContBlade7ConfEntry
    MAX-ACCESS not-accessible
    STATUS current
    DESCRIPTION
        "Session Control Configuration Table Entry."
    INDEX { apexSesContBlade7ConfOutputTsNum }
::= { apexSesContBlade7ConfTable 1 }

ApexSesContBlade7ConfEntry ::= SEQUENCE
    {
     apexSesContBlade7ConfOutputTsNum             Integer32,
     apexSesContBlade7ConfGbePrimaryInterface     Integer32,
     apexSesContBlade7ConfGbeSecondaryInterface   Integer32,
     apexSesContBlade7ConfQamDeviceIndex          Integer32,
     apexSesContBlade7ConfCmdOutputPort           Integer32
    }

apexSesContBlade7ConfOutputTsNum OBJECT-TYPE
    SYNTAX Integer32(1..256)
    MAX-ACCESS not-accessible
    STATUS current
    DESCRIPTION
        "Output transport stream number (index)."
::= { apexSesContBlade7ConfEntry 1 }

apexSesContBlade7ConfGbePrimaryInterface OBJECT-TYPE
    SYNTAX Integer32(0..12)
    MAX-ACCESS read-write
    STATUS current
    DESCRIPTION
        "The primary Gbe interface for Session Control.  Zero indicates not available.
         This parameter cannot be changed for any output stream if there is at
         least 1 active session control mapping.

         Not configurable for RTSP.
        "
::= { apexSesContBlade7ConfEntry 2 }

apexSesContBlade7ConfGbeSecondaryInterface OBJECT-TYPE
    SYNTAX Integer32(0..12)
    MAX-ACCESS read-write
    STATUS current
    DESCRIPTION
        "The secondary Gbe interface for RPC SDV.  Zero indicates not available.
         This parameter cannot be changed for any output stream if there is at
         least 1 active session control mapping.

         Not configurable for RTSP.
        "
::= { apexSesContBlade7ConfEntry 3 }

apexSesContBlade7ConfQamDeviceIndex OBJECT-TYPE
    SYNTAX Integer32(0..64)
    MAX-ACCESS read-write
    STATUS current
    DESCRIPTION
        "The index of the Generic QAM Device associated with this output TS. 
         Index of 0 indicates that this output is not associated with any specific
         device. RPC commands will be received on either ENET 1 or 2 interfaces
         using the Chassis IP addresses.
         Index 1 - 64 indicates RPC commands for this output will ONLY be received
         on that specific Ethernet address assigned to that QAM Device index. 
         
         Not configurable for RTSP.
        "
::= { apexSesContBlade7ConfEntry 4 }

apexSesContBlade7ConfCmdOutputPort OBJECT-TYPE
    SYNTAX Integer32(1..2048)
    MAX-ACCESS read-write
    STATUS current
    DESCRIPTION
        "The RPC command output port number associated with this output TS. This is
         a relative 1 command output port number. 0 is not valid and will result in
         a calculated default value for the command port to be used. 
         The command output port is the value in each received RPC command. Each  
         command output port is assigned to a specific QAM blade and output TS. 
         
         Not configurable for RTSP.
        "
::= { apexSesContBlade7ConfEntry 5 }


-- ------------------------------------------------------------------------------
--
-- apexSesContBlade8ConfTable
--

apexSesContBlade8ConfTable OBJECT-TYPE
    SYNTAX SEQUENCE OF ApexSesContBlade8ConfEntry
    MAX-ACCESS not-accessible
    STATUS current
    DESCRIPTION
        "This is a table of Session Control configuration parameters for
         each output transport stream. This table defines the primary
         and secondary Gigabit Ethernet interfaces for each output stream
         in Session Control operating mode. The primary and secondary
         interfaces cannot be changed for an output stream when there are
         active Session Control mappings. All Session Control mappings on
         an output stream must be removed prior to changing the primary or
         secondary interface settings.

         Once written, the change to this table will only take immediate
         effect after apexSesContConfTableApplyChange is set to 'apply'.  In
         order for the change to persist through subsequent reboots or power
         cycles, the change must be saved via the apexSaveConfig parameter.

         @Config(config=yes, reboot=no)
         @Commit(param=apexSesContConfTableApplyChange, value=2)
         @Save(apexSaveConfig, value=2)
         @File(sdvcfg.ini, type='ini')
        "
::= { apexSessionControlConfig 9 }

apexSesContBlade8ConfEntry OBJECT-TYPE
    SYNTAX ApexSesContBlade8ConfEntry
    MAX-ACCESS not-accessible
    STATUS current
    DESCRIPTION
        "Session Control Configuration Table Entry."
    INDEX { apexSesContBlade8ConfOutputTsNum }
::= { apexSesContBlade8ConfTable 1 }

ApexSesContBlade8ConfEntry ::= SEQUENCE
    {
     apexSesContBlade8ConfOutputTsNum             Integer32,
     apexSesContBlade8ConfGbePrimaryInterface     Integer32,
     apexSesContBlade8ConfGbeSecondaryInterface   Integer32,
     apexSesContBlade8ConfQamDeviceIndex          Integer32,
     apexSesContBlade8ConfCmdOutputPort           Integer32
    }

apexSesContBlade8ConfOutputTsNum OBJECT-TYPE
    SYNTAX Integer32(1..256)
    MAX-ACCESS not-accessible
    STATUS current
    DESCRIPTION
        "Output transport stream number (index)."
::= { apexSesContBlade8ConfEntry 1 }

apexSesContBlade8ConfGbePrimaryInterface OBJECT-TYPE
    SYNTAX Integer32(0..12)
    MAX-ACCESS read-write
    STATUS current
    DESCRIPTION
        "The primary Gbe interface for Session Control.  Zero indicates not available.
         This parameter cannot be changed for any output stream if there is at
         least 1 active session control mapping.

         Not configurable for RTSP.
        "
::= { apexSesContBlade8ConfEntry 2 }

apexSesContBlade8ConfGbeSecondaryInterface OBJECT-TYPE
    SYNTAX Integer32(0..12)
    MAX-ACCESS read-write
    STATUS current
    DESCRIPTION
        "The secondary Gbe interface for RPC SDV.  Zero indicates not available.
         This parameter cannot be changed for any output stream if there is at
         least 1 active session control mapping.

         Not configurable for RTSP.
        "
::= { apexSesContBlade8ConfEntry 3 }

apexSesContBlade8ConfQamDeviceIndex OBJECT-TYPE
    SYNTAX Integer32(0..64)
    MAX-ACCESS read-write
    STATUS current
    DESCRIPTION
        "The index of the Generic QAM Device associated with this output TS. 
         Index of 0 indicates that this output is not associated with any specific
         device. RPC commands will be received on either ENET 1 or 2 interfaces
         using the Chassis IP addresses.
         Index 1 - 64 indicates RPC commands for this output will ONLY be received
         on that specific Ethernet address assigned to that QAM Device index. 
         
         Not configurable for RTSP.
        "
::= { apexSesContBlade8ConfEntry 4 }

apexSesContBlade8ConfCmdOutputPort OBJECT-TYPE
    SYNTAX Integer32(1..2048)
    MAX-ACCESS read-write
    STATUS current
    DESCRIPTION
        "The RPC command output port number associated with this output TS. This is
         a relative 1 command output port number. 0 is not valid and will result in
         a calculated default value for the command port to be used. 
         The command output port is the value in each received RPC command. Each  
         command output port is assigned to a specific QAM blade and output TS. 
         
         Not configurable for RTSP.
        "
::= { apexSesContBlade8ConfEntry 5 }


-- ------------------------------------------------------------------------------
--
-- apexSessionControlStatus
--
-- apexSessionControlStatusGeneral
--

apexSesContStatusTableApplyText OBJECT-TYPE
    SYNTAX DisplayString (SIZE (0..80))
    MAX-ACCESS read-only
    STATUS current
    DESCRIPTION
        "When apexSesContConfTableApplyChange is set to applyNotInProgressInvalidData,
         this entry may contain a text description of what was wrong with the data.
         This entry contains the description for the most recent apply
         of a related entry that was invalid. 
        "
::= { apexSessionControlStatusGeneral 1 }

apexSesContStatusReportUdpMapApplyText OBJECT-TYPE
    SYNTAX DisplayString (SIZE (0..80))
    MAX-ACCESS read-only
    STATUS current
    DESCRIPTION
        "When apexSesContConfReportUdpMappings is changed, this entry may contain a 
         text description of what was wrong with the data. It will be clear (null)
         when there changed data is valid.
         
         This entry contains the description for the most recent apply
         of a related entry that was invalid. 
        "
::= { apexSessionControlStatusGeneral 2 }


-- ------------------------------------------------------------------------------
--
-- apexRpc
--
-- apexRpcConfig
--
-- apexRpcConfigGeneral
--

apexRpcDataCarouselProgram OBJECT-TYPE
    SYNTAX Integer32(0..65535)
    MAX-ACCESS read-write
    STATUS current
    DESCRIPTION
        "Indicates which Input Program Number to use for the Data
         Carousel.  The data carousel in SDV mode (RPC or RTSP) is on a fixed
         PMT PID along with a fixed component PID. In order to maintain
         these PID values, the APEX will check for a specific input service
         number defined by this parameter. This service mapping is assumed
         to be the Data Carousel mapping. The APEX will maintain the PMT PID
         value along with the component PID value.  To facilitate this mapping,
         the Data Carousel input/output program number is configurable.
           - Data Carousel Service Number Default: 0xF38F (62351)

         The PMT PID and component PID will be determined by the APEX by
         analyzing the PAT and PMT based on the program number configured. A
         program number of zero (0) indicates that there is no data carousel.

         Once written, the change to this parameter will take immediate
         effect.  In order for the change to persist through subsequent
         reboots or power cycles, the change must be saved via the
         apexSaveConfig parameter.

         @Config(config=yes, reboot=no)
         @Save(apexSaveConfig, value=2)
         @File(sdvcfg.ini, type='ini')
        "
::= { apexRpcConfigGeneral 1 }

apexRpcReportAllSessions OBJECT-TYPE
    SYNTAX EnableDisableTYPE
    MAX-ACCESS read-write
    STATUS current
    DESCRIPTION
        "Session reporting mode.  Indicates what sessions will be reported
         when the APEX is requested to report sessions to a manager.

         When 'enabled', the APEX will report all sessions.
         When 'disabled', the APEX will report only the sessions for the requesting
         manager.

         Once written, the change to this parameter will take immediate
         effect.  In order for the change to persist through subsequent
         reboots or power cycles, the change must be saved via the
         apexSaveConfig parameter.

         @Config(config=yes, reboot=no)
         @Save(apexSaveConfig, value=2)
         @File(sdvcfg.ini, type='ini')
        "
::= { apexRpcConfigGeneral 2 }

apexRpcDeviceName OBJECT-TYPE
    SYNTAX DisplayString (SIZE (0..64))
    MAX-ACCESS read-write
    STATUS current
    DESCRIPTION
        "The device name of this APEX.  This variable is only used to      
         generate an XML configuration file via the EM.

         Once written, the change to this parameter will take immediate
         effect.  In order for the change to persist through subsequent
         reboots or power cycles, the change must be saved via the
         apexSaveConfig parameter.
         
         @Config(config=yes, reboot=no)
         @Save(apexSaveConfig, value=2)
         @File(sdvcfg.ini, type='ini')
        "
::= { apexRpcConfigGeneral 3 }

apexRpcDeviceType OBJECT-TYPE
    SYNTAX DisplayString (SIZE (0..64))
    MAX-ACCESS read-write
    STATUS current
    DESCRIPTION
        "The device type string reported in XML configuration file.  This  
         variable is only used to generate an XML configuration file via the  
         EM.

         Once written, the change to this parameter will take immediate
         effect.  In order for the change to persist through subsequent
         reboots or power cycles, the change must be saved via the
         apexSaveConfig parameter.
         
         @Config(config=yes, reboot=no)
         @Save(apexSaveConfig, value=2)
         @File(sdvcfg.ini, type='ini')
        "
::= { apexRpcConfigGeneral 4 }

apexRpcControlInterface  OBJECT-TYPE
    SYNTAX EthernetInterfaceTYPE
    MAX-ACCESS read-write
    STATUS current
    DESCRIPTION
        "The Enet interface that will be used to set the IP address attribute
         in the generated XML file.  This variable is only used to generate
         an XML configuration file via the EM.

         Once written, the change to this parameter will only take immediate
         effect after apexRpcApplyChange is changed to 'apply'.
         In order for the change to persist through subsequent
         reboots or power cycles, the change must be saved via the
         apexSaveConfig parameter.
         
         @Config(config=yes, reboot=no)
         @Commit(param=apexRpcApplyChange, value=2)
         @Save(apexSaveConfig, value=2)
         @File(sdvcfg.ini, type='ini')
        "
::= { apexRpcConfigGeneral 5 }

apexRpcNumShellSessions OBJECT-TYPE
    SYNTAX Integer32(1..32)
    MAX-ACCESS read-write
    STATUS current
    DESCRIPTION
        "The number of shell sessions to be created on each channel marked 
         for session control mode.  This variable is only used to generate an 
         XML configuration file via    the EM.

         Once written, the change to this parameter will only take immediate
         effect after apexRpcApplyChange is changed to 'apply'.
         In order for the change to persist through subsequent
         reboots or power cycles, the change must be saved via the
         apexSaveConfig parameter.
         
         @Config(config=yes, reboot=no)
         @Commit(param=apexRpcApplyChange, value=2)
         @Save(apexSaveConfig, value=2)
         @File(sdvcfg.ini, type='ini')
        "
::= { apexRpcConfigGeneral 6 }

apexRpcAvgBandwidthEnable OBJECT-TYPE
    SYNTAX EnableDisableTYPE
    MAX-ACCESS read-write
    STATUS current
    DESCRIPTION
        "When enabled the APEX populates the sessionRate in the QuerySessionInfo Response 
         message with groupRate divided by the number of sessionIds in the group.  The 
         value reported makes no distinction between bound and unbound sessions.
         
         Once written, the change to this parameter will take immediate
         effect.  In order for the change to persist through subsequent
         reboots or power cycles, the change must be saved via the
         apexSaveConfig parameter.

         @Config(config=yes, reboot=no)
         @Save(apexSaveConfig, value=2)
         @File(sdvcfg.ini, type='ini')
        "
::= { apexRpcConfigGeneral 7 }

apexRpcApplyChange OBJECT-TYPE
    SYNTAX ApplyDataToDeviceTYPE
    MAX-ACCESS read-write
    STATUS current
    DESCRIPTION
        "The Apply for RPC Settings.  This applies to apexRpcControlInterface,
         apexRpcNumShellSessions, apexRpcBladeXRfPortServiceGroup.
         
         @Config(config=no, reboot=no)
        "
::= { apexRpcConfigGeneral 8 }

apexRpcTeardownSessions OBJECT-TYPE
    SYNTAX INTEGER
        {
         teardownNotInProgress     (1),
         teardownSessions          (2)
        }
    MAX-ACCESS read-write
    STATUS current
    DESCRIPTION
        "When set to teardownSessions(2), this results in the APEX
         removing all of the RPC sessions.  After the sessions
         have been torn down the parameter will be set to
         teardownNotInProgress.
         
         Once written, the change to this table will take immediate
         effect.

         @Config(config=no, reboot=no)
        "
::= { apexRpcConfigGeneral 9 }

apexRpcIncludeGenericQamDevices OBJECT-TYPE
    SYNTAX EnableDisableTYPE
    MAX-ACCESS read-write
    STATUS current
    DESCRIPTION
        "When enabled the APEX includes Generic QAM Devices when generating 
         an XML configuration file of the APEX. This allows for a file to be 
         generated that references outputs that are either assigned to a specific
         controlling device or not assigned to any controlling device.
         
         Once written, the change to this parameter will take immediate
         effect.  In order for the change to persist through subsequent
         reboots or power cycles, the change must be saved via the
         apexSaveConfig parameter.

         @Config(config=yes, reboot=no)
         @Save(apexSaveConfig, value=2)
         @File(sdvcfg.ini, type='ini')
        "
::= { apexRpcConfigGeneral 10 }

apexRpcReportSessionInfoPmt OBJECT-TYPE
    SYNTAX EnableDisableTYPE
    MAX-ACCESS read-write
    STATUS current
    DESCRIPTION
        "Session info PMT reporting flag. Indicates if the PMT is to be included in
         the session info query response. 

         When 'enabled', the APEX will include the PMT in the response if found.
         When 'disabled', the APEX will exclude the PMT from the session info response.

         Once written, the change to this parameter will take immediate
         effect.  In order for the change to persist through subsequent
         reboots or power cycles, the change must be saved via the
         apexSaveConfig parameter.

         @Config(config=yes, reboot=no)
         @Save(apexSaveConfig, value=2)
         @File(sdvcfg.ini, type='ini')
        "
::= { apexRpcConfigGeneral 11 }

apexRpcEdgeAnnounceEnable OBJECT-TYPE
    SYNTAX EnableDisableTYPE
    MAX-ACCESS read-write
    STATUS current
    DESCRIPTION
        "Edge Announce message reporting flag. Indicates if the Edge Announce message
         is to be sent. 

         When 'enabled', the APEX will send Edge Announce messages.
         When 'disabled', the APEX will not send Edge Announce messages.

         Once written, the change to this parameter will take immediate
         effect.  In order for the change to persist through subsequent
         reboots or power cycles, the change must be saved via the
         apexSaveConfig parameter.

         @Config(config=yes, reboot=no)
         @Save(apexSaveConfig, value=2)
         @File(sdvcfg.ini, type='ini')
        "
::= { apexRpcConfigGeneral 12 }


-- ------------------------------------------------------------------------------
--
-- apexRpcBlade1Config
--
-- apexRpcBlade1RfPortTable
--

apexRpcBlade1RfPortTable OBJECT-TYPE
    SYNTAX SEQUENCE OF ApexRpcBlade1RfPortEntry
    MAX-ACCESS not-accessible
    STATUS current
    DESCRIPTION
        "Table of Configuration data for RPC Session RF Ports.  This variable 
         is only used to generate an XML configuration file via the EM.
        "
::= { apexRpcBlade1Config 1 }

apexRpcBlade1RfPortEntry OBJECT-TYPE
    SYNTAX ApexRpcBlade1RfPortEntry 
    MAX-ACCESS not-accessible
    STATUS current
    DESCRIPTION
        "RPC RF Port Configuration Table Entry."
    INDEX { apexRpcBlade1RfPortNum }
::= { apexRpcBlade1RfPortTable 1 }

ApexRpcBlade1RfPortEntry ::= SEQUENCE
    {
     apexRpcBlade1RfPortNum          Integer32,
     apexRpcBlade1RfPortName         DisplayString,
     apexRpcBlade1RfPortServiceGroup Unsigned32
    }

apexRpcBlade1RfPortNum OBJECT-TYPE
    SYNTAX Integer32(1..4)
    MAX-ACCESS not-accessible
    STATUS current
    DESCRIPTION
        "The RF Port number."
::= { apexRpcBlade1RfPortEntry 1 }

apexRpcBlade1RfPortName OBJECT-TYPE
    SYNTAX DisplayString (SIZE (0..64))
    MAX-ACCESS read-write
    STATUS current
    DESCRIPTION
        "The RF Port name.
        
         Once written, the change to this parameter will take immediate
         effect.  In order for the change to persist through subsequent
         reboots or power cycles, the change must be saved via the
         apexSaveConfig parameter.  

         @Config(config=yes, reboot=no)
         @Save(apexSaveConfig, value=2)
         @File(sdvcfg.ini, type='ini')
        "
::= { apexRpcBlade1RfPortEntry 2 }

apexRpcBlade1RfPortServiceGroup OBJECT-TYPE
    SYNTAX Unsigned32(1..4294967295)   
    MAX-ACCESS read-write
    STATUS current
    DESCRIPTION
        "The RF Port service group.
        
         Once written, the change to this parameter will only take immediate
         effect after apexRpcApplyChange is changed to 'apply'.
         In order for the change to persist through subsequent
         reboots or power cycles, the change must be saved via the
         apexSaveConfig parameter.
         
         @Config(config=yes, reboot=no)
         @Commit(param=apexRpcApplyChange , value=2)
         @Save(apexSaveConfig, value=2)
         @File(sdvcfg.ini, type='ini')
        "
::= { apexRpcBlade1RfPortEntry 3 }


-- ------------------------------------------------------------------------------
--
-- apexRpcBlade1RfChannelTable
--

apexRpcBlade1RfChannelTable OBJECT-TYPE
    SYNTAX SEQUENCE OF ApexRpcBlade1RfChannelEntry
    MAX-ACCESS not-accessible
    STATUS current
    DESCRIPTION
        "Table of Configuration data for RPC Session RF Channels.  This variable
         is only used to generate an XML configuration file via the EM.

         Once written, the change to this parameter will take immediate
         effect.  In order for the change to persist through subsequent
         reboots or power cycles, the change must be saved via the
         apexSaveConfig parameter.  

         @Config(config=yes, reboot=no)
         @Save(apexSaveConfig, value=2)
         @File(sdvcfg.ini, type='ini')
        "
::= { apexRpcBlade1Config 2 }

apexRpcBlade1RfChannelEntry OBJECT-TYPE
    SYNTAX ApexRpcBlade1RfChannelEntry 
    MAX-ACCESS not-accessible
    STATUS current
    DESCRIPTION
        "RPC RF Channel Configuration Table Entry."
    INDEX { apexRpcBlade1RfChannelNum }
::= { apexRpcBlade1RfChannelTable 1 }

ApexRpcBlade1RfChannelEntry ::= SEQUENCE
    {
     apexRpcBlade1RfChannelNum   Integer32,
     apexRpcBlade1RfChannelName  DisplayString
    }

apexRpcBlade1RfChannelNum OBJECT-TYPE
    SYNTAX Integer32(1..256)
    MAX-ACCESS not-accessible
    STATUS current
    DESCRIPTION
        "The RF Channel number."
::= { apexRpcBlade1RfChannelEntry 1 }
    
apexRpcBlade1RfChannelName OBJECT-TYPE
    SYNTAX DisplayString (SIZE (0..64))
    MAX-ACCESS read-write
    STATUS current
    DESCRIPTION
        "The name of this RF Channel.
        "
::= { apexRpcBlade1RfChannelEntry 2 }


-- ------------------------------------------------------------------------------
--
-- apexRpcBlade2Config
--
-- apexRpcBlade2RfPortTable
--

apexRpcBlade2RfPortTable OBJECT-TYPE
    SYNTAX SEQUENCE OF ApexRpcBlade2RfPortEntry
    MAX-ACCESS not-accessible
    STATUS current
    DESCRIPTION
        "Table of Configuration data for RPC Session RF Ports.  This variable 
         is only used to generate an XML configuration file via the EM.
        "
::= { apexRpcBlade2Config 1 }

apexRpcBlade2RfPortEntry OBJECT-TYPE
    SYNTAX ApexRpcBlade2RfPortEntry 
    MAX-ACCESS not-accessible
    STATUS current
    DESCRIPTION
        "RPC RF Port Configuration Table Entry."
    INDEX { apexRpcBlade2RfPortNum }
::= { apexRpcBlade2RfPortTable 1 }

ApexRpcBlade2RfPortEntry ::= SEQUENCE
    {
     apexRpcBlade2RfPortNum          Integer32,
     apexRpcBlade2RfPortName         DisplayString,
     apexRpcBlade2RfPortServiceGroup Unsigned32
    }

apexRpcBlade2RfPortNum OBJECT-TYPE
    SYNTAX Integer32(1..4)
    MAX-ACCESS not-accessible
    STATUS current
    DESCRIPTION
        "The RF Port number."
::= { apexRpcBlade2RfPortEntry 1 }

apexRpcBlade2RfPortName OBJECT-TYPE
    SYNTAX DisplayString (SIZE (0..64))
    MAX-ACCESS read-write
    STATUS current
    DESCRIPTION
        "The RF Port name.
        
         Once written, the change to this parameter will take immediate
         effect.  In order for the change to persist through subsequent
         reboots or power cycles, the change must be saved via the
         apexSaveConfig parameter.  

         @Config(config=yes, reboot=no)
         @Save(apexSaveConfig, value=2)
         @File(sdvcfg.ini, type='ini')
        "
::= { apexRpcBlade2RfPortEntry 2 }

apexRpcBlade2RfPortServiceGroup OBJECT-TYPE
    SYNTAX Unsigned32(1..4294967295)   
    MAX-ACCESS read-write
    STATUS current
    DESCRIPTION
        "The RF Port service group.
        
         Once written, the change to this parameter will only take immediate
         effect after apexRpcApplyChange is changed to 'apply'.
         In order for the change to persist through subsequent
         reboots or power cycles, the change must be saved via the
         apexSaveConfig parameter.
         
         @Config(config=yes, reboot=no)
         @Commit(param=apexRpcApplyChange , value=2)
         @Save(apexSaveConfig, value=2)
         @File(sdvcfg.ini, type='ini')
        "
::= { apexRpcBlade2RfPortEntry 3 }


-- ------------------------------------------------------------------------------
--
-- apexRpcBlade2RfChannelTable
--

apexRpcBlade2RfChannelTable OBJECT-TYPE
    SYNTAX SEQUENCE OF ApexRpcBlade2RfChannelEntry
    MAX-ACCESS not-accessible
    STATUS current
    DESCRIPTION
        "Table of Configuration data for RPC Session RF Channels.  This variable
         is only used to generate an XML configuration file via the EM.

         Once written, the change to this parameter will take immediate
         effect.  In order for the change to persist through subsequent
         reboots or power cycles, the change must be saved via the
         apexSaveConfig parameter.  

         @Config(config=yes, reboot=no)
         @Save(apexSaveConfig, value=2)
         @File(sdvcfg.ini, type='ini')
        "
::= { apexRpcBlade2Config 2 }

apexRpcBlade2RfChannelEntry OBJECT-TYPE
    SYNTAX ApexRpcBlade2RfChannelEntry 
    MAX-ACCESS not-accessible
    STATUS current
    DESCRIPTION
        "RPC RF Channel Configuration Table Entry."
    INDEX { apexRpcBlade2RfChannelNum }
::= { apexRpcBlade2RfChannelTable 1 }

ApexRpcBlade2RfChannelEntry ::= SEQUENCE
    {
     apexRpcBlade2RfChannelNum   Integer32,
     apexRpcBlade2RfChannelName  DisplayString
    }

apexRpcBlade2RfChannelNum OBJECT-TYPE
    SYNTAX Integer32(1..256)
    MAX-ACCESS not-accessible
    STATUS current
    DESCRIPTION
        "The RF Channel number."
::= { apexRpcBlade2RfChannelEntry 1 }
    
apexRpcBlade2RfChannelName OBJECT-TYPE
    SYNTAX DisplayString (SIZE (0..64))
    MAX-ACCESS read-write
    STATUS current
    DESCRIPTION
        "The name of this RF Channel.
        "
::= { apexRpcBlade2RfChannelEntry 2 }


-- ------------------------------------------------------------------------------
--
-- apexRpcBlade3Config
--
-- apexRpcBlade3RfPortTable
--

apexRpcBlade3RfPortTable OBJECT-TYPE
    SYNTAX SEQUENCE OF ApexRpcBlade3RfPortEntry
    MAX-ACCESS not-accessible
    STATUS current
    DESCRIPTION
        "Table of Configuration data for RPC Session RF Ports.  This variable 
         is only used to generate an XML configuration file via the EM.
        "
::= { apexRpcBlade3Config 1 }

apexRpcBlade3RfPortEntry OBJECT-TYPE
    SYNTAX ApexRpcBlade3RfPortEntry 
    MAX-ACCESS not-accessible
    STATUS current
    DESCRIPTION
        "RPC RF Port Configuration Table Entry."
    INDEX { apexRpcBlade3RfPortNum }
::= { apexRpcBlade3RfPortTable 1 }

ApexRpcBlade3RfPortEntry ::= SEQUENCE
    {
     apexRpcBlade3RfPortNum          Integer32,
     apexRpcBlade3RfPortName         DisplayString,
     apexRpcBlade3RfPortServiceGroup Unsigned32
    }

apexRpcBlade3RfPortNum OBJECT-TYPE
    SYNTAX Integer32(1..4)
    MAX-ACCESS not-accessible
    STATUS current
    DESCRIPTION
        "The RF Port number."
::= { apexRpcBlade3RfPortEntry 1 }

apexRpcBlade3RfPortName OBJECT-TYPE
    SYNTAX DisplayString (SIZE (0..64))
    MAX-ACCESS read-write
    STATUS current
    DESCRIPTION
        "The RF Port name.
        
         Once written, the change to this parameter will take immediate
         effect.  In order for the change to persist through subsequent
         reboots or power cycles, the change must be saved via the
         apexSaveConfig parameter.  

         @Config(config=yes, reboot=no)
         @Save(apexSaveConfig, value=2)
         @File(sdvcfg.ini, type='ini')
        "
::= { apexRpcBlade3RfPortEntry 2 }

apexRpcBlade3RfPortServiceGroup OBJECT-TYPE
    SYNTAX Unsigned32(1..4294967295)   
    MAX-ACCESS read-write
    STATUS current
    DESCRIPTION
        "The RF Port service group.
        
         Once written, the change to this parameter will only take immediate
         effect after apexRpcApplyChange is changed to 'apply'.
         In order for the change to persist through subsequent
         reboots or power cycles, the change must be saved via the
         apexSaveConfig parameter.
         
         @Config(config=yes, reboot=no)
         @Commit(param=apexRpcApplyChange , value=2)
         @Save(apexSaveConfig, value=2)
         @File(sdvcfg.ini, type='ini')
        "
::= { apexRpcBlade3RfPortEntry 3 }


-- ------------------------------------------------------------------------------
--
-- apexRpcBlade3RfChannelTable
--

apexRpcBlade3RfChannelTable OBJECT-TYPE
    SYNTAX SEQUENCE OF ApexRpcBlade3RfChannelEntry
    MAX-ACCESS not-accessible
    STATUS current
    DESCRIPTION
        "Table of Configuration data for RPC Session RF Channels.  This variable
         is only used to generate an XML configuration file via the EM.

         Once written, the change to this parameter will take immediate
         effect.  In order for the change to persist through subsequent
         reboots or power cycles, the change must be saved via the
         apexSaveConfig parameter.  

         @Config(config=yes, reboot=no)
         @Save(apexSaveConfig, value=2)
         @File(sdvcfg.ini, type='ini')
        "
::= { apexRpcBlade3Config 2 }

apexRpcBlade3RfChannelEntry OBJECT-TYPE
    SYNTAX ApexRpcBlade3RfChannelEntry 
    MAX-ACCESS not-accessible
    STATUS current
    DESCRIPTION
        "RPC RF Channel Configuration Table Entry."
    INDEX { apexRpcBlade3RfChannelNum }
::= { apexRpcBlade3RfChannelTable 1 }

ApexRpcBlade3RfChannelEntry ::= SEQUENCE
    {
     apexRpcBlade3RfChannelNum   Integer32,
     apexRpcBlade3RfChannelName  DisplayString
    }

apexRpcBlade3RfChannelNum OBJECT-TYPE
    SYNTAX Integer32(1..256)
    MAX-ACCESS not-accessible
    STATUS current
    DESCRIPTION
        "The RF Channel number."
::= { apexRpcBlade3RfChannelEntry 1 }

apexRpcBlade3RfChannelName OBJECT-TYPE
    SYNTAX DisplayString (SIZE (0..64))
    MAX-ACCESS read-write
    STATUS current
    DESCRIPTION
        "The name of this RF Channel.
        "
::= { apexRpcBlade3RfChannelEntry 2 }


-- ------------------------------------------------------------------------------
--
-- apexRpcBlade4Config
--
-- apexRpcBlade4RfPortTable
--

apexRpcBlade4RfPortTable OBJECT-TYPE
    SYNTAX SEQUENCE OF ApexRpcBlade4RfPortEntry
    MAX-ACCESS not-accessible
    STATUS current
    DESCRIPTION
        "Table of Configuration data for RPC Session RF Ports.  This variable 
         is only used to generate an XML configuration file via the EM.
        "
::= { apexRpcBlade4Config 1 }

apexRpcBlade4RfPortEntry OBJECT-TYPE
    SYNTAX ApexRpcBlade4RfPortEntry 
    MAX-ACCESS not-accessible
    STATUS current
    DESCRIPTION
        "RPC RF Port Configuration Table Entry."
    INDEX { apexRpcBlade4RfPortNum }
::= { apexRpcBlade4RfPortTable 1 }

ApexRpcBlade4RfPortEntry ::= SEQUENCE
    {
     apexRpcBlade4RfPortNum          Integer32,
     apexRpcBlade4RfPortName         DisplayString,
     apexRpcBlade4RfPortServiceGroup Unsigned32
    }

apexRpcBlade4RfPortNum OBJECT-TYPE
    SYNTAX Integer32(1..4)
    MAX-ACCESS not-accessible
    STATUS current
    DESCRIPTION
        "The RF Port number."
::= { apexRpcBlade4RfPortEntry 1 }

apexRpcBlade4RfPortName OBJECT-TYPE
    SYNTAX DisplayString (SIZE (0..64))
    MAX-ACCESS read-write
    STATUS current
    DESCRIPTION
        "The RF Port name.
        
         Once written, the change to this parameter will take immediate
         effect.  In order for the change to persist through subsequent
         reboots or power cycles, the change must be saved via the
         apexSaveConfig parameter.  

         @Config(config=yes, reboot=no)
         @Save(apexSaveConfig, value=2)
         @File(sdvcfg.ini, type='ini')
        "
::= { apexRpcBlade4RfPortEntry 2 }

apexRpcBlade4RfPortServiceGroup OBJECT-TYPE
    SYNTAX Unsigned32(1..4294967295)   
    MAX-ACCESS read-write
    STATUS current
    DESCRIPTION
        "The RF Port service group.
        
         Once written, the change to this parameter will only take immediate
         effect after apexRpcApplyChange is changed to 'apply'.
         In order for the change to persist through subsequent
         reboots or power cycles, the change must be saved via the
         apexSaveConfig parameter.
         
         @Config(config=yes, reboot=no)
         @Commit(param=apexRpcApplyChange , value=2)
         @Save(apexSaveConfig, value=2)
         @File(sdvcfg.ini, type='ini')
        "
::= { apexRpcBlade4RfPortEntry 3 }


-- ------------------------------------------------------------------------------
--
-- apexRpcBlade4RfChannelTable
--

apexRpcBlade4RfChannelTable OBJECT-TYPE
    SYNTAX SEQUENCE OF ApexRpcBlade4RfChannelEntry
    MAX-ACCESS not-accessible
    STATUS current
    DESCRIPTION
        "Table of Configuration data for RPC Session RF Channels.  This variable
         is only used to generate an XML configuration file via the EM.

         Once written, the change to this parameter will take immediate
         effect.  In order for the change to persist through subsequent
         reboots or power cycles, the change must be saved via the
         apexSaveConfig parameter.  

         @Config(config=yes, reboot=no)
         @Save(apexSaveConfig, value=2)
         @File(sdvcfg.ini, type='ini')
        "
::= { apexRpcBlade4Config 2 }

apexRpcBlade4RfChannelEntry OBJECT-TYPE
    SYNTAX ApexRpcBlade4RfChannelEntry 
    MAX-ACCESS not-accessible
    STATUS current
    DESCRIPTION
        "RPC RF Channel Configuration Table Entry."
    INDEX { apexRpcBlade4RfChannelNum }
::= { apexRpcBlade4RfChannelTable 1 }

ApexRpcBlade4RfChannelEntry ::= SEQUENCE
    {
     apexRpcBlade4RfChannelNum   Integer32,
     apexRpcBlade4RfChannelName  DisplayString
    }

apexRpcBlade4RfChannelNum OBJECT-TYPE
    SYNTAX Integer32(1..256)
    MAX-ACCESS not-accessible
    STATUS current
    DESCRIPTION
        "The RF Channel number."
::= { apexRpcBlade4RfChannelEntry 1 }
    
apexRpcBlade4RfChannelName OBJECT-TYPE
    SYNTAX DisplayString (SIZE (0..64))
    MAX-ACCESS read-write
    STATUS current
    DESCRIPTION
        "The name of this RF Channel.
        "
::= { apexRpcBlade4RfChannelEntry 2 }


-- ------------------------------------------------------------------------------
--
-- apexRpcBlade5Config
--
-- apexRpcBlade5RfPortTable
--

apexRpcBlade5RfPortTable OBJECT-TYPE
    SYNTAX SEQUENCE OF ApexRpcBlade5RfPortEntry
    MAX-ACCESS not-accessible
    STATUS current
    DESCRIPTION
        "Table of Configuration data for RPC Session RF Ports.  This variable 
         is only used to generate an XML configuration file via the EM.
        "
::= { apexRpcBlade5Config 1 }

apexRpcBlade5RfPortEntry OBJECT-TYPE
    SYNTAX ApexRpcBlade5RfPortEntry 
    MAX-ACCESS not-accessible
    STATUS current
    DESCRIPTION
        "RPC RF Port Configuration Table Entry."
    INDEX { apexRpcBlade5RfPortNum }
::= { apexRpcBlade5RfPortTable 1 }

ApexRpcBlade5RfPortEntry ::= SEQUENCE
    {
     apexRpcBlade5RfPortNum          Integer32,
     apexRpcBlade5RfPortName         DisplayString,
     apexRpcBlade5RfPortServiceGroup Unsigned32
    }

apexRpcBlade5RfPortNum OBJECT-TYPE
    SYNTAX Integer32(1..4)
    MAX-ACCESS not-accessible
    STATUS current
    DESCRIPTION
        "The RF Port number."
::= { apexRpcBlade5RfPortEntry 1 }

apexRpcBlade5RfPortName OBJECT-TYPE
    SYNTAX DisplayString (SIZE (0..64))
    MAX-ACCESS read-write
    STATUS current
    DESCRIPTION
        "The RF Port name.
        
         Once written, the change to this parameter will take immediate
         effect.  In order for the change to persist through subsequent
         reboots or power cycles, the change must be saved via the
         apexSaveConfig parameter.  

         @Config(config=yes, reboot=no)
         @Save(apexSaveConfig, value=2)
         @File(sdvcfg.ini, type='ini')
        "
::= { apexRpcBlade5RfPortEntry 2 }

apexRpcBlade5RfPortServiceGroup OBJECT-TYPE
    SYNTAX Unsigned32(1..4294967295)   
    MAX-ACCESS read-write
    STATUS current
    DESCRIPTION
        "The RF Port service group.
        
         Once written, the change to this parameter will only take immediate
         effect after apexRpcApplyChange is changed to 'apply'.
         In order for the change to persist through subsequent
         reboots or power cycles, the change must be saved via the
         apexSaveConfig parameter.
         
         @Config(config=yes, reboot=no)
         @Commit(param=apexRpcApplyChange , value=2)
         @Save(apexSaveConfig, value=2)
         @File(sdvcfg.ini, type='ini')
        "
::= { apexRpcBlade5RfPortEntry 3 }


-- ------------------------------------------------------------------------------
--
-- apexRpcBlade5RfChannelTable
--

apexRpcBlade5RfChannelTable OBJECT-TYPE
    SYNTAX SEQUENCE OF ApexRpcBlade5RfChannelEntry
    MAX-ACCESS not-accessible
    STATUS current
    DESCRIPTION
        "Table of Configuration data for RPC Session RF Channels.  This variable
         is only used to generate an XML configuration file via the EM.

         Once written, the change to this parameter will take immediate
         effect.  In order for the change to persist through subsequent
         reboots or power cycles, the change must be saved via the
         apexSaveConfig parameter.  

         @Config(config=yes, reboot=no)
         @Save(apexSaveConfig, value=2)
         @File(sdvcfg.ini, type='ini')
        "
::= { apexRpcBlade5Config 2 }

apexRpcBlade5RfChannelEntry OBJECT-TYPE
    SYNTAX ApexRpcBlade5RfChannelEntry 
    MAX-ACCESS not-accessible
    STATUS current
    DESCRIPTION
        "RPC RF Channel Configuration Table Entry."
    INDEX { apexRpcBlade5RfChannelNum }
::= { apexRpcBlade5RfChannelTable 1 }

ApexRpcBlade5RfChannelEntry ::= SEQUENCE
    {
     apexRpcBlade5RfChannelNum   Integer32,
     apexRpcBlade5RfChannelName  DisplayString
    }

apexRpcBlade5RfChannelNum OBJECT-TYPE
    SYNTAX Integer32(1..256)
    MAX-ACCESS not-accessible
    STATUS current
    DESCRIPTION
        "The RF Channel number."
::= { apexRpcBlade5RfChannelEntry 1 }
    
apexRpcBlade5RfChannelName OBJECT-TYPE
    SYNTAX DisplayString (SIZE (0..64))
    MAX-ACCESS read-write
    STATUS current
    DESCRIPTION
        "The name of this RF Channel.
        "
::= { apexRpcBlade5RfChannelEntry 2 }


-- ------------------------------------------------------------------------------
--
-- apexRpcBlade6Config
--
-- apexRpcBlade6RfPortTable
--

apexRpcBlade6RfPortTable OBJECT-TYPE
    SYNTAX SEQUENCE OF ApexRpcBlade6RfPortEntry
    MAX-ACCESS not-accessible
    STATUS current
    DESCRIPTION
        "Table of Configuration data for RPC Session RF Ports.  This variable 
         is only used to generate an XML configuration file via the EM.
        "
::= { apexRpcBlade6Config 1 }

apexRpcBlade6RfPortEntry OBJECT-TYPE
    SYNTAX ApexRpcBlade6RfPortEntry 
    MAX-ACCESS not-accessible
    STATUS current
    DESCRIPTION
        "RPC RF Port Configuration Table Entry."
    INDEX { apexRpcBlade6RfPortNum }
::= { apexRpcBlade6RfPortTable 1 }

ApexRpcBlade6RfPortEntry ::= SEQUENCE
    {
     apexRpcBlade6RfPortNum          Integer32,
     apexRpcBlade6RfPortName         DisplayString,
     apexRpcBlade6RfPortServiceGroup Unsigned32
    }

apexRpcBlade6RfPortNum OBJECT-TYPE
    SYNTAX Integer32(1..4)
    MAX-ACCESS not-accessible
    STATUS current
    DESCRIPTION
        "The RF Port number."
::= { apexRpcBlade6RfPortEntry 1 }

apexRpcBlade6RfPortName OBJECT-TYPE
    SYNTAX DisplayString (SIZE (0..64))
    MAX-ACCESS read-write
    STATUS current
    DESCRIPTION
        "The RF Port name.
        
         Once written, the change to this parameter will take immediate
         effect.  In order for the change to persist through subsequent
         reboots or power cycles, the change must be saved via the
         apexSaveConfig parameter.  

         @Config(config=yes, reboot=no)
         @Save(apexSaveConfig, value=2)
         @File(sdvcfg.ini, type='ini')
        "
::= { apexRpcBlade6RfPortEntry 2 }

apexRpcBlade6RfPortServiceGroup OBJECT-TYPE
    SYNTAX Unsigned32(1..4294967295)   
    MAX-ACCESS read-write
    STATUS current
    DESCRIPTION
        "The RF Port service group.
        
         Once written, the change to this parameter will only take immediate
         effect after apexRpcApplyChange is changed to 'apply'.
         In order for the change to persist through subsequent
         reboots or power cycles, the change must be saved via the
         apexSaveConfig parameter.
         
         @Config(config=yes, reboot=no)
         @Commit(param=apexRpcApplyChange , value=2)
         @Save(apexSaveConfig, value=2)
         @File(sdvcfg.ini, type='ini')
        "
::= { apexRpcBlade6RfPortEntry 3 }


-- ------------------------------------------------------------------------------
--
-- apexRpcBlade6RfChannelTable
--

apexRpcBlade6RfChannelTable OBJECT-TYPE
    SYNTAX SEQUENCE OF ApexRpcBlade6RfChannelEntry
    MAX-ACCESS not-accessible
    STATUS current
    DESCRIPTION
        "Table of Configuration data for RPC Session RF Channels.  This variable
         is only used to generate an XML configuration file via the EM.

         Once written, the change to this parameter will take immediate
         effect.  In order for the change to persist through subsequent
         reboots or power cycles, the change must be saved via the
         apexSaveConfig parameter.  

         @Config(config=yes, reboot=no)
         @Save(apexSaveConfig, value=2)
         @File(sdvcfg.ini, type='ini')
        "
::= { apexRpcBlade6Config 2 }

apexRpcBlade6RfChannelEntry OBJECT-TYPE
    SYNTAX ApexRpcBlade6RfChannelEntry 
    MAX-ACCESS not-accessible
    STATUS current
    DESCRIPTION
        "RPC RF Channel Configuration Table Entry."
    INDEX { apexRpcBlade6RfChannelNum }
::= { apexRpcBlade6RfChannelTable 1 }

ApexRpcBlade6RfChannelEntry ::= SEQUENCE
    {
     apexRpcBlade6RfChannelNum   Integer32,
     apexRpcBlade6RfChannelName  DisplayString
    }

apexRpcBlade6RfChannelNum OBJECT-TYPE
    SYNTAX Integer32(1..256)
    MAX-ACCESS not-accessible
    STATUS current
    DESCRIPTION
        "The RF Channel number."
::= { apexRpcBlade6RfChannelEntry 1 }
    
apexRpcBlade6RfChannelName OBJECT-TYPE
    SYNTAX DisplayString (SIZE (0..64))
    MAX-ACCESS read-write
    STATUS current
    DESCRIPTION
        "The name of this RF Channel.
        "
::= { apexRpcBlade6RfChannelEntry 2 }


-- ------------------------------------------------------------------------------
--
-- apexRpcBlade7Config
--
-- apexRpcBlade7RfPortTable
--

apexRpcBlade7RfPortTable OBJECT-TYPE
    SYNTAX SEQUENCE OF ApexRpcBlade7RfPortEntry
    MAX-ACCESS not-accessible
    STATUS current
    DESCRIPTION
        "Table of Configuration data for RPC Session RF Ports.  This variable 
         is only used to generate an XML configuration file via the EM.
        "
::= { apexRpcBlade7Config 1 }

apexRpcBlade7RfPortEntry OBJECT-TYPE
    SYNTAX ApexRpcBlade7RfPortEntry 
    MAX-ACCESS not-accessible
    STATUS current
    DESCRIPTION
        "RPC RF Port Configuration Table Entry."
    INDEX { apexRpcBlade7RfPortNum }
::= { apexRpcBlade7RfPortTable 1 }

ApexRpcBlade7RfPortEntry ::= SEQUENCE
    {
     apexRpcBlade7RfPortNum          Integer32,
     apexRpcBlade7RfPortName         DisplayString,
     apexRpcBlade7RfPortServiceGroup Unsigned32
    }

apexRpcBlade7RfPortNum OBJECT-TYPE
    SYNTAX Integer32(1..4)
    MAX-ACCESS not-accessible
    STATUS current
    DESCRIPTION
        "The RF Port number."
::= { apexRpcBlade7RfPortEntry 1 }

apexRpcBlade7RfPortName OBJECT-TYPE
    SYNTAX DisplayString (SIZE (0..64))
    MAX-ACCESS read-write
    STATUS current
    DESCRIPTION
        "The RF Port name.
        
         Once written, the change to this parameter will take immediate
         effect.  In order for the change to persist through subsequent
         reboots or power cycles, the change must be saved via the
         apexSaveConfig parameter.  

         @Config(config=yes, reboot=no)
         @Save(apexSaveConfig, value=2)
         @File(sdvcfg.ini, type='ini')
        "
::= { apexRpcBlade7RfPortEntry 2 }

apexRpcBlade7RfPortServiceGroup OBJECT-TYPE
    SYNTAX Unsigned32(1..4294967295)   
    MAX-ACCESS read-write
    STATUS current
    DESCRIPTION
        "The RF Port service group.
        
         Once written, the change to this parameter will only take immediate
         effect after apexRpcApplyChange is changed to 'apply'.
         In order for the change to persist through subsequent
         reboots or power cycles, the change must be saved via the
         apexSaveConfig parameter.
         
         @Config(config=yes, reboot=no)
         @Commit(param=apexRpcApplyChange , value=2)
         @Save(apexSaveConfig, value=2)
         @File(sdvcfg.ini, type='ini')
        "
::= { apexRpcBlade7RfPortEntry 3 }


-- ------------------------------------------------------------------------------
--
-- apexRpcBlade7RfChannelTable
--

apexRpcBlade7RfChannelTable OBJECT-TYPE
    SYNTAX SEQUENCE OF ApexRpcBlade7RfChannelEntry
    MAX-ACCESS not-accessible
    STATUS current
    DESCRIPTION
        "Table of Configuration data for RPC Session RF Channels.  This variable
         is only used to generate an XML configuration file via the EM.

         Once written, the change to this parameter will take immediate
         effect.  In order for the change to persist through subsequent
         reboots or power cycles, the change must be saved via the
         apexSaveConfig parameter.  

         @Config(config=yes, reboot=no)
         @Save(apexSaveConfig, value=2)
         @File(sdvcfg.ini, type='ini')
        "
::= { apexRpcBlade7Config 2 }

apexRpcBlade7RfChannelEntry OBJECT-TYPE
    SYNTAX ApexRpcBlade7RfChannelEntry 
    MAX-ACCESS not-accessible
    STATUS current
    DESCRIPTION
        "RPC RF Channel Configuration Table Entry."
    INDEX { apexRpcBlade7RfChannelNum }
::= { apexRpcBlade7RfChannelTable 1 }

ApexRpcBlade7RfChannelEntry ::= SEQUENCE
    {
     apexRpcBlade7RfChannelNum   Integer32,
     apexRpcBlade7RfChannelName  DisplayString
    }

apexRpcBlade7RfChannelNum OBJECT-TYPE
    SYNTAX Integer32(1..256)
    MAX-ACCESS not-accessible
    STATUS current
    DESCRIPTION
        "The RF Channel number."
::= { apexRpcBlade7RfChannelEntry 1 }
    
apexRpcBlade7RfChannelName OBJECT-TYPE
    SYNTAX DisplayString (SIZE (0..64))
    MAX-ACCESS read-write
    STATUS current
    DESCRIPTION
        "The name of this RF Channel.
        "
::= { apexRpcBlade7RfChannelEntry 2 }


-- ------------------------------------------------------------------------------
--
-- apexRpcBlade8Config
--
-- apexRpcBlade8RfPortTable
--

apexRpcBlade8RfPortTable OBJECT-TYPE
    SYNTAX SEQUENCE OF ApexRpcBlade8RfPortEntry
    MAX-ACCESS not-accessible
    STATUS current
    DESCRIPTION
        "Table of Configuration data for RPC Session RF Ports.  This variable 
         is only used to generate an XML configuration file via the EM.
        "
::= { apexRpcBlade8Config 1 }

apexRpcBlade8RfPortEntry OBJECT-TYPE
    SYNTAX ApexRpcBlade8RfPortEntry 
    MAX-ACCESS not-accessible
    STATUS current
    DESCRIPTION
        "RPC RF Port Configuration Table Entry."
    INDEX { apexRpcBlade8RfPortNum }
::= { apexRpcBlade8RfPortTable 1 }

ApexRpcBlade8RfPortEntry ::= SEQUENCE
    {
     apexRpcBlade8RfPortNum          Integer32,
     apexRpcBlade8RfPortName         DisplayString,
     apexRpcBlade8RfPortServiceGroup Unsigned32
    }

apexRpcBlade8RfPortNum OBJECT-TYPE
    SYNTAX Integer32(1..4)
    MAX-ACCESS not-accessible
    STATUS current
    DESCRIPTION
        "The RF Port number."
::= { apexRpcBlade8RfPortEntry 1 }

apexRpcBlade8RfPortName OBJECT-TYPE
    SYNTAX DisplayString (SIZE (0..64))
    MAX-ACCESS read-write
    STATUS current
    DESCRIPTION
        "The RF Port name.
        
         Once written, the change to this parameter will take immediate
         effect.  In order for the change to persist through subsequent
         reboots or power cycles, the change must be saved via the
         apexSaveConfig parameter.  

         @Config(config=yes, reboot=no)
         @Save(apexSaveConfig, value=2)
         @File(sdvcfg.ini, type='ini')
        "
::= { apexRpcBlade8RfPortEntry 2 }

apexRpcBlade8RfPortServiceGroup OBJECT-TYPE
    SYNTAX Unsigned32(1..4294967295)   
    MAX-ACCESS read-write
    STATUS current
    DESCRIPTION
        "The RF Port service group.
        
         Once written, the change to this parameter will only take immediate
         effect after apexRpcApplyChange is changed to 'apply'.
         In order for the change to persist through subsequent
         reboots or power cycles, the change must be saved via the
         apexSaveConfig parameter.
         
         @Config(config=yes, reboot=no)
         @Commit(param=apexRpcApplyChange , value=2)
         @Save(apexSaveConfig, value=2)
         @File(sdvcfg.ini, type='ini')
        "
::= { apexRpcBlade8RfPortEntry 3 }


-- ------------------------------------------------------------------------------
--
-- apexRpcBlade8RfChannelTable
--

apexRpcBlade8RfChannelTable OBJECT-TYPE
    SYNTAX SEQUENCE OF ApexRpcBlade8RfChannelEntry
    MAX-ACCESS not-accessible
    STATUS current
    DESCRIPTION
        "Table of Configuration data for RPC Session RF Channels.  This variable
         is only used to generate an XML configuration file via the EM.

         Once written, the change to this parameter will take immediate
         effect.  In order for the change to persist through subsequent
         reboots or power cycles, the change must be saved via the
         apexSaveConfig parameter.  

         @Config(config=yes, reboot=no)
         @Save(apexSaveConfig, value=2)
         @File(sdvcfg.ini, type='ini')
        "
::= { apexRpcBlade8Config 2 }

apexRpcBlade8RfChannelEntry OBJECT-TYPE
    SYNTAX ApexRpcBlade8RfChannelEntry 
    MAX-ACCESS not-accessible
    STATUS current
    DESCRIPTION
        "RPC RF Channel Configuration Table Entry."
    INDEX { apexRpcBlade8RfChannelNum }
::= { apexRpcBlade8RfChannelTable 1 }

ApexRpcBlade8RfChannelEntry ::= SEQUENCE
    {
     apexRpcBlade8RfChannelNum   Integer32,
     apexRpcBlade8RfChannelName  DisplayString
    }

apexRpcBlade8RfChannelNum OBJECT-TYPE
    SYNTAX Integer32(1..256)
    MAX-ACCESS not-accessible
    STATUS current
    DESCRIPTION
        "The RF Channel number."
::= { apexRpcBlade8RfChannelEntry 1 }
    
apexRpcBlade8RfChannelName OBJECT-TYPE
    SYNTAX DisplayString (SIZE (0..64))
    MAX-ACCESS read-write
    STATUS current
    DESCRIPTION
        "The name of this RF Channel.
        "
::= { apexRpcBlade8RfChannelEntry 2 }


-- ------------------------------------------------------------------------------
--
-- apexRpcStatus
--
-- apexRpcStatusGeneral
--

-- none


-- ------------------------------------------------------------------------------
--
-- apexRpcSessionStatTable
--

apexRpcSessionStatTable OBJECT-TYPE
    SYNTAX SEQUENCE OF ApexRpcSessionStatEntry
    MAX-ACCESS not-accessible
    STATUS current
    DESCRIPTION
        "Table of RPC Switched Digital Video Session status.  This table
         contains rows for the maximum number of service mappings supported.
        "
::= { apexRpcStatus 2 }

apexRpcSessionStatEntry OBJECT-TYPE
    SYNTAX ApexRpcSessionStatEntry
    MAX-ACCESS not-accessible
    STATUS current
    DESCRIPTION
        "RPC Switched Digital Video Session Status Table Entry."
    INDEX { apexRpcSessionStatBladeNum, apexRpcSessionStatIndex }
::= { apexRpcSessionStatTable 1 }

ApexRpcSessionStatEntry ::= SEQUENCE
    {
     apexRpcSessionStatBladeNum          Integer32,
     apexRpcSessionStatIndex             Integer32,
     apexRpcSessionStatInputTsIndex      Integer32,
     apexRpcSessionStatInputProgramNum   Integer32,
     apexRpcSessionStatSourceIpAddr3     IpAddress,
     apexRpcSessionStatOutputQamChannel  Integer32,
     apexRpcSessionStatOutputProgramNum  Integer32,
     apexRpcSessionStatProgramBandwidth  Integer32,
     apexRpcSessionStatSessionType       INTEGER,
     apexRpcSessionStatSessionIdWord1    Unsigned32,
     apexRpcSessionStatSessionIdWord2    Unsigned32,
     apexRpcSessionStatSessionIdWord3    Unsigned32,
     apexRpcSessionStatManagerIpAddr     IpAddress,
     apexRpcSessionStatCmdOutputPort     Integer32
    }

apexRpcSessionStatBladeNum OBJECT-TYPE
    SYNTAX Integer32(1..8)
    MAX-ACCESS not-accessible
    STATUS current
    DESCRIPTION
        "Blade Number - This is calculated based on the original
         RPC command output port number."
::= { apexRpcSessionStatEntry 1 }

apexRpcSessionStatIndex OBJECT-TYPE
    SYNTAX Integer32(1..2304)
    MAX-ACCESS not-accessible
    STATUS current
    DESCRIPTION
        "The RPC Switched Digital Video Session Status table index.
        "
::= { apexRpcSessionStatEntry 2 }

apexRpcSessionStatInputTsIndex OBJECT-TYPE
    SYNTAX Integer32
    MAX-ACCESS read-only
    STATUS current
    DESCRIPTION
        "The index into the apexGbeStatusInputTsStatTable."
::= { apexRpcSessionStatEntry 3 }

apexRpcSessionStatInputProgramNum OBJECT-TYPE
    SYNTAX Integer32
    MAX-ACCESS read-only
    STATUS current
    DESCRIPTION
        "The Gigabit Ethernet Input Program Number. A value of
         zero (0) indicates that the input is an SPTS and the first
         program listed in the input PAT will be mapped by the APEX.
        "
::= { apexRpcSessionStatEntry 4 }

apexRpcSessionStatSourceIpAddr3 OBJECT-TYPE
    SYNTAX IpAddress
    MAX-ACCESS read-only
    STATUS current
    DESCRIPTION
        "The Gigabit Ethernet IGMP v3 Source IP Address 3.

         This IP address is currently unsupported by the APEX.
        "
::= { apexRpcSessionStatEntry 5 }

apexRpcSessionStatOutputQamChannel OBJECT-TYPE
    SYNTAX Integer32
    MAX-ACCESS read-only
    STATUS current
    DESCRIPTION
        "The logical output transport stream number. This is the output stream
         number within the entire QAM blade. This is calculated based on the original
         RPC command output port number.
        "
::= { apexRpcSessionStatEntry 6 }

apexRpcSessionStatOutputProgramNum OBJECT-TYPE
    SYNTAX Integer32
    MAX-ACCESS read-only
    STATUS current
    DESCRIPTION
        "The Output Program Number (1 - 65535).
        "
::= { apexRpcSessionStatEntry 7 }

apexRpcSessionStatProgramBandwidth OBJECT-TYPE
    SYNTAX Integer32
    MAX-ACCESS read-only
    STATUS current
    DESCRIPTION
        "The Expected Program Bandwidth (bps). This is the bandwidth
         of the program as defined in the service mapping. A value of
         0 indicates that the program BW is unknown.
        "
::= { apexRpcSessionStatEntry 8 }

apexRpcSessionStatSessionType OBJECT-TYPE
    SYNTAX INTEGER
        {
         noSession      (0),
         sdv            (1),
         vodOrBroadcast (2)
        }
    MAX-ACCESS read-only
    STATUS current
    DESCRIPTION
        "The Type of session (SDV binding or VOD/Broadcast session).
         1 = Switched Digital Video (SDV)
         2 = VOD or Broadcast
        "
::= { apexRpcSessionStatEntry 9 }

apexRpcSessionStatSessionIdWord1 OBJECT-TYPE
    SYNTAX Unsigned32
    MAX-ACCESS read-only
    STATUS current
    DESCRIPTION
        "The Session ID Word 1.

         Session IDs are 10 byte character arrays.  Session IDs are
         be stored as 3 4-byte words (3 ulongs) in this MIB. First
         2 Bytes are always 0, next 10 contain the session ID.

         Session ID is broken up as follows:
            Word 1: 00:01 = 0x0000 (unused)
            Word 1: 02:03 = 1st 2 bytes of session ID (1st 2 bytes of MAC address)
            Word 2: 00:03 = Next 4 bytes (these 4 plus 1st 2 are the MAC address of manager)
            Word 3: 00:03 = Last 4 bytes (unique number assigned by manager)
        "
::= { apexRpcSessionStatEntry 10 }

apexRpcSessionStatSessionIdWord2 OBJECT-TYPE
    SYNTAX Unsigned32
    MAX-ACCESS read-only
    STATUS current
    DESCRIPTION
        "The Session ID Word 2.

         Session IDs are 10 byte character arrays.  Session IDs are
         be stored as 3 4-byte words (3 Unsigned32) in this MIB. First
         2 Bytes are always 0, next 10 contain the session ID.

         Session ID is broken up as follows:
            Word 1: 00:01 = 0x0000 (unused)
            Word 1: 02:03 = 1st bytes of session ID (1st 2 bytes of MAC address)
            Word 2: 00:03 = Next 4 bytes (these 4 plus 1st 2 are the MAC address of manager)
            Word 3: 00:03 = Last 4 bytes (unique number assigned by manager)
        "
::= { apexRpcSessionStatEntry 11 }

apexRpcSessionStatSessionIdWord3 OBJECT-TYPE
    SYNTAX Unsigned32
    MAX-ACCESS read-only
    STATUS current
    DESCRIPTION
        "The Session ID Word 3.

         Session IDs are 10 byte character arrays.  Session IDs are
         be stored as 3 4-byte words (3 Unsigned32) in this MIB. First
         2 Bytes are always 0, next 10 contain the session ID.

         Session ID is broken up as follows:
            Word 1: 00:01 = 0x0000 (unused)
            Word 1: 02:03 = 1st bytes of session ID (1st 2 bytes of MAC address)
            Word 2: 00:03 = Next 4 bytes (these 4 plus 1st 2 are the MAC address of manager)
            Word 3: 00:03 = Last 4 bytes (unique number assigned by manager)
        "
::= { apexRpcSessionStatEntry 12 }

apexRpcSessionStatManagerIpAddr OBJECT-TYPE
    SYNTAX IpAddress
    MAX-ACCESS read-only
    STATUS current
    DESCRIPTION
        "The IP address of the RPC SDV, VOD, or Broadcast manager sending session
         commands.
        "
::= { apexRpcSessionStatEntry 13 }

apexRpcSessionStatCmdOutputPort OBJECT-TYPE
    SYNTAX Integer32
    MAX-ACCESS read-only
    STATUS current
    DESCRIPTION
        "The output port number from the original RPC session command. This output
         port is used by the APEX to calculate the APEX QAM blade and logical output
         transport stream number. 
        "
::= { apexRpcSessionStatEntry 14 }


-- ------------------------------------------------------------------------------
--
-- apexRpcQamStatTable
--

apexRpcQamStatTable OBJECT-TYPE
    SYNTAX SEQUENCE OF ApexRpcQamStatEntry
    MAX-ACCESS not-accessible
    STATUS current
    DESCRIPTION
        "Table of RPC Switched Digital Video QAM status.  This table
         is indexed by slot and output stream index.
        "
::= { apexRpcStatus 3 }

apexRpcQamStatEntry OBJECT-TYPE
    SYNTAX ApexRpcQamStatEntry
    MAX-ACCESS not-accessible
    STATUS current
    DESCRIPTION
        "RPC Switched Digital Video QAM Status Table Entry."
    INDEX { apexRpcQamStatQamChannelBladeNum, apexRpcQamStatQamChannelOtsNum }
::= { apexRpcQamStatTable 1 }

ApexRpcQamStatEntry ::= SEQUENCE
    {
     apexRpcQamStatQamChannelBladeNum   Integer32,
     apexRpcQamStatQamChannelOtsNum     Integer32,
     apexRpcQamStatNumSdvSessions       Integer32,
     apexRpcQamStatNumVodBcSessions     Integer32,
     apexRpcQamStatSdvGroupBandwidth    Unsigned32,
     apexRpcQamStatTotalInUseBandwidth  Unsigned32
    }

apexRpcQamStatQamChannelBladeNum OBJECT-TYPE
    SYNTAX Integer32(1..8)
    MAX-ACCESS not-accessible
    STATUS current
    DESCRIPTION
        "Blade Number."
::= { apexRpcQamStatEntry 1 }

apexRpcQamStatQamChannelOtsNum OBJECT-TYPE
    SYNTAX Integer32(1..256)
    MAX-ACCESS not-accessible
    STATUS current
    DESCRIPTION
        "Output Stream Index."
::= { apexRpcQamStatEntry 2 }

apexRpcQamStatNumSdvSessions OBJECT-TYPE
    SYNTAX Integer32
    MAX-ACCESS read-only
    STATUS current
    DESCRIPTION
        "The Number of reserved SDV sessions on this QAM Channel. This is the
         number of SDV sessions that have been reserved by the manager. Each
         SDV session requires that a manager reserve a QAM. This is the count
         of SDV sessions reserved (not the actual number of active SDV sessions).
        "
::= { apexRpcQamStatEntry 3 }

apexRpcQamStatNumVodBcSessions OBJECT-TYPE
    SYNTAX Integer32
    MAX-ACCESS read-only
    STATUS current
    DESCRIPTION
        "The Number of VOD/Broadcast sessions on this QAM Channel. This
         is the number of VOD/Broadcast sessions active on a QAM Channel. Since
         VOD and Broadcast sessions are not required to be reserved for an
         output, this is the count of active VOD and Broadcast sessions on
         a specific QAM.
        "
::= { apexRpcQamStatEntry 4 }

apexRpcQamStatSdvGroupBandwidth OBJECT-TYPE
    SYNTAX Unsigned32
    MAX-ACCESS read-only
    STATUS current
    DESCRIPTION
        "The Group BW for SDV sessions (not used for VOD/Broadcast sessions).
         This is the total amount of BW allocated for all SDV sessions on a channel.
         The total SDV BW for a channel is defined by the session manager. The manager
         reserves this BW for future SDV sessions. This is not the BW of current
         active SDV sessions, but the total BW reserved by the manager for SDV sessions.
        "
::= { apexRpcQamStatEntry 5 }

apexRpcQamStatTotalInUseBandwidth OBJECT-TYPE
    SYNTAX Unsigned32
    MAX-ACCESS read-only
    STATUS current
    DESCRIPTION
        "The total in use bandwidth is the bandwidth reserved for each create session and
         shell binding on a channel. This is not the BW of current
         active SDV sessions, but the total BW reserved by the manager for SDV and 
         VOD/Broadcast sessions.
        "
::= { apexRpcQamStatEntry 6 }


-- ------------------------------------------------------------------------------
--
-- apexRpcSessionInputInfoStatTable
--

apexRpcSessionInputInfoStatTable OBJECT-TYPE
    SYNTAX SEQUENCE OF ApexRpcSessionInputInfoStatEntry
    MAX-ACCESS not-accessible
    STATUS current
    DESCRIPTION
        "Table of Input Info status for RPC Switched Digital Video Sessions.
        "
::= { apexRpcStatus 4 }

apexRpcSessionInputInfoStatEntry OBJECT-TYPE
    SYNTAX ApexRpcSessionInputInfoStatEntry
    MAX-ACCESS not-accessible
    STATUS current
    DESCRIPTION
        "RPC Switched Digital Video Session Input Info Status Table Entry."
    INDEX { apexRpcSessionInputInfoStatBladeNum, apexRpcSessionInputInfoStatIndex }
::= { apexRpcSessionInputInfoStatTable 1 }

ApexRpcSessionInputInfoStatEntry ::= SEQUENCE
    {
     apexRpcSessionInputInfoStatBladeNum  Integer32,
     apexRpcSessionInputInfoStatIndex     Integer32,
     apexRpcSessionInputInfoStatPri       DisplayString,
     apexRpcSessionInputInfoStatSec       DisplayString
    }

apexRpcSessionInputInfoStatBladeNum OBJECT-TYPE
    SYNTAX Integer32(1..8)
    MAX-ACCESS not-accessible
    STATUS current
    DESCRIPTION
        "Blade Number."
::= { apexRpcSessionInputInfoStatEntry 1 }

apexRpcSessionInputInfoStatIndex OBJECT-TYPE
    SYNTAX Integer32(1..2304)
    MAX-ACCESS not-accessible
    STATUS current
    DESCRIPTION
        "The RPC Switched Digital Video Session Input Info Status table index.
        "
::= { apexRpcSessionInputInfoStatEntry 2 }

apexRpcSessionInputInfoStatPri OBJECT-TYPE
    SYNTAX DisplayString
    MAX-ACCESS read-only
    STATUS current
    DESCRIPTION
        "Comma-separated string showing Input Interface, UDP port, 
         Multicast IP, and Source IP of the Primary Input for the session."
::= { apexRpcSessionInputInfoStatEntry 3 }

apexRpcSessionInputInfoStatSec OBJECT-TYPE
    SYNTAX DisplayString
    MAX-ACCESS read-only
    STATUS current
    DESCRIPTION
        "Comma-separated string showing Input Interface, UDP port, 
         Multicast IP, and Source IP of the Secondary Input for the session."
::= { apexRpcSessionInputInfoStatEntry 4 }


-- ------------------------------------------------------------------------------
--
-- apexRpcSetupFailureStatTable
--

apexRpcSetupFailureStatTable OBJECT-TYPE
    SYNTAX SEQUENCE OF ApexRpcSetupFailureStatEntry
    MAX-ACCESS not-accessible
    STATUS current
    DESCRIPTION
        "Table of RPC session setup failures.
        "
::= { apexRpcStatus 5 }

apexRpcSetupFailureStatEntry OBJECT-TYPE
    SYNTAX ApexRpcSetupFailureStatEntry
    MAX-ACCESS not-accessible
    STATUS current
    DESCRIPTION
        "RPC Session Setup Failure Status Table Entry."
    INDEX { apexRpcSetupFailureStatBladeNum }
::= { apexRpcSetupFailureStatTable 1 }

ApexRpcSetupFailureStatEntry ::= SEQUENCE
    {
     apexRpcSetupFailureStatBladeNum  Integer32,
     apexRpcSetupFailureStatCount     Counter32
    }

apexRpcSetupFailureStatBladeNum OBJECT-TYPE
    SYNTAX Integer32(1..8)
    MAX-ACCESS not-accessible
    STATUS current
    DESCRIPTION
        "Blade Number."
::= { apexRpcSetupFailureStatEntry 1 }

apexRpcSetupFailureStatCount OBJECT-TYPE
    SYNTAX Counter32
    MAX-ACCESS read-only
    STATUS current
    DESCRIPTION
        "Number of RPC session setup failures since count last reset. Session
         setup failures include all Shell create failures, binding setup failures,
         and create session edge 1 and 2 failures. Count is currently reset at
         bootup of the APEX."
::= { apexRpcSetupFailureStatEntry 3 }


-- ------------------------------------------------------------------------------
--
-- apexRtsp
--
-- apexRtspConfig
--
-- apexRtspConfigGeneral
--

-- none


-- ------------------------------------------------------------------------------
--
-- apexRtspConfController
--

apexRtspConfControllerApplyChange OBJECT-TYPE
    SYNTAX ApplyDataToDeviceTYPE
    MAX-ACCESS read-write
    STATUS current
    DESCRIPTION
        "The Apply for data in apexRtspConfController.
     

         This parameter MUST be set to 'apply' in order for any of the data
         in apexRtspConfController to take effect in the APEX.  
         This parameter MUST be set LAST after all other data in  
         apexRtspConfController has been configured.
         
         @Config(config=no, reboot=no)
        "
::= { apexRtspConfController 1 }

apexRtspConfControllerIp OBJECT-TYPE
    SYNTAX IpAddress
    MAX-ACCESS read-write
    STATUS current
    DESCRIPTION
        "The IP Address of the RTSP session controller.
         
         @Config(config=yes, reboot=no)
         @Commit(param=apexRtspConfControllerApplyChange, value=2)
         @Save(apexSaveConfig, value=2)
         @File(sdvcfg.ini, type='ini')
        "
::= { apexRtspConfController 2 }

apexRtspConfControllerPort OBJECT-TYPE
    SYNTAX Integer32(1024..65535)
    MAX-ACCESS read-write
    STATUS current
    DESCRIPTION
        "Port for the RTSP session controller.
         
         @Config(config=yes, reboot=no)
         @Commit(param=apexRtspConfControllerApplyChange, value=2)
         @Save(apexSaveConfig, value=2)
         @File(sdvcfg.ini, type='ini')
        "
::= { apexRtspConfController 3 }

apexRtspConfControllerHoldTime OBJECT-TYPE
    SYNTAX Integer32(0 | 9..300)
    MAX-ACCESS read-write
    STATUS current
    DESCRIPTION
        "The session hold time in seconds.  If the APEX does not receive a
         keep session alive message from the controller in this time the
         APEX will close the session.

         The APEX will transmit keep session alive messages at one-third
         of this time.

         Zero indicates that the APEX should not send keep session alive
         messages.
         
         @Config(config=yes, reboot=no)
         @Commit(param=apexRtspConfControllerApplyChange, value=2)
         @Save(apexSaveConfig, value=2)
         @File(sdvcfg.ini, type='ini')
        "
::= { apexRtspConfController 4 }

apexRtspConfControllerBandwidthDelta OBJECT-TYPE
    SYNTAX Integer32(0 | 50..100000)
    MAX-ACCESS read-write
    STATUS current
    DESCRIPTION
        "The Bandwidth Delta, in kilobits per second (kbps), for sending an
         Update Message.

         Whenever a QAM Channel's output utilization changes by more than the
         bandwidth delta, the APEX will send a update message providing the
         current BW being utilized.

         Zero indicates that the APEX should not send update messages based on
         bandwidth changes.

         @Config(config=yes, reboot=no)
         @Commit(param=apexRtspConfControllerApplyChange, value=2)
         @Save(apexSaveConfig, value=2)
         @File(sdvcfg.ini, type='ini')
        "
::= { apexRtspConfController 5 }

apexRtspConfControllerStreamingZone OBJECT-TYPE
    SYNTAX DisplayString (SIZE (0..120))
    MAX-ACCESS read-write
    STATUS current
    DESCRIPTION
        "The streaming zone that the APEX is a member of.

         @Config(config=yes, reboot=no)
         @Commit(param=apexRtspConfControllerApplyChange, value=2)
         @Save(apexSaveConfig, value=2)
         @File(sdvcfg.ini, type='ini')
        "
::= { apexRtspConfController 6 }

apexRtspConfControllerDeviceName OBJECT-TYPE
    SYNTAX DisplayString (SIZE (0..128))
    MAX-ACCESS read-write
    STATUS current
    DESCRIPTION
        "The device name of this APEX.
         
         @Config(config=yes, reboot=no)
         @Commit(param=apexRtspConfControllerApplyChange, value=2)
         @Save(apexSaveConfig, value=2)
         @File(sdvcfg.ini, type='ini')
        "
::= { apexRtspConfController 7 }

apexRtspConfControllerSdvEdgeEncryption OBJECT-TYPE
    SYNTAX EnableDisableTYPE
    MAX-ACCESS read-write
    STATUS current
    DESCRIPTION
        "The enable setting for SDV Edge Encryption.

         @Config(config=yes, reboot=no)
         @Commit(param=apexRtspConfControllerApplyChange, value=2)
         @Save(apexSaveConfig, value=2)
         @File(sdvcfg.ini, type='ini')
        "
::= { apexRtspConfController 8 }

apexRtspConfControllerDefaultServiceProviderId OBJECT-TYPE
    SYNTAX Integer32(0..65535)
    MAX-ACCESS read-write
    STATUS current
    DESCRIPTION
        "The default service provider ID.

         The default service provider ID will be used when there are 
         multiple provider IDs for the same source ID.

         @Config(config=yes, reboot=no)
         @Commit(param=apexRtspConfControllerApplyChange, value=2)
         @Save(apexSaveConfig, value=2)
         @File(sdvcfg.ini, type='ini')
        "
::= { apexRtspConfController 9 }

apexRtspConfControllerDisableAnnounceMsg OBJECT-TYPE
    SYNTAX EnableDisableTYPE
    MAX-ACCESS read-write
    STATUS current
    DESCRIPTION
        "The disable setting for sending RTSP/MHA Announce 
          messages to the ERM.

         @Config(config=yes, reboot=no)
         @Commit(param=apexRtspConfControllerApplyChange, value=2)
         @Save(apexSaveConfig, value=2)
         @File(sdvcfg.ini, type='ini')
        "
::= { apexRtspConfController 10 }

apexRtspConfControllerTeardownSessions OBJECT-TYPE
    SYNTAX INTEGER
        {
         teardownNotInProgress     (1),
         teardownSessions          (2)
        }
    MAX-ACCESS read-write
    STATUS current
    DESCRIPTION
        "When set to teardownSessions(2), this results in the APEX
         removing all of the RTSP/MHA sessions.  After the sessions
         have been torn down the parameter will be set to
         teardownNotInProgress.
         
         Once written, the change to this table will take immediate.

         @Config(config=no, reboot=no)
        "
::= { apexRtspConfController 11 }

apexRtspConfControllerNextHopServerInterface OBJECT-TYPE
    SYNTAX EthernetInterfaceTYPE
    MAX-ACCESS read-write
    STATUS current
    DESCRIPTION
        "The Ethernet interface that will be used when reporting the 
         Next Hop Server IP address to the ERM.
         
         @Config(config=yes, reboot=no)
         @Commit(param=apexRtspConfControllerApplyChange, value=2)
         @Save(apexSaveConfig, value=2)
         @File(sdvcfg.ini, type='ini')
        "
::= { apexRtspConfController 12 }

apexRtspConfControllerVendorName OBJECT-TYPE
    SYNTAX DisplayString (SIZE (0..120))
    MAX-ACCESS read-write
    STATUS current
    DESCRIPTION
        "The vendor name string which is reported to the ERM in the OPEN message.

         @Config(config=yes, reboot=no)
         @Commit(param=apexRtspConfControllerApplyChange, value=2)
         @Save(apexSaveConfig, value=2)
         @File(sdvcfg.ini, type='ini')
        "
::= { apexRtspConfController 13 }

-- ------------------------------------------------------------------------------
--
-- apexRtspConfQamChannelApplyTable
--

apexRtspConfQamChannelApplyTable OBJECT-TYPE
    SYNTAX SEQUENCE OF ApexRtspConfQamChannelApplyEntry
    MAX-ACCESS not-accessible
    STATUS current
    DESCRIPTION
        "Table of Apply Change for the data for apexRtspConfQamChannelTable.

         A row of this table corresponds to a row in apexRtspConfQamChannelTable.
        "
::= { apexRtspConfig 3 }

apexRtspConfQamChannelApplyEntry OBJECT-TYPE
    SYNTAX ApexRtspConfQamChannelApplyEntry
    MAX-ACCESS not-accessible
    STATUS current
    DESCRIPTION
        "RTSP QAM Configuration Apply Table Entry."
    INDEX { apexRtspConfQamChannelApplyBladeNum, apexRtspConfQamChannelApplyOtsNum }
::= { apexRtspConfQamChannelApplyTable 1 }

ApexRtspConfQamChannelApplyEntry ::= SEQUENCE
    {
     apexRtspConfQamChannelApplyBladeNum  Integer32,
     apexRtspConfQamChannelApplyOtsNum    Integer32,
     apexRtspConfQamChannelApplyChange    ApplyDataToDeviceTYPE
    }

apexRtspConfQamChannelApplyBladeNum OBJECT-TYPE
    SYNTAX Integer32(1..8)
    MAX-ACCESS not-accessible
    STATUS current
    DESCRIPTION
        "Blade Number."
::= { apexRtspConfQamChannelApplyEntry 1 }

apexRtspConfQamChannelApplyOtsNum OBJECT-TYPE
    SYNTAX Integer32(1..256)
    MAX-ACCESS not-accessible
    STATUS current
    DESCRIPTION
        "Output Stream Index."
::= { apexRtspConfQamChannelApplyEntry 2 }

apexRtspConfQamChannelApplyChange OBJECT-TYPE
    SYNTAX ApplyDataToDeviceTYPE
    MAX-ACCESS read-write
    STATUS current
    DESCRIPTION
        "The Apply for a row of data in apexRtspConfQamChannelTable.

         A row in this table corresponds to the same row index in the
         apexRtspConfQamChannelTable.

         This parameter MUST be set to 'apply' in order for any of the data
         in the rows to take effect in the APEX.  This parameter MUST be set
         LAST after all other data in the configuration table rows has been
         configured.

         @Config(config=no, reboot=no)
        "
::= { apexRtspConfQamChannelApplyEntry 3 }


-- ------------------------------------------------------------------------------
--
-- apexRtspConfQamChannelTable
--

apexRtspConfQamChannelTable OBJECT-TYPE
    SYNTAX SEQUENCE OF ApexRtspConfQamChannelEntry
    MAX-ACCESS not-accessible
    STATUS current
    DESCRIPTION
        "Table of Configuration data for RTSP Session QAM Channels.

         Once written, the change to this table will only take immediate
         effect after apexRtspConfQamChannelApplyChange to 'apply'.  In
         order for the change to persist through subsequent reboots or power
         cycles, the change must be saved via the apexSaveConfig parameter.

         @Config(config=yes, reboot=no)
         @Commit(param=apexRtspConfQamChannelApplyChange , value=2)
         @Save(apexSaveConfig, value=2)
         @File(sdvcfg.ini, type='ini')
        "
::= { apexRtspConfig 4 }

apexRtspConfQamChannelEntry OBJECT-TYPE
    SYNTAX ApexRtspConfQamChannelEntry
    MAX-ACCESS not-accessible
    STATUS current
    DESCRIPTION
        "RTSP QAM Configuration Table Entry."
    INDEX { apexRtspConfQamChannelBladeNum, apexRtspConfQamChannelOtsNum }
::= { apexRtspConfQamChannelTable 1 }

ApexRtspConfQamChannelEntry ::= SEQUENCE
    {
     apexRtspConfQamChannelBladeNum     Integer32,
     apexRtspConfQamChannelOtsNum       Integer32,
     apexRtspConfQamChannelGroupName    DisplayString
    }

apexRtspConfQamChannelBladeNum OBJECT-TYPE
    SYNTAX Integer32(1..8)
    MAX-ACCESS not-accessible
    STATUS current
    DESCRIPTION
        "Blade Number."
::= { apexRtspConfQamChannelEntry 1 }

apexRtspConfQamChannelOtsNum OBJECT-TYPE
    SYNTAX Integer32(1..256)
    MAX-ACCESS not-accessible
    STATUS current
    DESCRIPTION
        "Output Stream Index."
::= { apexRtspConfQamChannelEntry 2 }

apexRtspConfQamChannelGroupName OBJECT-TYPE
    SYNTAX DisplayString (SIZE (0..128))
    MAX-ACCESS read-write
    STATUS current
    DESCRIPTION
        "The QAM Group Name that this QAM Channel is a member of.
        "
::= { apexRtspConfQamChannelEntry 3 }


-- ------------------------------------------------------------------------------
--
-- apexRtspConfGbeEdgeGroupTable
--

apexRtspConfGbeEdgeGroupTable OBJECT-TYPE
    SYNTAX SEQUENCE OF ApexRtspConfGbeEdgeGroupEntry
    MAX-ACCESS not-accessible
    STATUS current
    DESCRIPTION
        "Table of Configuration data for RTSP Session GigE Interfaces.

         Once written, the change to this table will take immediate
         effect.  In order for the change to persist through subsequent reboots
         or power cycles, the change must be saved via the apexSaveConfig parameter.

         @Config(config=yes, reboot=no)
         @Save(apexSaveConfig, value=2)
         @File(sdvcfg.ini, type='ini')
        "
::= { apexRtspConfig 5 }

apexRtspConfGbeEdgeGroupEntry OBJECT-TYPE
    SYNTAX ApexRtspConfGbeEdgeGroupEntry
    MAX-ACCESS not-accessible
    STATUS current
    DESCRIPTION
        "RTSP GigE Edge Group Configuration Table Entry."
    INDEX { apexRtspConfGbeEdgeGroupNum }
::= { apexRtspConfGbeEdgeGroupTable 1 }

ApexRtspConfGbeEdgeGroupEntry ::= SEQUENCE
    {
     apexRtspConfGbeEdgeGroupNum   Integer32,
     apexRtspConfGbeEdgeGroupName  DisplayString
    }

apexRtspConfGbeEdgeGroupNum OBJECT-TYPE
    SYNTAX Integer32(1..12)
    MAX-ACCESS not-accessible
    STATUS current
    DESCRIPTION
        "The GigE Edge Group Interface number."
::= { apexRtspConfGbeEdgeGroupEntry 1 }

apexRtspConfGbeEdgeGroupName OBJECT-TYPE
    SYNTAX DisplayString (SIZE (0..128))
    MAX-ACCESS read-write
    STATUS current
    DESCRIPTION
        "The Name of this GigE Interface.
        "
::= { apexRtspConfGbeEdgeGroupEntry 2 }


-- ------------------------------------------------------------------------------
--
-- apexRtspConfMha
--

apexRtspConfMhaAddressDomain OBJECT-TYPE
    SYNTAX Integer32(0..255)
    MAX-ACCESS read-write
    STATUS current
    DESCRIPTION
        "Address Domain of the sender used in ERRP.  Address Domain of the
         ERM and APEX must match in order to establish an ERRP connection.
         Zero is used as the global address domain, which is interpreted to
         mean that any advertised address can be reached from any address
         domain.
         
         @Config(config=yes, reboot=no)
         @Commit(param=apexRtspConfControllerApplyChange, value=2)
         @Save(apexSaveConfig, value=2)
         @File(sdvcfg.ini, type='ini')
        "
::= { apexRtspConfMha 1 }

apexRtspConfMhaPort OBJECT-TYPE
    SYNTAX Integer32(1024..65535)
    MAX-ACCESS read-write
    STATUS current
    DESCRIPTION
        "Port for the MHA session controller.
        
         @Config(config=yes, reboot=no)
         @Commit(param=apexRtspConfControllerApplyChange, value=2)
         @Save(apexSaveConfig, value=2)
         @File(sdvcfg.ini, type='ini')
        "
::= { apexRtspConfMha 2 }


-- ------------------------------------------------------------------------------
--
-- apexRtspConfMhaSbe
--

apexRtspConfMhaSbeEncryptionMode OBJECT-TYPE
    SYNTAX INTEGER
    {
         full               (1),
         fwk                (2),
         fpk                (3)
    }
    MAX-ACCESS read-write
    STATUS current
    DESCRIPTION
        "This parameter is used to set the Session based Encryption Mode.  
         It applies to all session based encryption sessions.

           - 'full'  - The APEX will use Full encryption. 
           
           - 'fwk'   - The APEX will use Fixed Working Key (FWK) encryption.

           - 'fpk'   - The APEX will use Fixed Program Key (FPK) encryption. The APEX
                       will not attempt to get EMMs.

         Once written, the change to this parameter will only take immediate
         effect after apexRtspConfMhaSbeApplyChange is set to 'apply'.  In
         order for the change to persist through subsequent reboots or power
         cycles, the change must be saved via the apexSaveConfig parameter.

         @Config(config=yes, reboot=no)
         @Commit(param=apexRtspConfMhaSbeApplyChange, value=2)
         @Save(apexSaveConfig, value=2)
         @File(sdvcfg.ini, type='ini')
        "
::= { apexRtspConfMhaSbe 1 }

apexRtspConfMhaSbeCciLevel OBJECT-TYPE
    SYNTAX INTEGER
        {
         notDefined   (1),
         copyFreely   (2),
         copyOnce     (3),
         copyNever    (4),
         noMoreCopies (5)
        }
    MAX-ACCESS read-write
    STATUS current
    DESCRIPTION
        "Copy Control Information (CCI) Level setting for session based PRK messages
         if CCI is not defined in the XML encryption blob.
           - notDefined   - CCI is not defined, settop box applications can
                            configure CCI
           - copyFreely   - program can be copied
           - copyOnce     - program can be copied once
           - copyNever    - program can never be copied
           - noMoreCopies -

         Once written, the change to this parameter will only take immediate
         effect after apexRtspConfMhaSbeApplyChange is set to 'apply'.  In
         order for the change to persist through subsequent reboots or power
         cycles, the change must be saved via the apexSaveConfig parameter.

         @Config(config=yes, reboot=no)
         @Commit(param=apexRtspConfMhaSbeApplyChange, value=2)
         @Save(apexSaveConfig, value=2)
         @File(sdvcfg.ini, type='ini')
        "
::= { apexRtspConfMhaSbe 2 }

apexRtspConfMhaSbeApsLevel OBJECT-TYPE
    SYNTAX INTEGER
        {
         notDefined      (1),
         off             (2),
         splitBurstOff   (3),
         splitBurst2Line (4),
         splitBurst4Line (5)
        }
    MAX-ACCESS read-write
    STATUS current
    DESCRIPTION
        "Analog Protection System (APS) Level setting for session based PRK 
         messages if APS is not defined in the XML encryption blob.  
         Defines what copy protection encoding will be applied to the analog 
         composite output by the settop box.
           - notDefined      - analog protection is not defined, settop box
                               applications can configure APS
           - off             - no analog protection
           - splitBurstOff   - AGC on, split burst off
           - splitBurst2Line - AGC on, 2 line split burst on
           - splitBurst4Line - AGC on, 4 line split burst on

         Once written, the change to this parameter will only take immediate
         effect after apexRtspConfMhaSbeApplyChange is set to 'apply'.  In
         order for the change to persist through subsequent reboots or power
         cycles, the change must be saved via the apexSaveConfig parameter.

         @Config(config=yes, reboot=no)
         @Commit(param=apexRtspConfMhaSbeApplyChange, value=2)
         @Save(apexSaveConfig, value=2)
         @File(sdvcfg.ini, type='ini')
        "
::= { apexRtspConfMhaSbe 3 }

apexRtspConfMhaSbeCitSetting OBJECT-TYPE
    SYNTAX INTEGER
        {
         disabled      (1),
         enabled       (2)
        }
    MAX-ACCESS read-write
    STATUS current
    DESCRIPTION
        "Copy protection Constraint Image Trigger setting. This is only
         applicable when the session is being encrypted and the CIT setting
         was not contained in the XML encryption blob.
         
         Once written, the change to this parameter will only take immediate
         effect after apexRtspConfMhaSbeApplyChange is set to 'apply'.  In
         order for the change to persist through subsequent reboots or power
         cycles, the change must be saved via the apexSaveConfig parameter.
         
         @Config(config=yes, reboot=no)
         @Commit(param=apexRtspConfMhaSbeApplyChange, value=2)
         @Save(apexSaveConfig, value=2)
         @File(sdvcfg.ini, type='ini')
        "
::= { apexRtspConfMhaSbe 4 }

apexRtspConfMhaSbeApplyChange OBJECT-TYPE
    SYNTAX ApplyDataToDeviceTYPE
    MAX-ACCESS read-write
    STATUS current
    DESCRIPTION
        "The Apply for the MHA session based encryption settings.

         This parameter MUST be set to 'apply' in order for any of the data
         in MHA SBE to take effect in the APEX.  This parameter MUST be set 
         LAST after all other data in the MHA SBE has been configured.

         @Config(config=no, reboot=no)
        "
::= { apexRtspConfMhaSbe 5 }


-- ------------------------------------------------------------------------------
--
-- apexRtspStatus
--
-- apexRtspStatusGeneral
--

apexRtspStatusSetupRequestRate OBJECT-TYPE
    SYNTAX Integer32
    MAX-ACCESS read-write
    STATUS current
    DESCRIPTION
        "The average number of RTSP/MHA setup request messages received per second 
         over the last 5 seconds from the ERM.
        "
::= { apexRtspStatusGeneral 1 }

apexRtspStatusTeardownRate OBJECT-TYPE
    SYNTAX Integer32
    MAX-ACCESS read-write
    STATUS current
    DESCRIPTION
        "The average number of RTSP/MHA teardown request messages received per second 
         over the last 5 seconds from the ERM.
        "
::= { apexRtspStatusGeneral 2 }

apexRtspStatusAnnounceRequestRate OBJECT-TYPE
    SYNTAX Integer32
    MAX-ACCESS read-write
    STATUS current
    DESCRIPTION
        "The average number of RTSP/MHA announce request messages sent per second 
         over the last 5 seconds to the ERM.
        "
::= { apexRtspStatusGeneral 3 }

apexRtspStatusAckRate OBJECT-TYPE
    SYNTAX Integer32
    MAX-ACCESS read-write
    STATUS current
    DESCRIPTION
        "The average number of RTSP/MHA acknowledge messages processed per second 
         over the last 5 seconds.  Acknowledge messages can be sent to the ERM or
         received from the ERM.
        "
::= { apexRtspStatusGeneral 4 }

apexRtspStatusSessionCount OBJECT-TYPE
    SYNTAX Integer32
    MAX-ACCESS read-write
    STATUS current
    DESCRIPTION
        "The total number of sessions that are currently active on the APEX.  The
         variable is updated once every 5 seconds.
        "
::= { apexRtspStatusGeneral 5 }


-- ------------------------------------------------------------------------------
--
-- apexRtspSessionStatTable
--

apexRtspSessionStatTable OBJECT-TYPE
    SYNTAX SEQUENCE OF ApexRtspSessionStatEntry
    MAX-ACCESS not-accessible
    STATUS current
    DESCRIPTION
        "Table of RTSP Session status.
        "
::= { apexRtspStatus 2 }

apexRtspSessionStatEntry OBJECT-TYPE
    SYNTAX ApexRtspSessionStatEntry
    MAX-ACCESS not-accessible
    STATUS current
    DESCRIPTION
        "RTSP Session Status Table Entry."
    INDEX { apexRtspSessionStatBladeNum, apexRtspSessionStatIndex }
::= { apexRtspSessionStatTable 1 }

ApexRtspSessionStatEntry ::= SEQUENCE
    {
     apexRtspSessionStatBladeNum         Integer32,
     apexRtspSessionStatIndex            Integer32,
     apexRtspSessionStatInputTsIndex     Integer32,
     apexRtspSessionStatInputProgramNum  Integer32,
     apexRtspSessionStatOutputQamChannel Integer32,
     apexRtspSessionStatOutputProgramNum Integer32,
     apexRtspSessionStatProgramBandwidth Integer32,
     apexRtspSessionStatManagerIpAddr    IpAddress
    }

apexRtspSessionStatBladeNum OBJECT-TYPE
    SYNTAX Integer32(1..8)
    MAX-ACCESS not-accessible
    STATUS current
    DESCRIPTION
        "Blade Number."
::= { apexRtspSessionStatEntry 1 }

apexRtspSessionStatIndex OBJECT-TYPE
    SYNTAX Integer32(1..2304)
    MAX-ACCESS not-accessible
    STATUS current
    DESCRIPTION
        "The RTSP Session Status table index.
        "
::= { apexRtspSessionStatEntry 2 }

apexRtspSessionStatInputTsIndex OBJECT-TYPE
    SYNTAX Integer32
    MAX-ACCESS read-only
    STATUS current
    DESCRIPTION
        "The index into the apexGbeStatusInputTsStatTable."
::= { apexRtspSessionStatEntry 3 }

apexRtspSessionStatInputProgramNum OBJECT-TYPE
    SYNTAX Integer32
    MAX-ACCESS read-only
    STATUS current
    DESCRIPTION
        "The Gigabit Ethernet Input Program Number. A value of
         zero (0) indicates that the input is an SPTS and the first
         program listed in the input PAT will be mapped by the APEX.
        "
::= { apexRtspSessionStatEntry 4 }

apexRtspSessionStatOutputQamChannel OBJECT-TYPE
    SYNTAX Integer32
    MAX-ACCESS read-only
    STATUS current
    DESCRIPTION
        "The Output QAM Channel.
        "
::= { apexRtspSessionStatEntry 5 }

apexRtspSessionStatOutputProgramNum OBJECT-TYPE
    SYNTAX Integer32
    MAX-ACCESS read-only
    STATUS current
    DESCRIPTION
        "The Output Program Number.
        "
::= { apexRtspSessionStatEntry 6 }

apexRtspSessionStatProgramBandwidth OBJECT-TYPE
    SYNTAX Integer32
    MAX-ACCESS read-only
    STATUS current
    DESCRIPTION
        "The Expected Program Bandwidth (bps). This is the bandwidth
         of the program as defined in the service mapping. A value of
         0 indicates that the program BW is unknown.
        "
::= { apexRtspSessionStatEntry 7 }

apexRtspSessionStatManagerIpAddr OBJECT-TYPE
    SYNTAX IpAddress
    MAX-ACCESS read-only
    STATUS current
    DESCRIPTION
        "The IP address of the manager sending session commands.
        "
::= { apexRtspSessionStatEntry 8 }


-- ------------------------------------------------------------------------------
--
-- apexRtspSessionIdTable
--

apexRtspSessionIdTable OBJECT-TYPE
    SYNTAX SEQUENCE OF ApexRtspSessionIdEntry
    MAX-ACCESS not-accessible
    STATUS current
    DESCRIPTION
        "Table of RTSP Session Ids.  This table is a row-for-row index
         match to apexRtspSessionStatTable.
        "
::= { apexRtspStatus 3 }

apexRtspSessionIdEntry OBJECT-TYPE
    SYNTAX ApexRtspSessionIdEntry
    MAX-ACCESS not-accessible
    STATUS current
    DESCRIPTION
        "RTSP Session ID Table Entry."
    INDEX { apexRtspSessionIdBladeNum, apexRtspSessionIdIndex }
::= { apexRtspSessionIdTable 1 }

ApexRtspSessionIdEntry ::= SEQUENCE
    {
     apexRtspSessionIdBladeNum  Integer32,
     apexRtspSessionIdIndex     Integer32,
     apexRtspSessionId          DisplayString
    }

apexRtspSessionIdBladeNum OBJECT-TYPE
    SYNTAX Integer32(1..8)
    MAX-ACCESS not-accessible
    STATUS current
    DESCRIPTION
        "Blade Number."
::= { apexRtspSessionIdEntry 1 }

apexRtspSessionIdIndex OBJECT-TYPE
    SYNTAX Integer32(1..2304)
    MAX-ACCESS not-accessible
    STATUS current
    DESCRIPTION
        "The RTSP Session ID table index.
         This is a row-for-row match to the
         RTSP Session Status table index.
        "
::= { apexRtspSessionIdEntry 2 }

apexRtspSessionId OBJECT-TYPE
    SYNTAX DisplayString (SIZE (0..64))
    MAX-ACCESS read-only
    STATUS current
    DESCRIPTION
        "The Session ID.
        "
::= { apexRtspSessionIdEntry 3 }


-- ------------------------------------------------------------------------------
--
-- apexRtspQamStatTable
--

apexRtspQamStatTable OBJECT-TYPE
    SYNTAX SEQUENCE OF ApexRtspQamStatEntry
    MAX-ACCESS not-accessible
    STATUS current
    DESCRIPTION
        "Table of RTSP Session QAM status.  This table
         is indexed by slot and output stream index.
        "
::= { apexRtspStatus 4 }

apexRtspQamStatEntry OBJECT-TYPE
    SYNTAX ApexRtspQamStatEntry
    MAX-ACCESS not-accessible
    STATUS current
    DESCRIPTION
        "RTSP Session QAM status Table Entry."
    INDEX { apexRtspQamStatQamChannelBladeNum, apexRtspQamStatQamChannelOtsNum }
::= { apexRtspQamStatTable 1 }

ApexRtspQamStatEntry ::= SEQUENCE
    {
     apexRtspQamStatQamChannelBladeNum  Integer32,
     apexRtspQamStatQamChannelOtsNum    Integer32,
     apexRtspQamStatNumSessions         Integer32,
     apexRtspQamStatAllocatedBandwidth  Unsigned32
    }

apexRtspQamStatQamChannelBladeNum OBJECT-TYPE
    SYNTAX Integer32(1..8)
    MAX-ACCESS not-accessible
    STATUS current
    DESCRIPTION
        "Blade Number."
::= { apexRtspQamStatEntry 1 }

apexRtspQamStatQamChannelOtsNum OBJECT-TYPE
    SYNTAX Integer32(1..256)
    MAX-ACCESS not-accessible
    STATUS current
    DESCRIPTION
        "Output Stream Index."
::= { apexRtspQamStatEntry 2 }

apexRtspQamStatNumSessions OBJECT-TYPE
    SYNTAX Integer32
    MAX-ACCESS read-only
    STATUS current
    DESCRIPTION
        "The Number of active sessions on this QAM Channel.
        "
::= { apexRtspQamStatEntry 3 }

apexRtspQamStatAllocatedBandwidth OBJECT-TYPE
    SYNTAX Unsigned32
    MAX-ACCESS read-only
    STATUS current
    DESCRIPTION
        "This is the total amount of BW allocated for all sessions on a channel.
        "
::= { apexRtspQamStatEntry 4 }


-- ------------------------------------------------------------------------------
--
-- apexRtspStatController
--

apexRtspStatControllerDiscovery OBJECT-TYPE
    SYNTAX INTEGER
        {
         notApplicable            (0),
         notDiscovered            (1),
         discovered               (2),
         discoveredConnectionLost (3)
        }
    MAX-ACCESS read-only
    STATUS current
    DESCRIPTION
        "Status of Controller to APEX discovery.
        "
::= { apexRtspStatController 1 }

apexRtspStatControllerConnection OBJECT-TYPE
    SYNTAX INTEGER
        {
         notApplicable     (0),
         notConnected      (1),
         connected         (2)
        }
    MAX-ACCESS read-only
    STATUS current
    DESCRIPTION
        "Status of the connection between the APEX and the Controller.

         'notConnected' causes apexAlarmRtspControllerCommFault.
        "
::= { apexRtspStatController 2 }

apexRtspStatControllerCommFault OBJECT-TYPE
    SYNTAX INTEGER
        {
         ok(1),
         indeterminate(2),
         warning(3),
         minor(4),
         major(5),
         critical(6)
        }
    MAX-ACCESS read-only
    STATUS current
    DESCRIPTION
        "Current fault condition of apexRtspStatControllerConnection.

         This is the apexAlarmRtspControllerCommFault level for this controller.
        "
::= { apexRtspStatController 3 }


-- ------------------------------------------------------------------------------
--
-- apexRtspStatQamChannelTable
--

apexRtspStatQamChannelTable OBJECT-TYPE
    SYNTAX SEQUENCE OF ApexRtspStatQamChannelEntry
    MAX-ACCESS not-accessible
    STATUS current
    DESCRIPTION
        "Table of Status data for RTSP Session QAM Channels.
        "
::= { apexRtspStatus 6 }

apexRtspStatQamChannelEntry OBJECT-TYPE
    SYNTAX ApexRtspStatQamChannelEntry
    MAX-ACCESS not-accessible
    STATUS current
    DESCRIPTION
        "RTSP QAM Configuration Table Entry."
    INDEX { apexRtspStatQamChannelBladeNum, apexRtspStatQamChannelOtsNum }
::= { apexRtspStatQamChannelTable 1 }

ApexRtspStatQamChannelEntry ::= SEQUENCE
    {
     apexRtspStatQamChannelBladeNum     Integer32,
     apexRtspStatQamChannelOtsNum       Integer32,
     apexRtspStatQamChannelName         DisplayString
    }

apexRtspStatQamChannelBladeNum OBJECT-TYPE
    SYNTAX Integer32(1..8)
    MAX-ACCESS not-accessible
    STATUS current
    DESCRIPTION
        "Blade Number."
::= { apexRtspStatQamChannelEntry 1 }

apexRtspStatQamChannelOtsNum OBJECT-TYPE
    SYNTAX Integer32(1..256)
    MAX-ACCESS not-accessible
    STATUS current
    DESCRIPTION
        "Output Stream Index."
::= { apexRtspStatQamChannelEntry 2 }

apexRtspStatQamChannelName OBJECT-TYPE
    SYNTAX DisplayString (SIZE (0..128))
    MAX-ACCESS read-only
    STATUS current
    DESCRIPTION
        "The Name of this QAM Channel.
        "
::= { apexRtspStatQamChannelEntry 3 }


-- ------------------------------------------------------------------------------
--
-- apexRtspStatQamMptsModeTable
--

apexRtspStatQamMptsModeTable OBJECT-TYPE
    SYNTAX SEQUENCE OF ApexRtspStatQamMptsModeEntry
    MAX-ACCESS not-accessible
    STATUS current
    DESCRIPTION
        "Table of MPTS Mode Status data for RTSP Session QAM Channels.
        "
::= { apexRtspStatus 7 }

apexRtspStatQamMptsModeEntry OBJECT-TYPE
    SYNTAX ApexRtspStatQamMptsModeEntry
    MAX-ACCESS not-accessible
    STATUS current
    DESCRIPTION
        "RTSP QAM MPTS Mode Configuration Table Entry."
    INDEX { apexRtspStatQamMptsModeBladeNum, apexRtspStatQamMptsModeOtsNum }
::= { apexRtspStatQamMptsModeTable 1 }

ApexRtspStatQamMptsModeEntry ::= SEQUENCE
    {
     apexRtspStatQamMptsModeBladeNum        Integer32,
     apexRtspStatQamMptsModeOtsNum          Integer32,
     apexRtspStatQamMptsModeQamChannelMode  INTEGER
    }

apexRtspStatQamMptsModeBladeNum OBJECT-TYPE
    SYNTAX Integer32(1..8)
    MAX-ACCESS not-accessible
    STATUS current
    DESCRIPTION
        "Blade Number."
::= { apexRtspStatQamMptsModeEntry 1 }

apexRtspStatQamMptsModeOtsNum OBJECT-TYPE
    SYNTAX Integer32(1..256)
    MAX-ACCESS not-accessible
    STATUS current
    DESCRIPTION
        "Output Stream Index."
::= { apexRtspStatQamMptsModeEntry 2 }

apexRtspStatQamMptsModeQamChannelMode OBJECT-TYPE
    SYNTAX INTEGER
        {
         notApplicable     (0),
         passthrough       (1),
         multiplexing      (2)
        }
    MAX-ACCESS read-only
    STATUS current
    DESCRIPTION
        "The MPTS mode of this QAM Channel.  The first session
         established on the QAM channel defines the
         MPTS mode.  Each new session must have the same
         mode as long as one session is still active.
        "
::= { apexRtspStatQamMptsModeEntry 3 }


-- ------------------------------------------------------------------------------
--
-- apexRtspSessionInputInfoStatTable
--

apexRtspSessionInputInfoStatTable OBJECT-TYPE
    SYNTAX SEQUENCE OF ApexRtspSessionInputInfoStatEntry
    MAX-ACCESS not-accessible
    STATUS current
    DESCRIPTION
        "Table of Input Info status for RTSP Sessions.  This table
         is a row-for-row index match to apexRtspSessionStatTable.
        "
::= { apexRtspStatus 8 }

apexRtspSessionInputInfoStatEntry OBJECT-TYPE
    SYNTAX ApexRtspSessionInputInfoStatEntry
    MAX-ACCESS not-accessible
    STATUS current
    DESCRIPTION
        "RTSP Session Input Info Status Table Entry."
    INDEX { apexRtspSessionInputInfoStatBladeNum,
            apexRtspSessionInputInfoStatIndex }
::= { apexRtspSessionInputInfoStatTable 1 }

ApexRtspSessionInputInfoStatEntry ::= SEQUENCE
    {
     apexRtspSessionInputInfoStatBladeNum  Integer32,
     apexRtspSessionInputInfoStatIndex     Integer32,
     apexRtspSessionInputInfoStatPri       DisplayString,
     apexRtspSessionInputInfoStatSec       DisplayString
    }

apexRtspSessionInputInfoStatBladeNum OBJECT-TYPE
    SYNTAX Integer32(1..8)
    MAX-ACCESS not-accessible
    STATUS current
    DESCRIPTION
        "Blade Number."
::= { apexRtspSessionInputInfoStatEntry 1 }

apexRtspSessionInputInfoStatIndex OBJECT-TYPE
    SYNTAX Integer32(1..2304)
    MAX-ACCESS not-accessible
    STATUS current
    DESCRIPTION
        "The RTSP Session Input Info Status table index.
        "
::= { apexRtspSessionInputInfoStatEntry 2 }

apexRtspSessionInputInfoStatPri OBJECT-TYPE
    SYNTAX DisplayString
    MAX-ACCESS read-only
    STATUS current
    DESCRIPTION
        "Comma-separated string showing Input Interface, UDP port, 
         Multicast IP, and Source IP of the Primary Input for the session."
::= { apexRtspSessionInputInfoStatEntry 3 }

apexRtspSessionInputInfoStatSec OBJECT-TYPE
    SYNTAX DisplayString
    MAX-ACCESS read-only
    STATUS current
    DESCRIPTION
        "Comma-separated string showing Input Interface, UDP port, 
         Multicast IP, and Source IP of the Secondary Input for the session."
::= { apexRtspSessionInputInfoStatEntry 4 }


-- ------------------------------------------------------------------------------
--
-- apexRtspStatBwReportedTable
--

apexRtspStatBwReportedTable OBJECT-TYPE
    SYNTAX SEQUENCE OF ApexRtspStatBwReportedEntry
    MAX-ACCESS not-accessible
    STATUS current
    DESCRIPTION
        "Table of Bandwidth reported status for Gbe interface.
        "
::= { apexRtspStatus 9 }

apexRtspStatBwReportedEntry OBJECT-TYPE
    SYNTAX ApexRtspStatBwReportedEntry
    MAX-ACCESS not-accessible
    STATUS current
    DESCRIPTION
        "RTSP Status Bandwidth Reported Table Entry."
    INDEX { apexRtspStatBwReportedGbePortNum }
::= { apexRtspStatBwReportedTable 1 }

ApexRtspStatBwReportedEntry ::= SEQUENCE
    {
     apexRtspStatBwReportedGbePortNum      Integer32,
     apexRtspStatBwReportedAvailableBw     Integer32,
     apexRtspStatBwReportedSentToErm       Integer32,
     apexRtspStatBwReportedRsrvUdpMap      Integer32,
     apexRtspStatBwReportedRsrvRpcOnly     Integer32,
     apexRtspStatBwReportedRsrvDepiMap     Integer32
    }

apexRtspStatBwReportedGbePortNum OBJECT-TYPE
    SYNTAX Integer32(1..12)
    MAX-ACCESS not-accessible
    STATUS current
    DESCRIPTION
        "Gbe Port Number."
::= { apexRtspStatBwReportedEntry 1 }

apexRtspStatBwReportedAvailableBw OBJECT-TYPE
    SYNTAX Integer32
    MAX-ACCESS read-only
    STATUS current
    DESCRIPTION
        "The total available bandwidth on the interface in kbps.
        "
::= { apexRtspStatBwReportedEntry 2 }

apexRtspStatBwReportedSentToErm OBJECT-TYPE
    SYNTAX Integer32
    MAX-ACCESS read-only
    STATUS current
    DESCRIPTION
        "The interface bandwidth reported to the ERM in kbps.
        "
::= { apexRtspStatBwReportedEntry 3 }

apexRtspStatBwReportedRsrvUdpMap OBJECT-TYPE
    SYNTAX Integer32
    MAX-ACCESS read-only
    STATUS current
    DESCRIPTION
        "The bandwidth in kbps that was reserved for UDP Port Mappings.
        "
::= { apexRtspStatBwReportedEntry 4 }

apexRtspStatBwReportedRsrvRpcOnly OBJECT-TYPE
    SYNTAX Integer32
    MAX-ACCESS read-only
    STATUS current
    DESCRIPTION
        "The bandwidth in kbps that was reserved for RPC mappings.
        "
::= { apexRtspStatBwReportedEntry 5 }

apexRtspStatBwReportedRsrvDepiMap OBJECT-TYPE
    SYNTAX Integer32
    MAX-ACCESS read-only
    STATUS current
    DESCRIPTION
        "The bandwidth in kbps that was reserved for DEPI mappings.
        "
::= { apexRtspStatBwReportedEntry 6 }


-- ------------------------------------------------------------------------------
--
-- apexRtspStatBladeBwTable
--

apexRtspStatBladeBwTable OBJECT-TYPE
    SYNTAX SEQUENCE OF ApexRtspStatBladeBwEntry
    MAX-ACCESS not-accessible
    STATUS current
    DESCRIPTION
        "Table of Bandwidth currently being sent to each blade.
        "
::= { apexRtspStatus 10 }

apexRtspStatBladeBwEntry OBJECT-TYPE
    SYNTAX ApexRtspStatBladeBwEntry
    MAX-ACCESS not-accessible
    STATUS current
    DESCRIPTION
        "RTSP Status Blade Bandwidth Table Entry."
    INDEX { apexRtspStatBladeBwBladeNum }
::= { apexRtspStatBladeBwTable 1 }

ApexRtspStatBladeBwEntry ::= SEQUENCE
    {
     apexRtspStatBladeBwBladeNum        Integer32,
     apexRtspStatBladeBwManualRoute     Integer32,
     apexRtspStatBladeBwUdpMap          Integer32,
     apexRtspStatBladeBwSdvMap          Integer32,
     apexRtspStatBladeBwTotal           Integer32,
     apexRtspStatBladeBwDepiMap         Integer32
    }

apexRtspStatBladeBwBladeNum OBJECT-TYPE
    SYNTAX Integer32(1..8)
    MAX-ACCESS not-accessible
    STATUS current
    DESCRIPTION
        "Blade Number."
::= { apexRtspStatBladeBwEntry 1 }

apexRtspStatBladeBwManualRoute OBJECT-TYPE
    SYNTAX Integer32
    MAX-ACCESS read-only
    STATUS current
    DESCRIPTION
        "The total bandwidth allocated for manual route mappings in mbps on blade.
        "
::= { apexRtspStatBladeBwEntry 2 }

apexRtspStatBladeBwUdpMap OBJECT-TYPE
    SYNTAX Integer32
    MAX-ACCESS read-only
    STATUS current
    DESCRIPTION
        "The total bandwidth allocated for UDP mappings in mbps on blade.
        "
::= { apexRtspStatBladeBwEntry 3 }

apexRtspStatBladeBwSdvMap OBJECT-TYPE
    SYNTAX Integer32
    MAX-ACCESS read-only
    STATUS current
    DESCRIPTION
        "The total bandwidth allocated for SDV mappings in mbps on blade.
        "
::= { apexRtspStatBladeBwEntry 4 }

apexRtspStatBladeBwTotal OBJECT-TYPE
    SYNTAX Integer32
    MAX-ACCESS read-only
    STATUS current
    DESCRIPTION
        "The total bandwidth allocated in mbps on blade.
        "
::= { apexRtspStatBladeBwEntry 5 }

apexRtspStatBladeBwDepiMap OBJECT-TYPE
    SYNTAX Integer32
    MAX-ACCESS read-only
    STATUS current
    DESCRIPTION
        "The total bandwidth allocated for DEPI mappings in mbps on blade.
        "
::= { apexRtspStatBladeBwEntry 6 }


-- ------------------------------------------------------------------------------
--
-- apexRtspSetupFailureStatTable
--

apexRtspSetupFailureStatTable OBJECT-TYPE
    SYNTAX SEQUENCE OF ApexRtspSetupFailureStatEntry
    MAX-ACCESS not-accessible
    STATUS current
    DESCRIPTION
        "Table of RPC session setup failures.
        "
::= { apexRtspStatus 11 }

apexRtspSetupFailureStatEntry OBJECT-TYPE
    SYNTAX ApexRtspSetupFailureStatEntry
    MAX-ACCESS not-accessible
    STATUS current
    DESCRIPTION
        "RPC Session Setup Failure Status Table Entry."
    INDEX { apexRtspSetupFailureStatBladeNum }
::= { apexRtspSetupFailureStatTable 1 }

ApexRtspSetupFailureStatEntry ::= SEQUENCE
    {
     apexRtspSetupFailureStatBladeNum  Integer32,
     apexRtspSetupFailureStatCount     Counter32
    }

apexRtspSetupFailureStatBladeNum OBJECT-TYPE
    SYNTAX Integer32(1..8)
    MAX-ACCESS not-accessible
    STATUS current
    DESCRIPTION
        "Blade Number."
::= { apexRtspSetupFailureStatEntry 1 }

apexRtspSetupFailureStatCount OBJECT-TYPE
    SYNTAX Counter32
    MAX-ACCESS read-only
    STATUS current
    DESCRIPTION
        "Number of RTSP and MHA session setup failures since count last reset. 
         Count is currently reset at bootup of the APEX."
::= { apexRtspSetupFailureStatEntry 3 }


-- ------------------------------------------------------------------------------
--
-- apexManualRouting
--
-- apexManualRoutingConfig
--
-- apexManualRoutingConfigGeneral
--

apexManualRouteEnableDisableApply OBJECT-TYPE
    SYNTAX EnableDisableAllTYPE
    MAX-ACCESS read-write
    STATUS current
    DESCRIPTION
        "Setting this causes all manual routes on the specified blade
         or on all blades to be enabled or disabled. When enabling routes,
         only routes that have a valid GigE interface and a valid output 
         program number defined will be enabled. This allows for all routes
         to quickly be enabled or disabled.
         
         This affects manual routed services only.
         
         Upon setting this field, no changes will take affect until after
         the APEX sets this field back to notInProgress.
         
         @Config(config=no, reboot=no)
        "
::= { apexManualRoutingConfigGeneral 1 }

apexManRtePassThruEnableDisableApply OBJECT-TYPE
    SYNTAX EnableDisableAllTYPE
    MAX-ACCESS read-write
    STATUS current
    DESCRIPTION
        "Setting this causes all manual routes on the specified blade
         or on all blades to be enabled or disabled. When enabling routes,
         only routes that have a valid GigE interface will be enabled. This 
         allows for all routes to quickly be enabled or disabled.
         
         This affects manual routed pass thru streams only.
         
         Upon setting this field, no changes will take affect until after
         the APEX sets this field back to notInProgress.
         
         @Config(config=no, reboot=no)
        "
::= { apexManualRoutingConfigGeneral 2 }


-- ------------------------------------------------------------------------------
--
-- apexManualRouteBlade1
--
-- apexManualRouteBlade1ApplyTable
--

apexManualRouteBlade1ApplyTable OBJECT-TYPE
    SYNTAX SEQUENCE OF ApexManualRouteBlade1ApplyEntry
    MAX-ACCESS not-accessible
    STATUS current
    DESCRIPTION
        "Table of Apply Change for the data for Manual Route Table.

         A row in this table corresponds to the same row index in the
         Manual Route table.
        "
::= { apexManualRouteBlade1 1 }

apexManualRouteBlade1ApplyEntry OBJECT-TYPE
    SYNTAX ApexManualRouteBlade1ApplyEntry
    MAX-ACCESS not-accessible
    STATUS current
    DESCRIPTION
        "Manual Route Apply Table Entry."
    INDEX { apexManualRouteBlade1ApplyIndex }
::= { apexManualRouteBlade1ApplyTable 1 }

ApexManualRouteBlade1ApplyEntry ::= SEQUENCE
    {
     apexManualRouteBlade1ApplyIndex        Integer32,
     apexManualRouteBlade1ApplyChange       ApplyDataToDeviceTYPE
    }

apexManualRouteBlade1ApplyIndex OBJECT-TYPE
    SYNTAX Integer32(1..2304)
    MAX-ACCESS not-accessible
    STATUS current
    DESCRIPTION
        "The index of the Manual Route Apply Table."
::= { apexManualRouteBlade1ApplyEntry 1 }

apexManualRouteBlade1ApplyChange OBJECT-TYPE
    SYNTAX ApplyDataToDeviceTYPE
    MAX-ACCESS read-write
    STATUS current
    DESCRIPTION
        "The Apply for the row of data in the Manual Route Table.

         A row in this table corresponds to the same row index in the
         Manual Route table.

         This parameter MUST be set to 'apply' in order for any of the data
         in the Manual Route Table row to take effect in the APEX.  This
         parameter MUST be set LAST after all other data in the Manual Route
         Table row has been configured.

         @Config(config=no, reboot=no)
        "
::= { apexManualRouteBlade1ApplyEntry 2 }


-- ------------------------------------------------------------------------------
--
-- apexManualRouteBlade1Table
--

apexManualRouteBlade1Table OBJECT-TYPE
    SYNTAX SEQUENCE OF ApexManualRouteBlade1Entry
    MAX-ACCESS not-accessible
    STATUS current
    DESCRIPTION
        "Table of data for Manual Routes.

         Once written, the change to a row this table will only take
         immediate effect after the appropriate apexManualRouteBlade1ApplyChange
         is set to 'apply'.  In order for the change to persist through
         subsequent reboots or power cycles, the change must be saved via
         the apexSaveConfig parameter.

         @Config(config=yes, reboot=no)
         @Commit(param=apexManualRouteBlade1ApplyChange, value=2)
         @Save(apexSaveConfig, value=2)
         @File(manrout1.ini, type='ini')
        "
::= { apexManualRouteBlade1 2 }

apexManualRouteBlade1Entry OBJECT-TYPE
    SYNTAX ApexManualRouteBlade1Entry
    MAX-ACCESS not-accessible
    STATUS current
    DESCRIPTION
        "Manual Route Table Entry."
    INDEX { apexManualRouteBlade1Index }
::= { apexManualRouteBlade1Table 1 }

ApexManualRouteBlade1Entry ::= SEQUENCE
    {
     apexManualRouteBlade1Index                   Integer32,
     apexManualRouteBlade1Enable                  EnableDisableTYPE,
     apexManualRouteBlade1InputInterface          Integer32,
     apexManualRouteBlade1InputUdp                Integer32,
     apexManualRouteBlade1InputMulticastIp        IpAddress,
     apexManualRouteBlade1InputSourceIp           IpAddress,
     apexManualRouteBlade1InputProgNum            Integer32,
     apexManualRouteBlade1InputPreEncryptCheck    EnableDisableTYPE,
     apexManualRouteBlade1OutputTsNum             Integer32,
     apexManualRouteBlade1OutputProgNum           Integer32,
     apexManualRouteBlade1FollowDtcp              EnableDisableTYPE
    }

apexManualRouteBlade1Index OBJECT-TYPE
    SYNTAX Integer32(1..2304)
    MAX-ACCESS not-accessible
    STATUS current
    DESCRIPTION
        "The index of the Manual Route Table."
::= { apexManualRouteBlade1Entry 1 }

apexManualRouteBlade1Enable OBJECT-TYPE
    SYNTAX EnableDisableTYPE
    MAX-ACCESS read-write
    STATUS current
    DESCRIPTION
        "Indicates that this Manual Route is enabled or disabled.
        "
::= { apexManualRouteBlade1Entry 2 }

apexManualRouteBlade1InputInterface OBJECT-TYPE
    SYNTAX Integer32(0..12)
    MAX-ACCESS read-write
    STATUS current
    DESCRIPTION
        "GigE Interface port number.
        "
::= { apexManualRouteBlade1Entry 3 }

apexManualRouteBlade1InputUdp OBJECT-TYPE
    SYNTAX Integer32(0..65535)
    MAX-ACCESS read-write
    STATUS current
    DESCRIPTION
        "Input UDP Port from which to obtain data.
        "
::= { apexManualRouteBlade1Entry 4 }

apexManualRouteBlade1InputMulticastIp OBJECT-TYPE
    SYNTAX IpAddress
    MAX-ACCESS read-write
    STATUS current
    DESCRIPTION
        "Input Multicast IP address from which to obtain data.

         An IP address of 0.0.0.0 indicates table entry not in use.

         Multicast IP addresses 224.0.0.0 to 224.0.0.255 are reserved.
        "
::= { apexManualRouteBlade1Entry 5 }

apexManualRouteBlade1InputSourceIp OBJECT-TYPE
    SYNTAX IpAddress
    MAX-ACCESS read-write
    STATUS current
    DESCRIPTION
        "Input IGMP v3 Source IP from which to obtain data.

         If the router supports IGMP v3 the GBE will only receive data from
         this source IP.  If Source IP is not specified or the router does not
         support IGMP v3 the GBE will receive data from any source device.
         Source IP address must be a valid singlecast address.
        "
::= { apexManualRouteBlade1Entry 6 }

apexManualRouteBlade1InputProgNum OBJECT-TYPE
    SYNTAX Integer32(0..65535)
    MAX-ACCESS read-write
    STATUS current
    DESCRIPTION
        "Input MPEG Program Number to multiplex. A value of 0 can be used as
         a wild card. This will cause the APEX to map the first program listed in
         the input PAT to the specified output (regardless of input program number).
         Input program number zero should only be used when mapping Single Program
         Transport Streams (SPTS).
        "
::= { apexManualRouteBlade1Entry 7 }

apexManualRouteBlade1InputPreEncryptCheck OBJECT-TYPE
    SYNTAX EnableDisableTYPE
    MAX-ACCESS read-write
    STATUS current
    DESCRIPTION
        "Manual Routing Pre-Encryption Checking.

         Indicates if the APEX is to check if the input service is pre-encrypted or
         clear. Pre-encrypted is determined by examining the input PMT for a CA ECM
         descriptor (any CA ECM descriptor). If pre-encrypted, setting this flag will
         cause the APEX to pass through ECM PID for this service. For input services
         that have a GI CA ECM descriptor, the APEX will also pass through the PIT
         message (extract and re-insert the PIT). The output PMT for pre-encrypted
         services will contain a CA ECM descriptor (referencing the ECM
         PID). When PID Remapping is enabled, pre-encryption for a service is
         only valid when the input ECM PID is on a different PID than the
         associated PMT PID. If this flag is set to pre-encryption and the
         input service is not pre-encrypted, then the setting of this flag has
         no affect on the output service.
        "
::= { apexManualRouteBlade1Entry 8 }

apexManualRouteBlade1OutputTsNum OBJECT-TYPE
    SYNTAX Integer32(0..256)
    MAX-ACCESS read-write
    STATUS current
    DESCRIPTION
        "Output Transport Stream Number of the output on which to place data.
         Zero = NotApplicable and is only valid if the apexManualRouteBlade1Table
         entry is not being used.
        "
::= { apexManualRouteBlade1Entry 9 }

apexManualRouteBlade1OutputProgNum OBJECT-TYPE
    SYNTAX Integer32(0..65535)
    MAX-ACCESS read-write
    STATUS current
    DESCRIPTION
        "Output Program number to use for the program.
         Zero = NotApplicable and is only valid if the apexManualRouteBlade1Table
         entry is not being used.
        "
::= { apexManualRouteBlade1Entry 10 }

apexManualRouteBlade1FollowDtcp OBJECT-TYPE
    SYNTAX EnableDisableTYPE
    MAX-ACCESS read-write
    STATUS current
    DESCRIPTION
        "Determines how the copy protection settings (CCI, APS, and CIT) within 
         the PRK will be set.
         For each service, will allow user to override the RDS or user 
         configured copy protection and force the service to follow 
         the input DTCP.
        
        - Disabled    - Use CTE configured settings if output in CTE encryption mode
        - Enabled     - Follow input DTCP.                                
        "
::= { apexManualRouteBlade1Entry 11 }


-- ------------------------------------------------------------------------------
--
-- apexManRtePassThruBlade1ApplyTable
--

apexManRtePassThruBlade1ApplyTable OBJECT-TYPE
    SYNTAX SEQUENCE OF ApexManRtePassThruBlade1ApplyEntry
    MAX-ACCESS not-accessible
    STATUS current
    DESCRIPTION
        "Table of Apply Change for the data for Manual Route Pass Through Table.

         A row in this table corresponds to the same row index in the
         Manual Route Pass Through table.
        "
::= { apexManualRouteBlade1 3 }

apexManRtePassThruBlade1ApplyEntry OBJECT-TYPE
    SYNTAX ApexManRtePassThruBlade1ApplyEntry
    MAX-ACCESS not-accessible
    STATUS current
    DESCRIPTION
        "Manual Route Pass Through Apply Table Entry."
    INDEX { apexManRtePassThruBlade1ApplyOutputTsNum }
::= { apexManRtePassThruBlade1ApplyTable 1 }

ApexManRtePassThruBlade1ApplyEntry ::= SEQUENCE
    {
     apexManRtePassThruBlade1ApplyOutputTsNum   Integer32,
     apexManRtePassThruBlade1ApplyChange        ApplyDataToDeviceTYPE
    }

apexManRtePassThruBlade1ApplyOutputTsNum OBJECT-TYPE
    SYNTAX Integer32(1..256)
    MAX-ACCESS not-accessible
    STATUS current
    DESCRIPTION
        "The index of the Manual Route Pass Through Apply Table."
::= { apexManRtePassThruBlade1ApplyEntry 1 }

apexManRtePassThruBlade1ApplyChange OBJECT-TYPE
    SYNTAX ApplyDataToDeviceTYPE
    MAX-ACCESS read-write
    STATUS current
    DESCRIPTION
        "The Apply for the row of data in the Manual Route Pass Through Table.

         A row in this table corresponds to the same row index in the
         Manual Route Pass Through table.

         This parameter MUST be set to 'apply' in order for any of the
         data in the Manual Route Pass Through Table row to take effect
         in the APEX.  This parameter MUST be set LAST after all other
         data in the Manual Route Pass Through Table row has been configured.

         @Config(config=no, reboot=no)
        "
::= { apexManRtePassThruBlade1ApplyEntry 2 }


-- ------------------------------------------------------------------------------
--
-- apexManRtePassThruBlade1Table
--

apexManRtePassThruBlade1Table OBJECT-TYPE
    SYNTAX SEQUENCE OF ApexManRtePassThruBlade1Entry
    MAX-ACCESS not-accessible
    STATUS current
    DESCRIPTION
        "Table of data for Manual Route Pass Through. This table is used to
         pass through an entire input stream to an output stream.

         Once written, the change to a row this table will only take
         immediate effect after the appropriate apexManRtePassThruBlade1ApplyChange
         is set to 'apply'.  In order for the change to persist through
         subsequent reboots or power cycles, the change must be saved via
         the apexSaveConfig parameter.

         @Config(config=yes, reboot=no)
         @Commit(param=apexManRtePassThruBlade1ApplyChange, value=2)
         @Save(apexSaveConfig, value=2)
         @File(manrout1.ini, type='ini')
        "
::= { apexManualRouteBlade1 4 }

apexManRtePassThruBlade1Entry OBJECT-TYPE
    SYNTAX ApexManRtePassThruBlade1Entry
    MAX-ACCESS not-accessible
    STATUS current
    DESCRIPTION
        "Manual Route Pass Through Table Entry."
    INDEX { apexManRtePassThruBlade1OutputTsNum }
::= { apexManRtePassThruBlade1Table 1 }

ApexManRtePassThruBlade1Entry ::= SEQUENCE
    {
     apexManRtePassThruBlade1OutputTsNum        Integer32,
     apexManRtePassThruBlade1Enable             EnableDisableTYPE,
     apexManRtePassThruBlade1InputInterface     Integer32,
     apexManRtePassThruBlade1InputUdp           Integer32,
     apexManRtePassThruBlade1InputMulticastIp   IpAddress,
     apexManRtePassThruBlade1InputSourceIp      IpAddress
    }

apexManRtePassThruBlade1OutputTsNum OBJECT-TYPE
    SYNTAX Integer32(1..256)
    MAX-ACCESS not-accessible
    STATUS current
    DESCRIPTION
        "The index of the Manual Route Pass Through Table."
::= { apexManRtePassThruBlade1Entry 1 }

apexManRtePassThruBlade1Enable OBJECT-TYPE
    SYNTAX EnableDisableTYPE
    MAX-ACCESS read-write
    STATUS current
    DESCRIPTION
        "Indicates that this Manual Route Pass Through is enabled or disabled.
         An input stream can only be passed through to an output stream when
         there are no active service or PID mappings to the output stream.
        "
::= { apexManRtePassThruBlade1Entry 2 }

apexManRtePassThruBlade1InputInterface OBJECT-TYPE
    SYNTAX Integer32(0..12)
    MAX-ACCESS read-write
    STATUS current
    DESCRIPTION
        "Number of the input GigE interface from which to obtain data.
        "
::= { apexManRtePassThruBlade1Entry 3 }

apexManRtePassThruBlade1InputUdp OBJECT-TYPE
    SYNTAX Integer32(0..65535)
    MAX-ACCESS read-write
    STATUS current
    DESCRIPTION
        "Input UDP Port from which to obtain data.
        "
::= { apexManRtePassThruBlade1Entry 4 }

apexManRtePassThruBlade1InputMulticastIp OBJECT-TYPE
    SYNTAX IpAddress
    MAX-ACCESS read-write
    STATUS current
    DESCRIPTION
        "Input Multicast IP address from which to obtain data.

         An IP address of 0.0.0.0 indicates table entry not in use.

         Multicast IP addresses 224.0.0.0 to 224.0.0.255 are reserved.
        "
::= { apexManRtePassThruBlade1Entry 5 }

apexManRtePassThruBlade1InputSourceIp OBJECT-TYPE
    SYNTAX IpAddress
    MAX-ACCESS read-write
    STATUS current
    DESCRIPTION
        "Input IGMP v3 Source IP address from which to obtain data.

         If the router supports IGMP v3 the GBE will only receive data from
         this source IP.  If Source IP is not specified or the router does not
         support IGMP v3 the GBE will receive data from any source device.
         Source IP address must be a valid singlecast address.
        "
::= { apexManRtePassThruBlade1Entry 6 }


-- ------------------------------------------------------------------------------
--
-- apexManualRouteBlade2
--
-- apexManualRouteBlade2ApplyTable
--

apexManualRouteBlade2ApplyTable OBJECT-TYPE
    SYNTAX SEQUENCE OF ApexManualRouteBlade2ApplyEntry
    MAX-ACCESS not-accessible
    STATUS current
    DESCRIPTION
        "Table of Apply Change for the data for Manual Route Table.

         A row in this table corresponds to the same row index in the
         Manual Route table.
        "
::= { apexManualRouteBlade2 1 }

apexManualRouteBlade2ApplyEntry OBJECT-TYPE
    SYNTAX ApexManualRouteBlade2ApplyEntry
    MAX-ACCESS not-accessible
    STATUS current
    DESCRIPTION
        "Manual Route Apply Table Entry."
    INDEX { apexManualRouteBlade2ApplyIndex }
::= { apexManualRouteBlade2ApplyTable 1 }

ApexManualRouteBlade2ApplyEntry ::= SEQUENCE
    {
     apexManualRouteBlade2ApplyIndex        Integer32,
     apexManualRouteBlade2ApplyChange       ApplyDataToDeviceTYPE
    }

apexManualRouteBlade2ApplyIndex OBJECT-TYPE
    SYNTAX Integer32(1..2304)
    MAX-ACCESS not-accessible
    STATUS current
    DESCRIPTION
        "The index of the Manual Route Apply Table."
::= { apexManualRouteBlade2ApplyEntry 1 }

apexManualRouteBlade2ApplyChange OBJECT-TYPE
    SYNTAX ApplyDataToDeviceTYPE
    MAX-ACCESS read-write
    STATUS current
    DESCRIPTION
        "The Apply for the row of data in the Manual Route Table.

         A row in this table corresponds to the same row index in the
         Manual Route table.

         This parameter MUST be set to 'apply' in order for any of the data
         in the Manual Route Table row to take effect in the APEX.  This
         parameter MUST be set LAST after all other data in the Manual Route
         Table row has been configured.

         @Config(config=no, reboot=no)
        "
::= { apexManualRouteBlade2ApplyEntry 2 }

                                       
-- ------------------------------------------------------------------------------
--
-- apexManualRouteBlade2Table
--

apexManualRouteBlade2Table OBJECT-TYPE
    SYNTAX SEQUENCE OF ApexManualRouteBlade2Entry
    MAX-ACCESS not-accessible
    STATUS current
    DESCRIPTION
        "Table of data for Manual Routes.

         Once written, the change to a row this table will only take
         immediate effect after the appropriate apexManualRouteBlade2ApplyChange
         is set to 'apply'.  In order for the change to persist through
         subsequent reboots or power cycles, the change must be saved via
         the apexSaveConfig parameter.

         @Config(config=yes, reboot=no)
         @Commit(param=apexManualRouteBlade2ApplyChange, value=2)
         @Save(apexSaveConfig, value=2)
         @File(manrout2.ini, type='ini')
        "
::= { apexManualRouteBlade2 2 }

apexManualRouteBlade2Entry OBJECT-TYPE
    SYNTAX ApexManualRouteBlade2Entry
    MAX-ACCESS not-accessible
    STATUS current
    DESCRIPTION
        "Manual Route Table Entry."
    INDEX { apexManualRouteBlade2Index }
::= { apexManualRouteBlade2Table 1 }

ApexManualRouteBlade2Entry ::= SEQUENCE
    {
     apexManualRouteBlade2Index                   Integer32,
     apexManualRouteBlade2Enable                  EnableDisableTYPE,
     apexManualRouteBlade2InputInterface          Integer32,
     apexManualRouteBlade2InputUdp                Integer32,
     apexManualRouteBlade2InputMulticastIp        IpAddress,
     apexManualRouteBlade2InputSourceIp           IpAddress,
     apexManualRouteBlade2InputProgNum            Integer32,
     apexManualRouteBlade2InputPreEncryptCheck    EnableDisableTYPE,
     apexManualRouteBlade2OutputTsNum             Integer32,
     apexManualRouteBlade2OutputProgNum           Integer32,
     apexManualRouteBlade2FollowDtcp              EnableDisableTYPE
    }

apexManualRouteBlade2Index OBJECT-TYPE
    SYNTAX Integer32(1..2304)
    MAX-ACCESS not-accessible
    STATUS current
    DESCRIPTION
        "The index of the Manual Route Table."
::= { apexManualRouteBlade2Entry 1 }

apexManualRouteBlade2Enable OBJECT-TYPE
    SYNTAX EnableDisableTYPE
    MAX-ACCESS read-write
    STATUS current
    DESCRIPTION
        "Indicates that this Manual Route is enabled or disabled.
        "
::= { apexManualRouteBlade2Entry 2 }

apexManualRouteBlade2InputInterface OBJECT-TYPE
    SYNTAX Integer32(0..12)
    MAX-ACCESS read-write
    STATUS current
    DESCRIPTION
        "Number of the input GigE interface from which to obtain data.
        "
::= { apexManualRouteBlade2Entry 3 }

apexManualRouteBlade2InputUdp OBJECT-TYPE
    SYNTAX Integer32(0..65535)
    MAX-ACCESS read-write
    STATUS current
    DESCRIPTION
        "Input UDP Port from which to obtain data.
        "
::= { apexManualRouteBlade2Entry 4 }

apexManualRouteBlade2InputMulticastIp OBJECT-TYPE
    SYNTAX IpAddress
    MAX-ACCESS read-write
    STATUS current
    DESCRIPTION
        "Input Multicast IP address from which to obtain data.

         An IP address of 0.0.0.0 indicates table entry not in use.

         Multicast IP addresses 224.0.0.0 to 224.0.0.255 are reserved.
        "
::= { apexManualRouteBlade2Entry 5 }

apexManualRouteBlade2InputSourceIp OBJECT-TYPE
    SYNTAX IpAddress
    MAX-ACCESS read-write
    STATUS current
    DESCRIPTION
        "Input IGMP v3 Source IP from which to obtain data.

         If the router supports IGMP v3 the GBE will only receive data from
         this source IP.  If Source IP is not specified or the router does not
         support IGMP v3 the GBE will receive data from any source device.
         Source IP address must be a valid singlecast address.
        "
::= { apexManualRouteBlade2Entry 6 }

apexManualRouteBlade2InputProgNum OBJECT-TYPE
    SYNTAX Integer32(0..65535)
    MAX-ACCESS read-write
    STATUS current
    DESCRIPTION
        "Input MPEG Program Number to multiplex. A value of 0 can be used as
         a wild card. This will cause the APEX to map the first program listed in
         the input PAT to the specified output (regardless of input program number).
         Input program number zero should only be used when mapping Single Program
         Transport Streams (SPTS).
        "
::= { apexManualRouteBlade2Entry 7 }

apexManualRouteBlade2InputPreEncryptCheck OBJECT-TYPE
    SYNTAX EnableDisableTYPE
    MAX-ACCESS read-write
    STATUS current
    DESCRIPTION
        "Manual Routing Pre-Encryption Checking.

         Indicates if the APEX is to check if the input service is pre-encrypted or
         clear. Pre-encrypted is determined by examining the input PMT for a CA ECM
         descriptor (any CA ECM descriptor). If pre-encrypted, setting this flag will
         cause the APEX to pass through ECM PID for this service. For input services
         that have a GI CA ECM descriptor, the APEX will also pass through the PIT
         message (extract and re-insert the PIT). The output PMT for pre-encrypted
         services will contain a CA ECM descriptor (referencing the ECM
         PID). When PID Remapping is enabled, pre-encryption for a service is
         only valid when the input ECM PID is on a different PID than the
         associated PMT PID. If this flag is set to pre-encryption and the
         input service is not pre-encrypted, then the setting of this flag has
         no affect on the output service.
        "
::= { apexManualRouteBlade2Entry 8 }

apexManualRouteBlade2OutputTsNum OBJECT-TYPE
    SYNTAX Integer32(0..256)
    MAX-ACCESS read-write
    STATUS current
    DESCRIPTION
        "Output Transport Stream Number of the output on which to place data.
         Zero = NotApplicable and is only valid if the apexManualRouteBlade2Table
         entry is not being used.
        "
::= { apexManualRouteBlade2Entry 9 }

apexManualRouteBlade2OutputProgNum OBJECT-TYPE
    SYNTAX Integer32(0..65535)
    MAX-ACCESS read-write
    STATUS current
    DESCRIPTION
        "Output Program number to use for the program.
         Zero = NotApplicable and is only valid if the apexManualRouteBlade2Table
         entry is not being used.
        "
::= { apexManualRouteBlade2Entry 10 }

apexManualRouteBlade2FollowDtcp OBJECT-TYPE
    SYNTAX EnableDisableTYPE
    MAX-ACCESS read-write
    STATUS current
    DESCRIPTION
        "Determines how the copy protection settings (CCI, APS, and CIT) within 
         the PRK will be set.
         For each service, will allow user to override the RDS or user 
         configured copy protection and force the service to follow 
         the input DTCP.
        
        - Disabled    - Use CTE configured settings if output in CTE encryption mode
        - Enabled     - Follow input DTCP.                                
        "
::= { apexManualRouteBlade2Entry 11 }


-- ------------------------------------------------------------------------------
--
-- apexManRtePassThruBlade2ApplyTable
--

apexManRtePassThruBlade2ApplyTable OBJECT-TYPE
    SYNTAX SEQUENCE OF ApexManRtePassThruBlade2ApplyEntry
    MAX-ACCESS not-accessible
    STATUS current
    DESCRIPTION
        "Table of Apply Change for the data for Manual Route Pass Through Table.

         A row in this table corresponds to the same row index in the
         Manual Route Pass Through table.
        "
::= { apexManualRouteBlade2 3 }

apexManRtePassThruBlade2ApplyEntry OBJECT-TYPE
    SYNTAX ApexManRtePassThruBlade2ApplyEntry
    MAX-ACCESS not-accessible
    STATUS current
    DESCRIPTION
        "Manual Route Pass Through Apply Table Entry."
    INDEX { apexManRtePassThruBlade2ApplyOutputTsNum }
::= { apexManRtePassThruBlade2ApplyTable 1 }

ApexManRtePassThruBlade2ApplyEntry ::= SEQUENCE
    {
     apexManRtePassThruBlade2ApplyOutputTsNum   Integer32,
     apexManRtePassThruBlade2ApplyChange        ApplyDataToDeviceTYPE
    }

apexManRtePassThruBlade2ApplyOutputTsNum OBJECT-TYPE
    SYNTAX Integer32(1..256)
    MAX-ACCESS not-accessible
    STATUS current
    DESCRIPTION
        "The index of the Manual Route Pass Through Apply Table."
::= { apexManRtePassThruBlade2ApplyEntry 1 }

apexManRtePassThruBlade2ApplyChange OBJECT-TYPE
    SYNTAX ApplyDataToDeviceTYPE
    MAX-ACCESS read-write
    STATUS current
    DESCRIPTION
        "The Apply for the row of data in the Manual Route Pass Through Table.

         A row in this table corresponds to the same row index in the
         Manual Route Pass Through table.

         This parameter MUST be set to 'apply' in order for any of the
         data in the Manual Route Pass Through Table row to take effect
         in the APEX.  This parameter MUST be set LAST after all other
         data in the Manual Route Pass Through Table row has been configured.

         @Config(config=no, reboot=no)
        "
::= { apexManRtePassThruBlade2ApplyEntry 2 }


-- ------------------------------------------------------------------------------
--
-- apexManRtePassThruBlade2Table
--

apexManRtePassThruBlade2Table OBJECT-TYPE
    SYNTAX SEQUENCE OF ApexManRtePassThruBlade2Entry
    MAX-ACCESS not-accessible
    STATUS current
    DESCRIPTION
        "Table of data for Manual Route Pass Through. This table is used to
         pass through an entire input stream to an output stream.

         Once written, the change to a row this table will only take
         immediate effect after the appropriate apexManRtePassThruBlade2ApplyChange
         is set to 'apply'.  In order for the change to persist through
         subsequent reboots or power cycles, the change must be saved via
         the apexSaveConfig parameter.

         @Config(config=yes, reboot=no)
         @Commit(param=apexManRtePassThruBlade2ApplyChange, value=2)
         @Save(apexSaveConfig, value=2)
         @File(manrout2.ini, type='ini')
        "
::= { apexManualRouteBlade2 4 }

apexManRtePassThruBlade2Entry OBJECT-TYPE
    SYNTAX ApexManRtePassThruBlade2Entry
    MAX-ACCESS not-accessible
    STATUS current
    DESCRIPTION
        "Manual Route Pass Through Table Entry."
    INDEX { apexManRtePassThruBlade2OutputTsNum }
::= { apexManRtePassThruBlade2Table 1 }

ApexManRtePassThruBlade2Entry ::= SEQUENCE
    {
     apexManRtePassThruBlade2OutputTsNum        Integer32,
     apexManRtePassThruBlade2Enable             EnableDisableTYPE,
     apexManRtePassThruBlade2InputInterface     Integer32,
     apexManRtePassThruBlade2InputUdp           Integer32,
     apexManRtePassThruBlade2InputMulticastIp   IpAddress,
     apexManRtePassThruBlade2InputSourceIp      IpAddress
    }

apexManRtePassThruBlade2OutputTsNum OBJECT-TYPE
    SYNTAX Integer32(1..256)
    MAX-ACCESS not-accessible
    STATUS current
    DESCRIPTION
        "The index of the Manual Route Pass Through Table."
::= { apexManRtePassThruBlade2Entry 1 }

apexManRtePassThruBlade2Enable OBJECT-TYPE
    SYNTAX EnableDisableTYPE
    MAX-ACCESS read-write
    STATUS current
    DESCRIPTION
        "Indicates that this Manual Route Pass Through is enabled or disabled.
         An input stream can only be passed through to an output stream when
         there are no active service or PID mappings to the output stream.
        "
::= { apexManRtePassThruBlade2Entry 2 }

apexManRtePassThruBlade2InputInterface OBJECT-TYPE
    SYNTAX Integer32(0..12)
    MAX-ACCESS read-write
    STATUS current
    DESCRIPTION
        "Number of the input GigE interface from which to obtain data.
        "
::= { apexManRtePassThruBlade2Entry 3 }

apexManRtePassThruBlade2InputUdp OBJECT-TYPE
    SYNTAX Integer32(0..65535)
    MAX-ACCESS read-write
    STATUS current
    DESCRIPTION
        "Input UDP Port from which to obtain data.
        "
::= { apexManRtePassThruBlade2Entry 4 }

apexManRtePassThruBlade2InputMulticastIp OBJECT-TYPE
    SYNTAX IpAddress
    MAX-ACCESS read-write
    STATUS current
    DESCRIPTION
        "Input Multicast IP address from which to obtain data.

         An IP address of 0.0.0.0 indicates table entry not in use.

         Multicast IP addresses 224.0.0.0 to 224.0.0.255 are reserved.
        "
::= { apexManRtePassThruBlade2Entry 5 }

apexManRtePassThruBlade2InputSourceIp OBJECT-TYPE
    SYNTAX IpAddress
    MAX-ACCESS read-write
    STATUS current
    DESCRIPTION
        "Input IGMP v3 Source IP address from which to obtain data.

         If the router supports IGMP v3 the GBE will only receive data from
         this source IP.  If Source IP is not specified or the router does not
         support IGMP v3 the GBE will receive data from any source device.
         Source IP address must be a valid singlecast address.
        "
::= { apexManRtePassThruBlade2Entry 6 }


-- ------------------------------------------------------------------------------
--
-- apexManualRouteBlade3
--
-- apexManualRouteBlade3ApplyTable
--

apexManualRouteBlade3ApplyTable OBJECT-TYPE
    SYNTAX SEQUENCE OF ApexManualRouteBlade3ApplyEntry
    MAX-ACCESS not-accessible
    STATUS current
    DESCRIPTION
        "Table of Apply Change for the data for Manual Route Table.

         A row in this table corresponds to the same row index in the
         Manual Route table.
        "
::= { apexManualRouteBlade3 1 }

apexManualRouteBlade3ApplyEntry OBJECT-TYPE
    SYNTAX ApexManualRouteBlade3ApplyEntry
    MAX-ACCESS not-accessible
    STATUS current
    DESCRIPTION
        "Manual Route Apply Table Entry."
    INDEX { apexManualRouteBlade3ApplyIndex }
::= { apexManualRouteBlade3ApplyTable 1 }

ApexManualRouteBlade3ApplyEntry ::= SEQUENCE
    {
     apexManualRouteBlade3ApplyIndex        Integer32,
     apexManualRouteBlade3ApplyChange       ApplyDataToDeviceTYPE    
    }

apexManualRouteBlade3ApplyIndex OBJECT-TYPE
    SYNTAX Integer32(1..2304)
    MAX-ACCESS not-accessible
    STATUS current
    DESCRIPTION
        "The index of the Manual Route Apply Table."
::= { apexManualRouteBlade3ApplyEntry 1 }

apexManualRouteBlade3ApplyChange OBJECT-TYPE
    SYNTAX ApplyDataToDeviceTYPE
    MAX-ACCESS read-write
    STATUS current
    DESCRIPTION
        "The Apply for the row of data in the Manual Route Table.

         A row in this table corresponds to the same row index in the
         Manual Route table.

         This parameter MUST be set to 'apply' in order for any of the data
         in the Manual Route Table row to take effect in the APEX.  This
         parameter MUST be set LAST after all other data in the Manual Route
         Table row has been configured.

         @Config(config=no, reboot=no)
        "
::= { apexManualRouteBlade3ApplyEntry 2 }

                                       
-- ------------------------------------------------------------------------------
--
-- apexManualRouteBlade3Table
--

apexManualRouteBlade3Table OBJECT-TYPE
    SYNTAX SEQUENCE OF ApexManualRouteBlade3Entry
    MAX-ACCESS not-accessible
    STATUS current
    DESCRIPTION
        "Table of data for Manual Routes.

         Once written, the change to a row this table will only take
         immediate effect after the appropriate apexManualRouteBlade3ApplyChange
         is set to 'apply'.  In order for the change to persist through
         subsequent reboots or power cycles, the change must be saved via
         the apexSaveConfig parameter.

         @Config(config=yes, reboot=no)
         @Commit(param=apexManualRouteBlade3ApplyChange, value=2)
         @Save(apexSaveConfig, value=2)
         @File(manrout3.ini, type='ini')
        "
::= { apexManualRouteBlade3 2 }

apexManualRouteBlade3Entry OBJECT-TYPE
    SYNTAX ApexManualRouteBlade3Entry
    MAX-ACCESS not-accessible
    STATUS current
    DESCRIPTION
        "Manual Route Table Entry."
    INDEX { apexManualRouteBlade3Index }
::= { apexManualRouteBlade3Table 1 }

ApexManualRouteBlade3Entry ::= SEQUENCE
    {
     apexManualRouteBlade3Index                   Integer32,
     apexManualRouteBlade3Enable                  EnableDisableTYPE,
     apexManualRouteBlade3InputInterface          Integer32,
     apexManualRouteBlade3InputUdp                Integer32,
     apexManualRouteBlade3InputMulticastIp        IpAddress,
     apexManualRouteBlade3InputSourceIp           IpAddress,
     apexManualRouteBlade3InputProgNum            Integer32,
     apexManualRouteBlade3InputPreEncryptCheck    EnableDisableTYPE,
     apexManualRouteBlade3OutputTsNum             Integer32,
     apexManualRouteBlade3OutputProgNum           Integer32,
     apexManualRouteBlade3FollowDtcp              EnableDisableTYPE
    }

apexManualRouteBlade3Index OBJECT-TYPE
    SYNTAX Integer32(1..2304)
    MAX-ACCESS not-accessible
    STATUS current
    DESCRIPTION
        "The index of the Manual Route Table."
::= { apexManualRouteBlade3Entry 1 }

apexManualRouteBlade3Enable OBJECT-TYPE
    SYNTAX EnableDisableTYPE
    MAX-ACCESS read-write
    STATUS current
    DESCRIPTION
        "Indicates that this Manual Route is enabled or disabled.
        "
::= { apexManualRouteBlade3Entry 2 }

apexManualRouteBlade3InputInterface OBJECT-TYPE
    SYNTAX Integer32(0..12)
    MAX-ACCESS read-write
    STATUS current
    DESCRIPTION
        "Number of the input GigE interface from which to obtain data.
        "
::= { apexManualRouteBlade3Entry 3 }

apexManualRouteBlade3InputUdp OBJECT-TYPE
    SYNTAX Integer32(0..65535)
    MAX-ACCESS read-write
    STATUS current
    DESCRIPTION
        "Input UDP Port from which to obtain data.
        "
::= { apexManualRouteBlade3Entry 4 }

apexManualRouteBlade3InputMulticastIp OBJECT-TYPE
    SYNTAX IpAddress
    MAX-ACCESS read-write
    STATUS current
    DESCRIPTION
        "Input Multicast IP address from which to obtain data.

         An IP address of 0.0.0.0 indicates table entry not in use.

         Multicast IP addresses 224.0.0.0 to 224.0.0.255 are reserved.
        "
::= { apexManualRouteBlade3Entry 5 }

apexManualRouteBlade3InputSourceIp OBJECT-TYPE
    SYNTAX IpAddress
    MAX-ACCESS read-write
    STATUS current
    DESCRIPTION
        "Input IGMP v3 Source IP from which to obtain data.

         If the router supports IGMP v3 the GBE will only receive data from
         this source IP.  If Source IP is not specified or the router does not
         support IGMP v3 the GBE will receive data from any source device.
         Source IP address must be a valid singlecast address.
        "
::= { apexManualRouteBlade3Entry 6 }

apexManualRouteBlade3InputProgNum OBJECT-TYPE
    SYNTAX Integer32(0..65535)
    MAX-ACCESS read-write
    STATUS current
    DESCRIPTION
        "Input MPEG Program Number to multiplex. A value of 0 can be used as
         a wild card. This will cause the APEX to map the first program listed in
         the input PAT to the specified output (regardless of input program number).
         Input program number zero should only be used when mapping Single Program
         Transport Streams (SPTS).
        "
::= { apexManualRouteBlade3Entry 7 }

apexManualRouteBlade3InputPreEncryptCheck OBJECT-TYPE
    SYNTAX EnableDisableTYPE
    MAX-ACCESS read-write
    STATUS current
    DESCRIPTION
        "Manual Routing Pre-Encryption Checking.

         Indicates if the APEX is to check if the input service is pre-encrypted or
         clear. Pre-encrypted is determined by examining the input PMT for a CA ECM
         descriptor (any CA ECM descriptor). If pre-encrypted, setting this flag will
         cause the APEX to pass through ECM PID for this service. For input services
         that have a GI CA ECM descriptor, the APEX will also pass through the PIT
         message (extract and re-insert the PIT). The output PMT for pre-encrypted
         services will contain a CA ECM descriptor (referencing the ECM
         PID). When PID Remapping is enabled, pre-encryption for a service is
         only valid when the input ECM PID is on a different PID than the
         associated PMT PID. If this flag is set to pre-encryption and the
         input service is not pre-encrypted, then the setting of this flag has
         no affect on the output service.
        "
::= { apexManualRouteBlade3Entry 8 }

apexManualRouteBlade3OutputTsNum OBJECT-TYPE
    SYNTAX Integer32(0..256)
    MAX-ACCESS read-write
    STATUS current
    DESCRIPTION
        "Output Transport Stream Number of the output on which to place data.
         Zero = NotApplicable and is only valid if the apexManualRouteBlade3Table
         entry is not being used.
        "
::= { apexManualRouteBlade3Entry 9 }

apexManualRouteBlade3OutputProgNum OBJECT-TYPE
    SYNTAX Integer32(0..65535)
    MAX-ACCESS read-write
    STATUS current
    DESCRIPTION
        "Output Program number to use for the program.
         Zero = NotApplicable and is only valid if the apexManualRouteBlade3Table
         entry is not being used.
        "
::= { apexManualRouteBlade3Entry 10 }

apexManualRouteBlade3FollowDtcp OBJECT-TYPE
    SYNTAX EnableDisableTYPE
    MAX-ACCESS read-write
    STATUS current
    DESCRIPTION
        "Determines how the copy protection settings (CCI, APS, and CIT) within 
         the PRK will be set.
         For each service, will allow user to override the RDS or user 
         configured copy protection and force the service to follow 
         the input DTCP.
        
        - Disabled    - Use CTE configured settings if output in CTE encryption mode
        - Enabled     - Follow input DTCP.                                
        "
::= { apexManualRouteBlade3Entry 11 }


-- ------------------------------------------------------------------------------
--
-- apexManRtePassThruBlade3ApplyTable
--

apexManRtePassThruBlade3ApplyTable OBJECT-TYPE
    SYNTAX SEQUENCE OF ApexManRtePassThruBlade3ApplyEntry
    MAX-ACCESS not-accessible
    STATUS current
    DESCRIPTION
        "Table of Apply Change for the data for Manual Route Pass Through Table.

         A row in this table corresponds to the same row index in the
         Manual Route Pass Through table.
        "
::= { apexManualRouteBlade3 3 }

apexManRtePassThruBlade3ApplyEntry OBJECT-TYPE
    SYNTAX ApexManRtePassThruBlade3ApplyEntry
    MAX-ACCESS not-accessible
    STATUS current
    DESCRIPTION
        "Manual Route Pass Through Apply Table Entry."
    INDEX { apexManRtePassThruBlade3ApplyOutputTsNum }
::= { apexManRtePassThruBlade3ApplyTable 1 }

ApexManRtePassThruBlade3ApplyEntry ::= SEQUENCE
    {
     apexManRtePassThruBlade3ApplyOutputTsNum   Integer32,
     apexManRtePassThruBlade3ApplyChange        ApplyDataToDeviceTYPE
    }

apexManRtePassThruBlade3ApplyOutputTsNum OBJECT-TYPE
    SYNTAX Integer32(1..256)
    MAX-ACCESS not-accessible
    STATUS current
    DESCRIPTION
        "The index of the Manual Route Pass Through Apply Table."
::= { apexManRtePassThruBlade3ApplyEntry 1 }

apexManRtePassThruBlade3ApplyChange OBJECT-TYPE
    SYNTAX ApplyDataToDeviceTYPE
    MAX-ACCESS read-write
    STATUS current
    DESCRIPTION
        "The Apply for the row of data in the Manual Route Pass Through Table.

         A row in this table corresponds to the same row index in the
         Manual Route Pass Through table.

         This parameter MUST be set to 'apply' in order for any of the
         data in the Manual Route Pass Through Table row to take effect
         in the APEX.  This parameter MUST be set LAST after all other
         data in the Manual Route Pass Through Table row has been configured.

         @Config(config=no, reboot=no)
        "
::= { apexManRtePassThruBlade3ApplyEntry 2 }


-- ------------------------------------------------------------------------------
--
-- apexManRtePassThruBlade3Table
--

apexManRtePassThruBlade3Table OBJECT-TYPE
    SYNTAX SEQUENCE OF ApexManRtePassThruBlade3Entry
    MAX-ACCESS not-accessible
    STATUS current
    DESCRIPTION
        "Table of data for Manual Route Pass Through. This table is used to
         pass through an entire input stream to an output stream.

         Once written, the change to a row this table will only take
         immediate effect after the appropriate apexManRtePassThruBlade3ApplyChange
         is set to 'apply'.  In order for the change to persist through
         subsequent reboots or power cycles, the change must be saved via
         the apexSaveConfig parameter.

         @Config(config=yes, reboot=no)
         @Commit(param=apexManRtePassThruBlade3ApplyChange, value=2)
         @Save(apexSaveConfig, value=2)
         @File(manrout3.ini, type='ini')
        "
::= { apexManualRouteBlade3 4 }

apexManRtePassThruBlade3Entry OBJECT-TYPE
    SYNTAX ApexManRtePassThruBlade3Entry
    MAX-ACCESS not-accessible
    STATUS current
    DESCRIPTION
        "Manual Route Pass Through Table Entry."
    INDEX { apexManRtePassThruBlade3OutputTsNum }
::= { apexManRtePassThruBlade3Table 1 }

ApexManRtePassThruBlade3Entry ::= SEQUENCE
    {
     apexManRtePassThruBlade3OutputTsNum        Integer32,
     apexManRtePassThruBlade3Enable             EnableDisableTYPE,
     apexManRtePassThruBlade3InputInterface     Integer32,
     apexManRtePassThruBlade3InputUdp           Integer32,
     apexManRtePassThruBlade3InputMulticastIp   IpAddress,
     apexManRtePassThruBlade3InputSourceIp      IpAddress
    }

apexManRtePassThruBlade3OutputTsNum OBJECT-TYPE
    SYNTAX Integer32(1..256)
    MAX-ACCESS not-accessible
    STATUS current
    DESCRIPTION
        "The index of the Manual Route Pass Through Table."
::= { apexManRtePassThruBlade3Entry 1 }

apexManRtePassThruBlade3Enable OBJECT-TYPE
    SYNTAX EnableDisableTYPE
    MAX-ACCESS read-write
    STATUS current
    DESCRIPTION
        "Indicates that this Manual Route Pass Through is enabled or disabled.
         An input stream can only be passed through to an output stream when
         there are no active service or PID mappings to the output stream.
        "
::= { apexManRtePassThruBlade3Entry 2 }

apexManRtePassThruBlade3InputInterface OBJECT-TYPE
    SYNTAX Integer32(0..12)
    MAX-ACCESS read-write
    STATUS current
    DESCRIPTION
        "Number of the input GigE interface from which to obtain data.
        "
::= { apexManRtePassThruBlade3Entry 3 }

apexManRtePassThruBlade3InputUdp OBJECT-TYPE
    SYNTAX Integer32(0..65535)
    MAX-ACCESS read-write
    STATUS current
    DESCRIPTION
        "Input UDP Port from which to obtain data.
        "
::= { apexManRtePassThruBlade3Entry 4 }

apexManRtePassThruBlade3InputMulticastIp OBJECT-TYPE
    SYNTAX IpAddress
    MAX-ACCESS read-write
    STATUS current
    DESCRIPTION
        "Input Multicast IP address from which to obtain data.

         An IP address of 0.0.0.0 indicates table entry not in use.

         Multicast IP addresses 224.0.0.0 to 224.0.0.255 are reserved.
        "
::= { apexManRtePassThruBlade3Entry 5 }

apexManRtePassThruBlade3InputSourceIp OBJECT-TYPE
    SYNTAX IpAddress
    MAX-ACCESS read-write
    STATUS current
    DESCRIPTION
        "Input IGMP v3 Source IP address from which to obtain data.

         If the router supports IGMP v3 the GBE will only receive data from
         this source IP.  If Source IP is not specified or the router does not
         support IGMP v3 the GBE will receive data from any source device.
         Source IP address must be a valid singlecast address.
        "
::= { apexManRtePassThruBlade3Entry 6 }


-- ------------------------------------------------------------------------------
--
-- apexManualRouteBlade4
--
-- apexManualRouteBlade4ApplyTable
--

apexManualRouteBlade4ApplyTable OBJECT-TYPE
    SYNTAX SEQUENCE OF ApexManualRouteBlade4ApplyEntry
    MAX-ACCESS not-accessible
    STATUS current
    DESCRIPTION
        "Table of Apply Change for the data for Manual Route Table.

         A row in this table corresponds to the same row index in the
         Manual Route table.
        "
::= { apexManualRouteBlade4 1 }

apexManualRouteBlade4ApplyEntry OBJECT-TYPE
    SYNTAX ApexManualRouteBlade4ApplyEntry
    MAX-ACCESS not-accessible
    STATUS current
    DESCRIPTION
        "Manual Route Apply Table Entry."
    INDEX { apexManualRouteBlade4ApplyIndex }
::= { apexManualRouteBlade4ApplyTable 1 }

ApexManualRouteBlade4ApplyEntry ::= SEQUENCE
    {
     apexManualRouteBlade4ApplyIndex        Integer32,
     apexManualRouteBlade4ApplyChange       ApplyDataToDeviceTYPE    
    }

apexManualRouteBlade4ApplyIndex OBJECT-TYPE
    SYNTAX Integer32(1..2304)
    MAX-ACCESS not-accessible
    STATUS current
    DESCRIPTION
        "The index of the Manual Route Apply Table."
::= { apexManualRouteBlade4ApplyEntry 1 }

apexManualRouteBlade4ApplyChange OBJECT-TYPE
    SYNTAX ApplyDataToDeviceTYPE
    MAX-ACCESS read-write
    STATUS current
    DESCRIPTION
        "The Apply for the row of data in the Manual Route Table.

         A row in this table corresponds to the same row index in the
         Manual Route table.

         This parameter MUST be set to 'apply' in order for any of the data
         in the Manual Route Table row to take effect in the APEX.  This
         parameter MUST be set LAST after all other data in the Manual Route
         Table row has been configured.

         @Config(config=no, reboot=no)
        "
::= { apexManualRouteBlade4ApplyEntry 2 }

                                       
-- ------------------------------------------------------------------------------
--
-- apexManualRouteBlade4Table
--

apexManualRouteBlade4Table OBJECT-TYPE
    SYNTAX SEQUENCE OF ApexManualRouteBlade4Entry
    MAX-ACCESS not-accessible
    STATUS current
    DESCRIPTION
        "Table of data for Manual Routes.

         Once written, the change to a row this table will only take
         immediate effect after the appropriate apexManualRouteBlade4ApplyChange
         is set to 'apply'.  In order for the change to persist through
         subsequent reboots or power cycles, the change must be saved via
         the apexSaveConfig parameter.

         @Config(config=yes, reboot=no)
         @Commit(param=apexManualRouteBlade4ApplyChange, value=2)
         @Save(apexSaveConfig, value=2)
         @File(manrout4.ini, type='ini')
        "
::= { apexManualRouteBlade4 2 }

apexManualRouteBlade4Entry OBJECT-TYPE
    SYNTAX ApexManualRouteBlade4Entry
    MAX-ACCESS not-accessible
    STATUS current
    DESCRIPTION
        "Manual Route Table Entry."
    INDEX { apexManualRouteBlade4Index }
::= { apexManualRouteBlade4Table 1 }

ApexManualRouteBlade4Entry ::= SEQUENCE
    {
     apexManualRouteBlade4Index                   Integer32,
     apexManualRouteBlade4Enable                  EnableDisableTYPE,
     apexManualRouteBlade4InputInterface          Integer32,
     apexManualRouteBlade4InputUdp                Integer32,
     apexManualRouteBlade4InputMulticastIp        IpAddress,
     apexManualRouteBlade4InputSourceIp           IpAddress,
     apexManualRouteBlade4InputProgNum            Integer32,
     apexManualRouteBlade4InputPreEncryptCheck    EnableDisableTYPE,
     apexManualRouteBlade4OutputTsNum             Integer32,
     apexManualRouteBlade4OutputProgNum           Integer32,
     apexManualRouteBlade4FollowDtcp              EnableDisableTYPE
    }

apexManualRouteBlade4Index OBJECT-TYPE
    SYNTAX Integer32(1..2304)
    MAX-ACCESS not-accessible
    STATUS current
    DESCRIPTION
        "The index of the Manual Route Table."
::= { apexManualRouteBlade4Entry 1 }

apexManualRouteBlade4Enable OBJECT-TYPE
    SYNTAX EnableDisableTYPE
    MAX-ACCESS read-write
    STATUS current
    DESCRIPTION
        "Indicates that this Manual Route is enabled or disabled.
        "
::= { apexManualRouteBlade4Entry 2 }

apexManualRouteBlade4InputInterface OBJECT-TYPE
    SYNTAX Integer32(0..12)
    MAX-ACCESS read-write
    STATUS current
    DESCRIPTION
        "Number of the input GigE interface from which to obtain data.
        "
::= { apexManualRouteBlade4Entry 3 }

apexManualRouteBlade4InputUdp OBJECT-TYPE
    SYNTAX Integer32(0..65535)
    MAX-ACCESS read-write
    STATUS current
    DESCRIPTION
        "Input UDP Port from which to obtain data.
        "
::= { apexManualRouteBlade4Entry 4 }

apexManualRouteBlade4InputMulticastIp OBJECT-TYPE
    SYNTAX IpAddress
    MAX-ACCESS read-write
    STATUS current
    DESCRIPTION
        "Input Multicast IP address from which to obtain data.

         An IP address of 0.0.0.0 indicates table entry not in use.

         Multicast IP addresses 224.0.0.0 to 224.0.0.255 are reserved.
        "
::= { apexManualRouteBlade4Entry 5 }

apexManualRouteBlade4InputSourceIp OBJECT-TYPE
    SYNTAX IpAddress
    MAX-ACCESS read-write
    STATUS current
    DESCRIPTION
        "Input IGMP v3 Source IP from which to obtain data.

         If the router supports IGMP v3 the GBE will only receive data from
         this source IP.  If Source IP is not specified or the router does not
         support IGMP v3 the GBE will receive data from any source device.
         Source IP address must be a valid singlecast address.
        "
::= { apexManualRouteBlade4Entry 6 }

apexManualRouteBlade4InputProgNum OBJECT-TYPE
    SYNTAX Integer32(0..65535)
    MAX-ACCESS read-write
    STATUS current
    DESCRIPTION
        "Input MPEG Program Number to multiplex. A value of 0 can be used as
         a wild card. This will cause the APEX to map the first program listed in
         the input PAT to the specified output (regardless of input program number).
         Input program number zero should only be used when mapping Single Program
         Transport Streams (SPTS).
        "
::= { apexManualRouteBlade4Entry 7 }

apexManualRouteBlade4InputPreEncryptCheck OBJECT-TYPE
    SYNTAX EnableDisableTYPE
    MAX-ACCESS read-write
    STATUS current
    DESCRIPTION
        "Manual Routing Pre-Encryption Checking.

         Indicates if the APEX is to check if the input service is pre-encrypted or
         clear. Pre-encrypted is determined by examining the input PMT for a CA ECM
         descriptor (any CA ECM descriptor). If pre-encrypted, setting this flag will
         cause the APEX to pass through ECM PID for this service. For input services
         that have a GI CA ECM descriptor, the APEX will also pass through the PIT
         message (extract and re-insert the PIT). The output PMT for pre-encrypted
         services will contain a CA ECM descriptor (referencing the ECM
         PID). When PID Remapping is enabled, pre-encryption for a service is
         only valid when the input ECM PID is on a different PID than the
         associated PMT PID. If this flag is set to pre-encryption and the
         input service is not pre-encrypted, then the setting of this flag has
         no affect on the output service.
        "
::= { apexManualRouteBlade4Entry 8 }

apexManualRouteBlade4OutputTsNum OBJECT-TYPE
    SYNTAX Integer32(0..256)
    MAX-ACCESS read-write
    STATUS current
    DESCRIPTION
        "Output Transport Stream Number of the output on which to place data.
         Zero = NotApplicable and is only valid if the apexManualRouteBlade4Table
         entry is not being used.
        "
::= { apexManualRouteBlade4Entry 9 }

apexManualRouteBlade4OutputProgNum OBJECT-TYPE
    SYNTAX Integer32(0..65535)
    MAX-ACCESS read-write
    STATUS current
    DESCRIPTION
        "Output Program number to use for the program.
         Zero = NotApplicable and is only valid if the apexManualRouteBlade4Table
         entry is not being used.
        "
::= { apexManualRouteBlade4Entry 10 }

apexManualRouteBlade4FollowDtcp OBJECT-TYPE
    SYNTAX EnableDisableTYPE
    MAX-ACCESS read-write
    STATUS current
    DESCRIPTION
        "Determines how the copy protection settings (CCI, APS, and CIT) within 
         the PRK will be set.
         For each service, will allow user to override the RDS or user 
         configured copy protection and force the service to follow 
         the input DTCP.
        
        - Disabled    - Use CTE configured settings if output in CTE encryption mode
        - Enabled     - Follow input DTCP.                                
        "
::= { apexManualRouteBlade4Entry 11 }


-- ------------------------------------------------------------------------------
--
-- apexManRtePassThruBlade4ApplyTable
--

apexManRtePassThruBlade4ApplyTable OBJECT-TYPE
    SYNTAX SEQUENCE OF ApexManRtePassThruBlade4ApplyEntry
    MAX-ACCESS not-accessible
    STATUS current
    DESCRIPTION
        "Table of Apply Change for the data for Manual Route Pass Through Table.

         A row in this table corresponds to the same row index in the
         Manual Route Pass Through table.
        "
::= { apexManualRouteBlade4 3 }

apexManRtePassThruBlade4ApplyEntry OBJECT-TYPE
    SYNTAX ApexManRtePassThruBlade4ApplyEntry
    MAX-ACCESS not-accessible
    STATUS current
    DESCRIPTION
        "Manual Route Pass Through Apply Table Entry."
    INDEX { apexManRtePassThruBlade4ApplyOutputTsNum }
::= { apexManRtePassThruBlade4ApplyTable 1 }

ApexManRtePassThruBlade4ApplyEntry ::= SEQUENCE
    {
     apexManRtePassThruBlade4ApplyOutputTsNum   Integer32,
     apexManRtePassThruBlade4ApplyChange        ApplyDataToDeviceTYPE
    }

apexManRtePassThruBlade4ApplyOutputTsNum OBJECT-TYPE
    SYNTAX Integer32(1..256)
    MAX-ACCESS not-accessible
    STATUS current
    DESCRIPTION
        "The index of the Manual Route Pass Through Apply Table."
::= { apexManRtePassThruBlade4ApplyEntry 1 }

apexManRtePassThruBlade4ApplyChange OBJECT-TYPE
    SYNTAX ApplyDataToDeviceTYPE
    MAX-ACCESS read-write
    STATUS current
    DESCRIPTION
        "The Apply for the row of data in the Manual Route Pass Through Table.

         A row in this table corresponds to the same row index in the
         Manual Route Pass Through table.

         This parameter MUST be set to 'apply' in order for any of the
         data in the Manual Route Pass Through Table row to take effect
         in the APEX.  This parameter MUST be set LAST after all other
         data in the Manual Route Pass Through Table row has been configured.

         @Config(config=no, reboot=no)
        "
::= { apexManRtePassThruBlade4ApplyEntry 2 }


-- ------------------------------------------------------------------------------
--
-- apexManRtePassThruBlade4Table
--

apexManRtePassThruBlade4Table OBJECT-TYPE
    SYNTAX SEQUENCE OF ApexManRtePassThruBlade4Entry
    MAX-ACCESS not-accessible
    STATUS current
    DESCRIPTION
        "Table of data for Manual Route Pass Through. This table is used to
         pass through an entire input stream to an output stream.

         Once written, the change to a row this table will only take
         immediate effect after the appropriate apexManRtePassThruBlade4ApplyChange
         is set to 'apply'.  In order for the change to persist through
         subsequent reboots or power cycles, the change must be saved via
         the apexSaveConfig parameter.

         @Config(config=yes, reboot=no)
         @Commit(param=apexManRtePassThruBlade4ApplyChange, value=2)
         @Save(apexSaveConfig, value=2)
         @File(manrout4.ini, type='ini')
        "
::= { apexManualRouteBlade4 4 }

apexManRtePassThruBlade4Entry OBJECT-TYPE
    SYNTAX ApexManRtePassThruBlade4Entry
    MAX-ACCESS not-accessible
    STATUS current
    DESCRIPTION
        "Manual Route Pass Through Table Entry."
    INDEX { apexManRtePassThruBlade4OutputTsNum }
::= { apexManRtePassThruBlade4Table 1 }

ApexManRtePassThruBlade4Entry ::= SEQUENCE
    {
     apexManRtePassThruBlade4OutputTsNum        Integer32,
     apexManRtePassThruBlade4Enable             EnableDisableTYPE,
     apexManRtePassThruBlade4InputInterface     Integer32,
     apexManRtePassThruBlade4InputUdp           Integer32,
     apexManRtePassThruBlade4InputMulticastIp   IpAddress,
     apexManRtePassThruBlade4InputSourceIp      IpAddress
    }

apexManRtePassThruBlade4OutputTsNum OBJECT-TYPE
    SYNTAX Integer32(1..256)
    MAX-ACCESS not-accessible
    STATUS current
    DESCRIPTION
        "The index of the Manual Route Pass Through Table."
::= { apexManRtePassThruBlade4Entry 1 }

apexManRtePassThruBlade4Enable OBJECT-TYPE
    SYNTAX EnableDisableTYPE
    MAX-ACCESS read-write
    STATUS current
    DESCRIPTION
        "Indicates that this Manual Route Pass Through is enabled or disabled.
         An input stream can only be passed through to an output stream when
         there are no active service or PID mappings to the output stream.
        "
::= { apexManRtePassThruBlade4Entry 2 }

apexManRtePassThruBlade4InputInterface OBJECT-TYPE
    SYNTAX Integer32(0..12)
    MAX-ACCESS read-write
    STATUS current
    DESCRIPTION
        "Number of the input GigE interface from which to obtain data.
        "
::= { apexManRtePassThruBlade4Entry 3 }

apexManRtePassThruBlade4InputUdp OBJECT-TYPE
    SYNTAX Integer32(0..65535)
    MAX-ACCESS read-write
    STATUS current
    DESCRIPTION
        "Input UDP Port from which to obtain data.
        "
::= { apexManRtePassThruBlade4Entry 4 }

apexManRtePassThruBlade4InputMulticastIp OBJECT-TYPE
    SYNTAX IpAddress
    MAX-ACCESS read-write
    STATUS current
    DESCRIPTION
        "Input Multicast IP address from which to obtain data.

         An IP address of 0.0.0.0 indicates table entry not in use.

         Multicast IP addresses 224.0.0.0 to 224.0.0.255 are reserved.
        "
::= { apexManRtePassThruBlade4Entry 5 }

apexManRtePassThruBlade4InputSourceIp OBJECT-TYPE
    SYNTAX IpAddress
    MAX-ACCESS read-write
    STATUS current
    DESCRIPTION
        "Input IGMP v3 Source IP address from which to obtain data.

         If the router supports IGMP v3 the GBE will only receive data from
         this source IP.  If Source IP is not specified or the router does not
         support IGMP v3 the GBE will receive data from any source device.
         Source IP address must be a valid singlecast address.
        "
::= { apexManRtePassThruBlade4Entry 6 }


-- ------------------------------------------------------------------------------
--
-- apexManualRouteBlade5
--
-- apexManualRouteBlade5ApplyTable
--

apexManualRouteBlade5ApplyTable OBJECT-TYPE
    SYNTAX SEQUENCE OF ApexManualRouteBlade5ApplyEntry
    MAX-ACCESS not-accessible
    STATUS current
    DESCRIPTION
        "Table of Apply Change for the data for Manual Route Table.

         A row in this table corresponds to the same row index in the
         Manual Route table.
        "
::= { apexManualRouteBlade5 1 }

apexManualRouteBlade5ApplyEntry OBJECT-TYPE
    SYNTAX ApexManualRouteBlade5ApplyEntry
    MAX-ACCESS not-accessible
    STATUS current
    DESCRIPTION
        "Manual Route Apply Table Entry."
    INDEX { apexManualRouteBlade5ApplyIndex }
::= { apexManualRouteBlade5ApplyTable 1 }

ApexManualRouteBlade5ApplyEntry ::= SEQUENCE
    {
     apexManualRouteBlade5ApplyIndex        Integer32,
     apexManualRouteBlade5ApplyChange       ApplyDataToDeviceTYPE    
    }

apexManualRouteBlade5ApplyIndex OBJECT-TYPE
    SYNTAX Integer32(1..2304)
    MAX-ACCESS not-accessible
    STATUS current
    DESCRIPTION
        "The index of the Manual Route Apply Table."
::= { apexManualRouteBlade5ApplyEntry 1 }

apexManualRouteBlade5ApplyChange OBJECT-TYPE
    SYNTAX ApplyDataToDeviceTYPE
    MAX-ACCESS read-write
    STATUS current
    DESCRIPTION
        "The Apply for the row of data in the Manual Route Table.

         A row in this table corresponds to the same row index in the
         Manual Route table.

         This parameter MUST be set to 'apply' in order for any of the data
         in the Manual Route Table row to take effect in the APEX.  This
         parameter MUST be set LAST after all other data in the Manual Route
         Table row has been configured.

         @Config(config=no, reboot=no)
        "
::= { apexManualRouteBlade5ApplyEntry 2 }

                                       
-- ------------------------------------------------------------------------------
--
-- apexManualRouteBlade5Table
--

apexManualRouteBlade5Table OBJECT-TYPE
    SYNTAX SEQUENCE OF ApexManualRouteBlade5Entry
    MAX-ACCESS not-accessible
    STATUS current
    DESCRIPTION
        "Table of data for Manual Routes.

         Once written, the change to a row this table will only take
         immediate effect after the appropriate apexManualRouteBlade5ApplyChange
         is set to 'apply'.  In order for the change to persist through
         subsequent reboots or power cycles, the change must be saved via
         the apexSaveConfig parameter.

         @Config(config=yes, reboot=no)
         @Commit(param=apexManualRouteBlade5ApplyChange, value=2)
         @Save(apexSaveConfig, value=2)
         @File(manrout5.ini, type='ini')
        "
::= { apexManualRouteBlade5 2 }

apexManualRouteBlade5Entry OBJECT-TYPE
    SYNTAX ApexManualRouteBlade5Entry
    MAX-ACCESS not-accessible
    STATUS current
    DESCRIPTION
        "Manual Route Table Entry."
    INDEX { apexManualRouteBlade5Index }
::= { apexManualRouteBlade5Table 1 }

ApexManualRouteBlade5Entry ::= SEQUENCE
    {
     apexManualRouteBlade5Index                   Integer32,
     apexManualRouteBlade5Enable                  EnableDisableTYPE,
     apexManualRouteBlade5InputInterface          Integer32,
     apexManualRouteBlade5InputUdp                Integer32,
     apexManualRouteBlade5InputMulticastIp        IpAddress,
     apexManualRouteBlade5InputSourceIp           IpAddress,
     apexManualRouteBlade5InputProgNum            Integer32,
     apexManualRouteBlade5InputPreEncryptCheck    EnableDisableTYPE,
     apexManualRouteBlade5OutputTsNum             Integer32,
     apexManualRouteBlade5OutputProgNum           Integer32,
     apexManualRouteBlade5FollowDtcp              EnableDisableTYPE
    }

apexManualRouteBlade5Index OBJECT-TYPE
    SYNTAX Integer32(1..2304)
    MAX-ACCESS not-accessible
    STATUS current
    DESCRIPTION
        "The index of the Manual Route Table."
::= { apexManualRouteBlade5Entry 1 }

apexManualRouteBlade5Enable OBJECT-TYPE
    SYNTAX EnableDisableTYPE
    MAX-ACCESS read-write
    STATUS current
    DESCRIPTION
        "Indicates that this Manual Route is enabled or disabled.
        "
::= { apexManualRouteBlade5Entry 2 }

apexManualRouteBlade5InputInterface OBJECT-TYPE
    SYNTAX Integer32(0..12)
    MAX-ACCESS read-write
    STATUS current
    DESCRIPTION
        "Number of the input GigE interface from which to obtain data.
        "
::= { apexManualRouteBlade5Entry 3 }

apexManualRouteBlade5InputUdp OBJECT-TYPE
    SYNTAX Integer32(0..65535)
    MAX-ACCESS read-write
    STATUS current
    DESCRIPTION
        "Input UDP Port from which to obtain data.
        "
::= { apexManualRouteBlade5Entry 4 }

apexManualRouteBlade5InputMulticastIp OBJECT-TYPE
    SYNTAX IpAddress
    MAX-ACCESS read-write
    STATUS current
    DESCRIPTION
        "Input Multicast IP address from which to obtain data.

         An IP address of 0.0.0.0 indicates table entry not in use.

         Multicast IP addresses 224.0.0.0 to 224.0.0.255 are reserved.
        "
::= { apexManualRouteBlade5Entry 5 }

apexManualRouteBlade5InputSourceIp OBJECT-TYPE
    SYNTAX IpAddress
    MAX-ACCESS read-write
    STATUS current
    DESCRIPTION
        "Input IGMP v3 Source IP from which to obtain data.

         If the router supports IGMP v3 the GBE will only receive data from
         this source IP.  If Source IP is not specified or the router does not
         support IGMP v3 the GBE will receive data from any source device.
         Source IP address must be a valid singlecast address.
        "
::= { apexManualRouteBlade5Entry 6 }

apexManualRouteBlade5InputProgNum OBJECT-TYPE
    SYNTAX Integer32(0..65535)
    MAX-ACCESS read-write
    STATUS current
    DESCRIPTION
        "Input MPEG Program Number to multiplex. A value of 0 can be used as
         a wild card. This will cause the APEX to map the first program listed in
         the input PAT to the specified output (regardless of input program number).
         Input program number zero should only be used when mapping Single Program
         Transport Streams (SPTS).
        "
::= { apexManualRouteBlade5Entry 7 }

apexManualRouteBlade5InputPreEncryptCheck OBJECT-TYPE
    SYNTAX EnableDisableTYPE
    MAX-ACCESS read-write
    STATUS current
    DESCRIPTION
        "Manual Routing Pre-Encryption Checking.

         Indicates if the APEX is to check if the input service is pre-encrypted or
         clear. Pre-encrypted is determined by examining the input PMT for a CA ECM
         descriptor (any CA ECM descriptor). If pre-encrypted, setting this flag will
         cause the APEX to pass through ECM PID for this service. For input services
         that have a GI CA ECM descriptor, the APEX will also pass through the PIT
         message (extract and re-insert the PIT). The output PMT for pre-encrypted
         services will contain a CA ECM descriptor (referencing the ECM
         PID). When PID Remapping is enabled, pre-encryption for a service is
         only valid when the input ECM PID is on a different PID than the
         associated PMT PID. If this flag is set to pre-encryption and the
         input service is not pre-encrypted, then the setting of this flag has
         no affect on the output service.
        "
::= { apexManualRouteBlade5Entry 8 }

apexManualRouteBlade5OutputTsNum OBJECT-TYPE
    SYNTAX Integer32(0..256)
    MAX-ACCESS read-write
    STATUS current
    DESCRIPTION
        "Output Transport Stream Number of the output on which to place data.
         Zero = NotApplicable and is only valid if the apexManualRouteBlade5Table
         entry is not being used.
        "
::= { apexManualRouteBlade5Entry 9 }

apexManualRouteBlade5OutputProgNum OBJECT-TYPE
    SYNTAX Integer32(0..65535)
    MAX-ACCESS read-write
    STATUS current
    DESCRIPTION
        "Output Program number to use for the program.
         Zero = NotApplicable and is only valid if the apexManualRouteBlade5Table
         entry is not being used.
        "
::= { apexManualRouteBlade5Entry 10 }

apexManualRouteBlade5FollowDtcp OBJECT-TYPE
    SYNTAX EnableDisableTYPE
    MAX-ACCESS read-write
    STATUS current
    DESCRIPTION
        "Determines how the copy protection settings (CCI, APS, and CIT) within 
         the PRK will be set.
         For each service, will allow user to override the RDS or user 
         configured copy protection and force the service to follow 
         the input DTCP.
        
        - Disabled    - Use CTE configured settings if output in CTE encryption mode
        - Enabled     - Follow input DTCP.                                
        "
::= { apexManualRouteBlade5Entry 11 }


-- ------------------------------------------------------------------------------
--
-- apexManRtePassThruBlade5ApplyTable
--

apexManRtePassThruBlade5ApplyTable OBJECT-TYPE
    SYNTAX SEQUENCE OF ApexManRtePassThruBlade5ApplyEntry
    MAX-ACCESS not-accessible
    STATUS current
    DESCRIPTION
        "Table of Apply Change for the data for Manual Route Pass Through Table.

         A row in this table corresponds to the same row index in the
         Manual Route Pass Through table.
        "
::= { apexManualRouteBlade5 3 }

apexManRtePassThruBlade5ApplyEntry OBJECT-TYPE
    SYNTAX ApexManRtePassThruBlade5ApplyEntry
    MAX-ACCESS not-accessible
    STATUS current
    DESCRIPTION
        "Manual Route Pass Through Apply Table Entry."
    INDEX { apexManRtePassThruBlade5ApplyOutputTsNum }
::= { apexManRtePassThruBlade5ApplyTable 1 }

ApexManRtePassThruBlade5ApplyEntry ::= SEQUENCE
    {
     apexManRtePassThruBlade5ApplyOutputTsNum   Integer32,
     apexManRtePassThruBlade5ApplyChange        ApplyDataToDeviceTYPE
    }

apexManRtePassThruBlade5ApplyOutputTsNum OBJECT-TYPE
    SYNTAX Integer32(1..256)
    MAX-ACCESS not-accessible
    STATUS current
    DESCRIPTION
        "The index of the Manual Route Pass Through Apply Table."
::= { apexManRtePassThruBlade5ApplyEntry 1 }

apexManRtePassThruBlade5ApplyChange OBJECT-TYPE
    SYNTAX ApplyDataToDeviceTYPE
    MAX-ACCESS read-write
    STATUS current
    DESCRIPTION
        "The Apply for the row of data in the Manual Route Pass Through Table.

         A row in this table corresponds to the same row index in the
         Manual Route Pass Through table.

         This parameter MUST be set to 'apply' in order for any of the
         data in the Manual Route Pass Through Table row to take effect
         in the APEX.  This parameter MUST be set LAST after all other
         data in the Manual Route Pass Through Table row has been configured.

         @Config(config=no, reboot=no)
        "
::= { apexManRtePassThruBlade5ApplyEntry 2 }


-- ------------------------------------------------------------------------------
--
-- apexManRtePassThruBlade5Table
--

apexManRtePassThruBlade5Table OBJECT-TYPE
    SYNTAX SEQUENCE OF ApexManRtePassThruBlade5Entry
    MAX-ACCESS not-accessible
    STATUS current
    DESCRIPTION
        "Table of data for Manual Route Pass Through. This table is used to
         pass through an entire input stream to an output stream.

         Once written, the change to a row this table will only take
         immediate effect after the appropriate apexManRtePassThruBlade5ApplyChange
         is set to 'apply'.  In order for the change to persist through
         subsequent reboots or power cycles, the change must be saved via
         the apexSaveConfig parameter.

         @Config(config=yes, reboot=no)
         @Commit(param=apexManRtePassThruBlade5ApplyChange, value=2)
         @Save(apexSaveConfig, value=2)
         @File(manrout5.ini, type='ini')
        "
::= { apexManualRouteBlade5 4 }

apexManRtePassThruBlade5Entry OBJECT-TYPE
    SYNTAX ApexManRtePassThruBlade5Entry
    MAX-ACCESS not-accessible
    STATUS current
    DESCRIPTION
        "Manual Route Pass Through Table Entry."
    INDEX { apexManRtePassThruBlade5OutputTsNum }
::= { apexManRtePassThruBlade5Table 1 }

ApexManRtePassThruBlade5Entry ::= SEQUENCE
    {
     apexManRtePassThruBlade5OutputTsNum        Integer32,
     apexManRtePassThruBlade5Enable             EnableDisableTYPE,
     apexManRtePassThruBlade5InputInterface     Integer32,
     apexManRtePassThruBlade5InputUdp           Integer32,
     apexManRtePassThruBlade5InputMulticastIp   IpAddress,
     apexManRtePassThruBlade5InputSourceIp      IpAddress
    }

apexManRtePassThruBlade5OutputTsNum OBJECT-TYPE
    SYNTAX Integer32(1..256)
    MAX-ACCESS not-accessible
    STATUS current
    DESCRIPTION
        "The index of the Manual Route Pass Through Table."
::= { apexManRtePassThruBlade5Entry 1 }

apexManRtePassThruBlade5Enable OBJECT-TYPE
    SYNTAX EnableDisableTYPE
    MAX-ACCESS read-write
    STATUS current
    DESCRIPTION
        "Indicates that this Manual Route Pass Through is enabled or disabled.
         An input stream can only be passed through to an output stream when
         there are no active service or PID mappings to the output stream.
        "
::= { apexManRtePassThruBlade5Entry 2 }

apexManRtePassThruBlade5InputInterface OBJECT-TYPE
    SYNTAX Integer32(0..12)
    MAX-ACCESS read-write
    STATUS current
    DESCRIPTION
        "Number of the input GigE interface from which to obtain data.
        "
::= { apexManRtePassThruBlade5Entry 3 }

apexManRtePassThruBlade5InputUdp OBJECT-TYPE
    SYNTAX Integer32(0..65535)
    MAX-ACCESS read-write
    STATUS current
    DESCRIPTION
        "Input UDP Port from which to obtain data.
        "
::= { apexManRtePassThruBlade5Entry 4 }

apexManRtePassThruBlade5InputMulticastIp OBJECT-TYPE
    SYNTAX IpAddress
    MAX-ACCESS read-write
    STATUS current
    DESCRIPTION
        "Input Multicast IP address from which to obtain data.

         An IP address of 0.0.0.0 indicates table entry not in use.

         Multicast IP addresses 224.0.0.0 to 224.0.0.255 are reserved.
        "
::= { apexManRtePassThruBlade5Entry 5 }

apexManRtePassThruBlade5InputSourceIp OBJECT-TYPE
    SYNTAX IpAddress
    MAX-ACCESS read-write
    STATUS current
    DESCRIPTION
        "Input IGMP v3 Source IP address from which to obtain data.

         If the router supports IGMP v3 the GBE will only receive data from
         this source IP.  If Source IP is not specified or the router does not
         support IGMP v3 the GBE will receive data from any source device.
         Source IP address must be a valid singlecast address.
        "
::= { apexManRtePassThruBlade5Entry 6 }


-- ------------------------------------------------------------------------------
--
-- apexManualRouteBlade6
--
-- apexManualRouteBlade6ApplyTable
--

apexManualRouteBlade6ApplyTable OBJECT-TYPE
    SYNTAX SEQUENCE OF ApexManualRouteBlade6ApplyEntry
    MAX-ACCESS not-accessible
    STATUS current
    DESCRIPTION
        "Table of Apply Change for the data for Manual Route Table.

         A row in this table corresponds to the same row index in the
         Manual Route table.
        "
::= { apexManualRouteBlade6 1 }

apexManualRouteBlade6ApplyEntry OBJECT-TYPE
    SYNTAX ApexManualRouteBlade6ApplyEntry
    MAX-ACCESS not-accessible
    STATUS current
    DESCRIPTION
        "Manual Route Apply Table Entry."
    INDEX { apexManualRouteBlade6ApplyIndex }
::= { apexManualRouteBlade6ApplyTable 1 }

ApexManualRouteBlade6ApplyEntry ::= SEQUENCE
    {
     apexManualRouteBlade6ApplyIndex        Integer32,
     apexManualRouteBlade6ApplyChange       ApplyDataToDeviceTYPE    
    }

apexManualRouteBlade6ApplyIndex OBJECT-TYPE
    SYNTAX Integer32(1..2304)
    MAX-ACCESS not-accessible
    STATUS current
    DESCRIPTION
        "The index of the Manual Route Apply Table."
::= { apexManualRouteBlade6ApplyEntry 1 }

apexManualRouteBlade6ApplyChange OBJECT-TYPE
    SYNTAX ApplyDataToDeviceTYPE
    MAX-ACCESS read-write
    STATUS current
    DESCRIPTION
        "The Apply for the row of data in the Manual Route Table.

         A row in this table corresponds to the same row index in the
         Manual Route table.

         This parameter MUST be set to 'apply' in order for any of the data
         in the Manual Route Table row to take effect in the APEX.  This
         parameter MUST be set LAST after all other data in the Manual Route
         Table row has been configured.

         @Config(config=no, reboot=no)
        "
::= { apexManualRouteBlade6ApplyEntry 2 }

                                       
-- ------------------------------------------------------------------------------
--
-- apexManualRouteBlade6Table
--

apexManualRouteBlade6Table OBJECT-TYPE
    SYNTAX SEQUENCE OF ApexManualRouteBlade6Entry
    MAX-ACCESS not-accessible
    STATUS current
    DESCRIPTION
        "Table of data for Manual Routes.

         Once written, the change to a row this table will only take
         immediate effect after the appropriate apexManualRouteBlade6ApplyChange
         is set to 'apply'.  In order for the change to persist through
         subsequent reboots or power cycles, the change must be saved via
         the apexSaveConfig parameter.

         @Config(config=yes, reboot=no)
         @Commit(param=apexManualRouteBlade6ApplyChange, value=2)
         @Save(apexSaveConfig, value=2)
         @File(manrout6.ini, type='ini')
        "
::= { apexManualRouteBlade6 2 }

apexManualRouteBlade6Entry OBJECT-TYPE
    SYNTAX ApexManualRouteBlade6Entry
    MAX-ACCESS not-accessible
    STATUS current
    DESCRIPTION
        "Manual Route Table Entry."
    INDEX { apexManualRouteBlade6Index }
::= { apexManualRouteBlade6Table 1 }

ApexManualRouteBlade6Entry ::= SEQUENCE
    {
     apexManualRouteBlade6Index                   Integer32,
     apexManualRouteBlade6Enable                  EnableDisableTYPE,
     apexManualRouteBlade6InputInterface          Integer32,
     apexManualRouteBlade6InputUdp                Integer32,
     apexManualRouteBlade6InputMulticastIp        IpAddress,
     apexManualRouteBlade6InputSourceIp           IpAddress,
     apexManualRouteBlade6InputProgNum            Integer32,
     apexManualRouteBlade6InputPreEncryptCheck    EnableDisableTYPE,
     apexManualRouteBlade6OutputTsNum             Integer32,
     apexManualRouteBlade6OutputProgNum           Integer32,
     apexManualRouteBlade6FollowDtcp              EnableDisableTYPE
    }

apexManualRouteBlade6Index OBJECT-TYPE
    SYNTAX Integer32(1..2304)
    MAX-ACCESS not-accessible
    STATUS current
    DESCRIPTION
        "The index of the Manual Route Table."
::= { apexManualRouteBlade6Entry 1 }

apexManualRouteBlade6Enable OBJECT-TYPE
    SYNTAX EnableDisableTYPE
    MAX-ACCESS read-write
    STATUS current
    DESCRIPTION
        "Indicates that this Manual Route is enabled or disabled.
        "
::= { apexManualRouteBlade6Entry 2 }

apexManualRouteBlade6InputInterface OBJECT-TYPE
    SYNTAX Integer32(0..12)
    MAX-ACCESS read-write
    STATUS current
    DESCRIPTION
        "Number of the input GigE interface from which to obtain data.
        "
::= { apexManualRouteBlade6Entry 3 }

apexManualRouteBlade6InputUdp OBJECT-TYPE
    SYNTAX Integer32(0..65535)
    MAX-ACCESS read-write
    STATUS current
    DESCRIPTION
        "Input UDP Port from which to obtain data.
        "
::= { apexManualRouteBlade6Entry 4 }

apexManualRouteBlade6InputMulticastIp OBJECT-TYPE
    SYNTAX IpAddress
    MAX-ACCESS read-write
    STATUS current
    DESCRIPTION
        "Input Multicast IP address from which to obtain data.

         An IP address of 0.0.0.0 indicates table entry not in use.

         Multicast IP addresses 224.0.0.0 to 224.0.0.255 are reserved.
        "
::= { apexManualRouteBlade6Entry 5 }

apexManualRouteBlade6InputSourceIp OBJECT-TYPE
    SYNTAX IpAddress
    MAX-ACCESS read-write
    STATUS current
    DESCRIPTION
        "Input IGMP v3 Source IP from which to obtain data.

         If the router supports IGMP v3 the GBE will only receive data from
         this source IP.  If Source IP is not specified or the router does not
         support IGMP v3 the GBE will receive data from any source device.
         Source IP address must be a valid singlecast address.
        "
::= { apexManualRouteBlade6Entry 6 }

apexManualRouteBlade6InputProgNum OBJECT-TYPE
    SYNTAX Integer32(0..65535)
    MAX-ACCESS read-write
    STATUS current
    DESCRIPTION
        "Input MPEG Program Number to multiplex. A value of 0 can be used as
         a wild card. This will cause the APEX to map the first program listed in
         the input PAT to the specified output (regardless of input program number).
         Input program number zero should only be used when mapping Single Program
         Transport Streams (SPTS).
        "
::= { apexManualRouteBlade6Entry 7 }

apexManualRouteBlade6InputPreEncryptCheck OBJECT-TYPE
    SYNTAX EnableDisableTYPE
    MAX-ACCESS read-write
    STATUS current
    DESCRIPTION
        "Manual Routing Pre-Encryption Checking.

         Indicates if the APEX is to check if the input service is pre-encrypted or
         clear. Pre-encrypted is determined by examining the input PMT for a CA ECM
         descriptor (any CA ECM descriptor). If pre-encrypted, setting this flag will
         cause the APEX to pass through ECM PID for this service. For input services
         that have a GI CA ECM descriptor, the APEX will also pass through the PIT
         message (extract and re-insert the PIT). The output PMT for pre-encrypted
         services will contain a CA ECM descriptor (referencing the ECM
         PID). When PID Remapping is enabled, pre-encryption for a service is
         only valid when the input ECM PID is on a different PID than the
         associated PMT PID. If this flag is set to pre-encryption and the
         input service is not pre-encrypted, then the setting of this flag has
         no affect on the output service.
        "
::= { apexManualRouteBlade6Entry 8 }

apexManualRouteBlade6OutputTsNum OBJECT-TYPE
    SYNTAX Integer32(0..256)
    MAX-ACCESS read-write
    STATUS current
    DESCRIPTION
        "Output Transport Stream Number of the output on which to place data.
         Zero = NotApplicable and is only valid if the apexManualRouteBlade6Table
         entry is not being used.
        "
::= { apexManualRouteBlade6Entry 9 }

apexManualRouteBlade6OutputProgNum OBJECT-TYPE
    SYNTAX Integer32(0..65535)
    MAX-ACCESS read-write
    STATUS current
    DESCRIPTION
        "Output Program number to use for the program.
         Zero = NotApplicable and is only valid if the apexManualRouteBlade6Table
         entry is not being used.
        "
::= { apexManualRouteBlade6Entry 10 }

apexManualRouteBlade6FollowDtcp OBJECT-TYPE
    SYNTAX EnableDisableTYPE
    MAX-ACCESS read-write
    STATUS current
    DESCRIPTION
        "Determines how the copy protection settings (CCI, APS, and CIT) within 
         the PRK will be set.
         For each service, will allow user to override the RDS or user 
         configured copy protection and force the service to follow 
         the input DTCP.
        
        - Disabled    - Use CTE configured settings if output in CTE encryption mode
        - Enabled     - Follow input DTCP.                                
        "
::= { apexManualRouteBlade6Entry 11 }


-- ------------------------------------------------------------------------------
--
-- apexManRtePassThruBlade6ApplyTable
--

apexManRtePassThruBlade6ApplyTable OBJECT-TYPE
    SYNTAX SEQUENCE OF ApexManRtePassThruBlade6ApplyEntry
    MAX-ACCESS not-accessible
    STATUS current
    DESCRIPTION
        "Table of Apply Change for the data for Manual Route Pass Through Table.

         A row in this table corresponds to the same row index in the
         Manual Route Pass Through table.
        "
::= { apexManualRouteBlade6 3 }

apexManRtePassThruBlade6ApplyEntry OBJECT-TYPE
    SYNTAX ApexManRtePassThruBlade6ApplyEntry
    MAX-ACCESS not-accessible
    STATUS current
    DESCRIPTION
        "Manual Route Pass Through Apply Table Entry."
    INDEX { apexManRtePassThruBlade6ApplyOutputTsNum }
::= { apexManRtePassThruBlade6ApplyTable 1 }

ApexManRtePassThruBlade6ApplyEntry ::= SEQUENCE
    {
     apexManRtePassThruBlade6ApplyOutputTsNum   Integer32,
     apexManRtePassThruBlade6ApplyChange        ApplyDataToDeviceTYPE
    }

apexManRtePassThruBlade6ApplyOutputTsNum OBJECT-TYPE
    SYNTAX Integer32(1..256)
    MAX-ACCESS not-accessible
    STATUS current
    DESCRIPTION
        "The index of the Manual Route Pass Through Apply Table."
::= { apexManRtePassThruBlade6ApplyEntry 1 }

apexManRtePassThruBlade6ApplyChange OBJECT-TYPE
    SYNTAX ApplyDataToDeviceTYPE
    MAX-ACCESS read-write
    STATUS current
    DESCRIPTION
        "The Apply for the row of data in the Manual Route Pass Through Table.

         A row in this table corresponds to the same row index in the
         Manual Route Pass Through table.

         This parameter MUST be set to 'apply' in order for any of the
         data in the Manual Route Pass Through Table row to take effect
         in the APEX.  This parameter MUST be set LAST after all other
         data in the Manual Route Pass Through Table row has been configured.

         @Config(config=no, reboot=no)
        "
::= { apexManRtePassThruBlade6ApplyEntry 2 }


-- ------------------------------------------------------------------------------
--
-- apexManRtePassThruBlade6Table
--

apexManRtePassThruBlade6Table OBJECT-TYPE
    SYNTAX SEQUENCE OF ApexManRtePassThruBlade6Entry
    MAX-ACCESS not-accessible
    STATUS current
    DESCRIPTION
        "Table of data for Manual Route Pass Through. This table is used to
         pass through an entire input stream to an output stream.

         Once written, the change to a row this table will only take
         immediate effect after the appropriate apexManRtePassThruBlade6ApplyChange
         is set to 'apply'.  In order for the change to persist through
         subsequent reboots or power cycles, the change must be saved via
         the apexSaveConfig parameter.

         @Config(config=yes, reboot=no)
         @Commit(param=apexManRtePassThruBlade6ApplyChange, value=2)
         @Save(apexSaveConfig, value=2)
         @File(manrout6.ini, type='ini')
        "
::= { apexManualRouteBlade6 4 }

apexManRtePassThruBlade6Entry OBJECT-TYPE
    SYNTAX ApexManRtePassThruBlade6Entry
    MAX-ACCESS not-accessible
    STATUS current
    DESCRIPTION
        "Manual Route Pass Through Table Entry."
    INDEX { apexManRtePassThruBlade6OutputTsNum }
::= { apexManRtePassThruBlade6Table 1 }

ApexManRtePassThruBlade6Entry ::= SEQUENCE
    {
     apexManRtePassThruBlade6OutputTsNum        Integer32,
     apexManRtePassThruBlade6Enable             EnableDisableTYPE,
     apexManRtePassThruBlade6InputInterface     Integer32,
     apexManRtePassThruBlade6InputUdp           Integer32,
     apexManRtePassThruBlade6InputMulticastIp   IpAddress,
     apexManRtePassThruBlade6InputSourceIp      IpAddress
    }

apexManRtePassThruBlade6OutputTsNum OBJECT-TYPE
    SYNTAX Integer32(1..256)
    MAX-ACCESS not-accessible
    STATUS current
    DESCRIPTION
        "The index of the Manual Route Pass Through Table."
::= { apexManRtePassThruBlade6Entry 1 }

apexManRtePassThruBlade6Enable OBJECT-TYPE
    SYNTAX EnableDisableTYPE
    MAX-ACCESS read-write
    STATUS current
    DESCRIPTION
        "Indicates that this Manual Route Pass Through is enabled or disabled.
         An input stream can only be passed through to an output stream when
         there are no active service or PID mappings to the output stream.
        "
::= { apexManRtePassThruBlade6Entry 2 }

apexManRtePassThruBlade6InputInterface OBJECT-TYPE
    SYNTAX Integer32(0..12)
    MAX-ACCESS read-write
    STATUS current
    DESCRIPTION
        "Number of the input GigE interface from which to obtain data.
        "
::= { apexManRtePassThruBlade6Entry 3 }

apexManRtePassThruBlade6InputUdp OBJECT-TYPE
    SYNTAX Integer32(0..65535)
    MAX-ACCESS read-write
    STATUS current
    DESCRIPTION
        "Input UDP Port from which to obtain data.
        "
::= { apexManRtePassThruBlade6Entry 4 }

apexManRtePassThruBlade6InputMulticastIp OBJECT-TYPE
    SYNTAX IpAddress
    MAX-ACCESS read-write
    STATUS current
    DESCRIPTION
        "Input Multicast IP address from which to obtain data.

         An IP address of 0.0.0.0 indicates table entry not in use.

         Multicast IP addresses 224.0.0.0 to 224.0.0.255 are reserved.
        "
::= { apexManRtePassThruBlade6Entry 5 }

apexManRtePassThruBlade6InputSourceIp OBJECT-TYPE
    SYNTAX IpAddress
    MAX-ACCESS read-write
    STATUS current
    DESCRIPTION
        "Input IGMP v3 Source IP address from which to obtain data.

         If the router supports IGMP v3 the GBE will only receive data from
         this source IP.  If Source IP is not specified or the router does not
         support IGMP v3 the GBE will receive data from any source device.
         Source IP address must be a valid singlecast address.
        "
::= { apexManRtePassThruBlade6Entry 6 }


-- ------------------------------------------------------------------------------
--
-- apexManualRouteBlade7
--
-- apexManualRouteBlade7ApplyTable
--

apexManualRouteBlade7ApplyTable OBJECT-TYPE
    SYNTAX SEQUENCE OF ApexManualRouteBlade7ApplyEntry
    MAX-ACCESS not-accessible
    STATUS current
    DESCRIPTION
        "Table of Apply Change for the data for Manual Route Table.

         A row in this table corresponds to the same row index in the
         Manual Route table.
        "
::= { apexManualRouteBlade7 1 }

apexManualRouteBlade7ApplyEntry OBJECT-TYPE
    SYNTAX ApexManualRouteBlade7ApplyEntry
    MAX-ACCESS not-accessible
    STATUS current
    DESCRIPTION
        "Manual Route Apply Table Entry."
    INDEX { apexManualRouteBlade7ApplyIndex }
::= { apexManualRouteBlade7ApplyTable 1 }

ApexManualRouteBlade7ApplyEntry ::= SEQUENCE
    {
     apexManualRouteBlade7ApplyIndex        Integer32,
     apexManualRouteBlade7ApplyChange       ApplyDataToDeviceTYPE    
    }

apexManualRouteBlade7ApplyIndex OBJECT-TYPE
    SYNTAX Integer32(1..2304)
    MAX-ACCESS not-accessible
    STATUS current
    DESCRIPTION
        "The index of the Manual Route Apply Table."
::= { apexManualRouteBlade7ApplyEntry 1 }

apexManualRouteBlade7ApplyChange OBJECT-TYPE
    SYNTAX ApplyDataToDeviceTYPE
    MAX-ACCESS read-write
    STATUS current
    DESCRIPTION
        "The Apply for the row of data in the Manual Route Table.

         A row in this table corresponds to the same row index in the
         Manual Route table.

         This parameter MUST be set to 'apply' in order for any of the data
         in the Manual Route Table row to take effect in the APEX.  This
         parameter MUST be set LAST after all other data in the Manual Route
         Table row has been configured.

         @Config(config=no, reboot=no)
        "
::= { apexManualRouteBlade7ApplyEntry 2 }

                                       
-- ------------------------------------------------------------------------------
--
-- apexManualRouteBlade7Table
--

apexManualRouteBlade7Table OBJECT-TYPE
    SYNTAX SEQUENCE OF ApexManualRouteBlade7Entry
    MAX-ACCESS not-accessible
    STATUS current
    DESCRIPTION
        "Table of data for Manual Routes.

         Once written, the change to a row this table will only take
         immediate effect after the appropriate apexManualRouteBlade7ApplyChange
         is set to 'apply'.  In order for the change to persist through
         subsequent reboots or power cycles, the change must be saved via
         the apexSaveConfig parameter.

         @Config(config=yes, reboot=no)
         @Commit(param=apexManualRouteBlade7ApplyChange, value=2)
         @Save(apexSaveConfig, value=2)
         @File(manrout7.ini, type='ini')
        "
::= { apexManualRouteBlade7 2 }

apexManualRouteBlade7Entry OBJECT-TYPE
    SYNTAX ApexManualRouteBlade7Entry
    MAX-ACCESS not-accessible
    STATUS current
    DESCRIPTION
        "Manual Route Table Entry."
    INDEX { apexManualRouteBlade7Index }
::= { apexManualRouteBlade7Table 1 }

ApexManualRouteBlade7Entry ::= SEQUENCE
    {
     apexManualRouteBlade7Index                   Integer32,
     apexManualRouteBlade7Enable                  EnableDisableTYPE,
     apexManualRouteBlade7InputInterface          Integer32,
     apexManualRouteBlade7InputUdp                Integer32,
     apexManualRouteBlade7InputMulticastIp        IpAddress,
     apexManualRouteBlade7InputSourceIp           IpAddress,
     apexManualRouteBlade7InputProgNum            Integer32,
     apexManualRouteBlade7InputPreEncryptCheck    EnableDisableTYPE,
     apexManualRouteBlade7OutputTsNum             Integer32,
     apexManualRouteBlade7OutputProgNum           Integer32,
     apexManualRouteBlade7FollowDtcp              EnableDisableTYPE
    }

apexManualRouteBlade7Index OBJECT-TYPE
    SYNTAX Integer32(1..2304)
    MAX-ACCESS not-accessible
    STATUS current
    DESCRIPTION
        "The index of the Manual Route Table."
::= { apexManualRouteBlade7Entry 1 }

apexManualRouteBlade7Enable OBJECT-TYPE
    SYNTAX EnableDisableTYPE
    MAX-ACCESS read-write
    STATUS current
    DESCRIPTION
        "Indicates that this Manual Route is enabled or disabled.
        "
::= { apexManualRouteBlade7Entry 2 }

apexManualRouteBlade7InputInterface OBJECT-TYPE
    SYNTAX Integer32(0..12)
    MAX-ACCESS read-write
    STATUS current
    DESCRIPTION
        "Number of the input GigE interface from which to obtain data.
        "
::= { apexManualRouteBlade7Entry 3 }

apexManualRouteBlade7InputUdp OBJECT-TYPE
    SYNTAX Integer32(0..65535)
    MAX-ACCESS read-write
    STATUS current
    DESCRIPTION
        "Input UDP Port from which to obtain data.
        "
::= { apexManualRouteBlade7Entry 4 }

apexManualRouteBlade7InputMulticastIp OBJECT-TYPE
    SYNTAX IpAddress
    MAX-ACCESS read-write
    STATUS current
    DESCRIPTION
        "Input Multicast IP address from which to obtain data.

         An IP address of 0.0.0.0 indicates table entry not in use.

         Multicast IP addresses 224.0.0.0 to 224.0.0.255 are reserved.
        "
::= { apexManualRouteBlade7Entry 5 }

apexManualRouteBlade7InputSourceIp OBJECT-TYPE
    SYNTAX IpAddress
    MAX-ACCESS read-write
    STATUS current
    DESCRIPTION
        "Input IGMP v3 Source IP from which to obtain data.

         If the router supports IGMP v3 the GBE will only receive data from
         this source IP.  If Source IP is not specified or the router does not
         support IGMP v3 the GBE will receive data from any source device.
         Source IP address must be a valid singlecast address.
        "
::= { apexManualRouteBlade7Entry 6 }

apexManualRouteBlade7InputProgNum OBJECT-TYPE
    SYNTAX Integer32(0..65535)
    MAX-ACCESS read-write
    STATUS current
    DESCRIPTION
        "Input MPEG Program Number to multiplex. A value of 0 can be used as
         a wild card. This will cause the APEX to map the first program listed in
         the input PAT to the specified output (regardless of input program number).
         Input program number zero should only be used when mapping Single Program
         Transport Streams (SPTS).
        "
::= { apexManualRouteBlade7Entry 7 }

apexManualRouteBlade7InputPreEncryptCheck OBJECT-TYPE
    SYNTAX EnableDisableTYPE
    MAX-ACCESS read-write
    STATUS current
    DESCRIPTION
        "Manual Routing Pre-Encryption Checking.

         Indicates if the APEX is to check if the input service is pre-encrypted or
         clear. Pre-encrypted is determined by examining the input PMT for a CA ECM
         descriptor (any CA ECM descriptor). If pre-encrypted, setting this flag will
         cause the APEX to pass through ECM PID for this service. For input services
         that have a GI CA ECM descriptor, the APEX will also pass through the PIT
         message (extract and re-insert the PIT). The output PMT for pre-encrypted
         services will contain a CA ECM descriptor (referencing the ECM
         PID). When PID Remapping is enabled, pre-encryption for a service is
         only valid when the input ECM PID is on a different PID than the
         associated PMT PID. If this flag is set to pre-encryption and the
         input service is not pre-encrypted, then the setting of this flag has
         no affect on the output service.
        "
::= { apexManualRouteBlade7Entry 8 }

apexManualRouteBlade7OutputTsNum OBJECT-TYPE
    SYNTAX Integer32(0..256)
    MAX-ACCESS read-write
    STATUS current
    DESCRIPTION
        "Output Transport Stream Number of the output on which to place data.
         Zero = NotApplicable and is only valid if the apexManualRouteBlade7Table
         entry is not being used.
        "
::= { apexManualRouteBlade7Entry 9 }

apexManualRouteBlade7OutputProgNum OBJECT-TYPE
    SYNTAX Integer32(0..65535)
    MAX-ACCESS read-write
    STATUS current
    DESCRIPTION
        "Output Program number to use for the program.
         Zero = NotApplicable and is only valid if the apexManualRouteBlade7Table
         entry is not being used.
        "
::= { apexManualRouteBlade7Entry 10 }

apexManualRouteBlade7FollowDtcp OBJECT-TYPE
    SYNTAX EnableDisableTYPE
    MAX-ACCESS read-write
    STATUS current
    DESCRIPTION
        "Determines how the copy protection settings (CCI, APS, and CIT) within 
         the PRK will be set.
         For each service, will allow user to override the RDS or user 
         configured copy protection and force the service to follow 
         the input DTCP.
        
        - Disabled    - Use CTE configured settings if output in CTE encryption mode
        - Enabled     - Follow input DTCP.                                
        "
::= { apexManualRouteBlade7Entry 11 }


-- ------------------------------------------------------------------------------
--
-- apexManRtePassThruBlade7ApplyTable
--

apexManRtePassThruBlade7ApplyTable OBJECT-TYPE
    SYNTAX SEQUENCE OF ApexManRtePassThruBlade7ApplyEntry
    MAX-ACCESS not-accessible
    STATUS current
    DESCRIPTION
        "Table of Apply Change for the data for Manual Route Pass Through Table.

         A row in this table corresponds to the same row index in the
         Manual Route Pass Through table.
        "
::= { apexManualRouteBlade7 3 }

apexManRtePassThruBlade7ApplyEntry OBJECT-TYPE
    SYNTAX ApexManRtePassThruBlade7ApplyEntry
    MAX-ACCESS not-accessible
    STATUS current
    DESCRIPTION
        "Manual Route Pass Through Apply Table Entry."
    INDEX { apexManRtePassThruBlade7ApplyOutputTsNum }
::= { apexManRtePassThruBlade7ApplyTable 1 }

ApexManRtePassThruBlade7ApplyEntry ::= SEQUENCE
    {
     apexManRtePassThruBlade7ApplyOutputTsNum   Integer32,
     apexManRtePassThruBlade7ApplyChange        ApplyDataToDeviceTYPE
    }

apexManRtePassThruBlade7ApplyOutputTsNum OBJECT-TYPE
    SYNTAX Integer32(1..256)
    MAX-ACCESS not-accessible
    STATUS current
    DESCRIPTION
        "The index of the Manual Route Pass Through Apply Table."
::= { apexManRtePassThruBlade7ApplyEntry 1 }

apexManRtePassThruBlade7ApplyChange OBJECT-TYPE
    SYNTAX ApplyDataToDeviceTYPE
    MAX-ACCESS read-write
    STATUS current
    DESCRIPTION
        "The Apply for the row of data in the Manual Route Pass Through Table.

         A row in this table corresponds to the same row index in the
         Manual Route Pass Through table.

         This parameter MUST be set to 'apply' in order for any of the
         data in the Manual Route Pass Through Table row to take effect
         in the APEX.  This parameter MUST be set LAST after all other
         data in the Manual Route Pass Through Table row has been configured.

         @Config(config=no, reboot=no)
        "
::= { apexManRtePassThruBlade7ApplyEntry 2 }


-- ------------------------------------------------------------------------------
--
-- apexManRtePassThruBlade7Table
--

apexManRtePassThruBlade7Table OBJECT-TYPE
    SYNTAX SEQUENCE OF ApexManRtePassThruBlade7Entry
    MAX-ACCESS not-accessible
    STATUS current
    DESCRIPTION
        "Table of data for Manual Route Pass Through. This table is used to
         pass through an entire input stream to an output stream.

         Once written, the change to a row this table will only take
         immediate effect after the appropriate apexManRtePassThruBlade7ApplyChange
         is set to 'apply'.  In order for the change to persist through
         subsequent reboots or power cycles, the change must be saved via
         the apexSaveConfig parameter.

         @Config(config=yes, reboot=no)
         @Commit(param=apexManRtePassThruBlade7ApplyChange, value=2)
         @Save(apexSaveConfig, value=2)
         @File(manrout7.ini, type='ini')
        "
::= { apexManualRouteBlade7 4 }

apexManRtePassThruBlade7Entry OBJECT-TYPE
    SYNTAX ApexManRtePassThruBlade7Entry
    MAX-ACCESS not-accessible
    STATUS current
    DESCRIPTION
        "Manual Route Pass Through Table Entry."
    INDEX { apexManRtePassThruBlade7OutputTsNum }
::= { apexManRtePassThruBlade7Table 1 }

ApexManRtePassThruBlade7Entry ::= SEQUENCE
    {
     apexManRtePassThruBlade7OutputTsNum        Integer32,
     apexManRtePassThruBlade7Enable             EnableDisableTYPE,
     apexManRtePassThruBlade7InputInterface     Integer32,
     apexManRtePassThruBlade7InputUdp           Integer32,
     apexManRtePassThruBlade7InputMulticastIp   IpAddress,
     apexManRtePassThruBlade7InputSourceIp      IpAddress
    }

apexManRtePassThruBlade7OutputTsNum OBJECT-TYPE
    SYNTAX Integer32(1..256)
    MAX-ACCESS not-accessible
    STATUS current
    DESCRIPTION
        "The index of the Manual Route Pass Through Table."
::= { apexManRtePassThruBlade7Entry 1 }

apexManRtePassThruBlade7Enable OBJECT-TYPE
    SYNTAX EnableDisableTYPE
    MAX-ACCESS read-write
    STATUS current
    DESCRIPTION
        "Indicates that this Manual Route Pass Through is enabled or disabled.
         An input stream can only be passed through to an output stream when
         there are no active service or PID mappings to the output stream.
        "
::= { apexManRtePassThruBlade7Entry 2 }

apexManRtePassThruBlade7InputInterface OBJECT-TYPE
    SYNTAX Integer32(0..12)
    MAX-ACCESS read-write
    STATUS current
    DESCRIPTION
        "Number of the input GigE interface from which to obtain data.
        "
::= { apexManRtePassThruBlade7Entry 3 }

apexManRtePassThruBlade7InputUdp OBJECT-TYPE
    SYNTAX Integer32(0..65535)
    MAX-ACCESS read-write
    STATUS current
    DESCRIPTION
        "Input UDP Port from which to obtain data.
        "
::= { apexManRtePassThruBlade7Entry 4 }

apexManRtePassThruBlade7InputMulticastIp OBJECT-TYPE
    SYNTAX IpAddress
    MAX-ACCESS read-write
    STATUS current
    DESCRIPTION
        "Input Multicast IP address from which to obtain data.

         An IP address of 0.0.0.0 indicates table entry not in use.

         Multicast IP addresses 224.0.0.0 to 224.0.0.255 are reserved.
        "
::= { apexManRtePassThruBlade7Entry 5 }

apexManRtePassThruBlade7InputSourceIp OBJECT-TYPE
    SYNTAX IpAddress
    MAX-ACCESS read-write
    STATUS current
    DESCRIPTION
        "Input IGMP v3 Source IP address from which to obtain data.

         If the router supports IGMP v3 the GBE will only receive data from
         this source IP.  If Source IP is not specified or the router does not
         support IGMP v3 the GBE will receive data from any source device.
         Source IP address must be a valid singlecast address.
        "
::= { apexManRtePassThruBlade7Entry 6 }


-- ------------------------------------------------------------------------------
--
-- apexManualRouteBlade8
--
-- apexManualRouteBlade8ApplyTable
--

apexManualRouteBlade8ApplyTable OBJECT-TYPE
    SYNTAX SEQUENCE OF ApexManualRouteBlade8ApplyEntry
    MAX-ACCESS not-accessible
    STATUS current
    DESCRIPTION
        "Table of Apply Change for the data for Manual Route Table.

         A row in this table corresponds to the same row index in the
         Manual Route table.
        "
::= { apexManualRouteBlade8 1 }

apexManualRouteBlade8ApplyEntry OBJECT-TYPE
    SYNTAX ApexManualRouteBlade8ApplyEntry
    MAX-ACCESS not-accessible
    STATUS current
    DESCRIPTION
        "Manual Route Apply Table Entry."
    INDEX { apexManualRouteBlade8ApplyIndex }
::= { apexManualRouteBlade8ApplyTable 1 }

ApexManualRouteBlade8ApplyEntry ::= SEQUENCE
    {
     apexManualRouteBlade8ApplyIndex        Integer32,
     apexManualRouteBlade8ApplyChange       ApplyDataToDeviceTYPE    
    }

apexManualRouteBlade8ApplyIndex OBJECT-TYPE
    SYNTAX Integer32(1..2304)
    MAX-ACCESS not-accessible
    STATUS current
    DESCRIPTION
        "The index of the Manual Route Apply Table."
::= { apexManualRouteBlade8ApplyEntry 1 }

apexManualRouteBlade8ApplyChange OBJECT-TYPE
    SYNTAX ApplyDataToDeviceTYPE
    MAX-ACCESS read-write
    STATUS current
    DESCRIPTION
        "The Apply for the row of data in the Manual Route Table.

         A row in this table corresponds to the same row index in the
         Manual Route table.

         This parameter MUST be set to 'apply' in order for any of the data
         in the Manual Route Table row to take effect in the APEX.  This
         parameter MUST be set LAST after all other data in the Manual Route
         Table row has been configured.

         @Config(config=no, reboot=no)
        "
::= { apexManualRouteBlade8ApplyEntry 2 }

                                       
-- ------------------------------------------------------------------------------
--
-- apexManualRouteBlade8Table
--

apexManualRouteBlade8Table OBJECT-TYPE
    SYNTAX SEQUENCE OF ApexManualRouteBlade8Entry
    MAX-ACCESS not-accessible
    STATUS current
    DESCRIPTION
        "Table of data for Manual Routes.

         Once written, the change to a row this table will only take
         immediate effect after the appropriate apexManualRouteBlade8ApplyChange
         is set to 'apply'.  In order for the change to persist through
         subsequent reboots or power cycles, the change must be saved via
         the apexSaveConfig parameter.

         @Config(config=yes, reboot=no)
         @Commit(param=apexManualRouteBlade8ApplyChange, value=2)
         @Save(apexSaveConfig, value=2)
         @File(manrout8.ini, type='ini')
        "
::= { apexManualRouteBlade8 2 }

apexManualRouteBlade8Entry OBJECT-TYPE
    SYNTAX ApexManualRouteBlade8Entry
    MAX-ACCESS not-accessible
    STATUS current
    DESCRIPTION
        "Manual Route Table Entry."
    INDEX { apexManualRouteBlade8Index }
::= { apexManualRouteBlade8Table 1 }

ApexManualRouteBlade8Entry ::= SEQUENCE
    {
     apexManualRouteBlade8Index                   Integer32,
     apexManualRouteBlade8Enable                  EnableDisableTYPE,
     apexManualRouteBlade8InputInterface          Integer32,
     apexManualRouteBlade8InputUdp                Integer32,
     apexManualRouteBlade8InputMulticastIp        IpAddress,
     apexManualRouteBlade8InputSourceIp           IpAddress,
     apexManualRouteBlade8InputProgNum            Integer32,
     apexManualRouteBlade8InputPreEncryptCheck    EnableDisableTYPE,
     apexManualRouteBlade8OutputTsNum             Integer32,
     apexManualRouteBlade8OutputProgNum           Integer32,
     apexManualRouteBlade8FollowDtcp              EnableDisableTYPE
    }

apexManualRouteBlade8Index OBJECT-TYPE
    SYNTAX Integer32(1..2304)
    MAX-ACCESS not-accessible
    STATUS current
    DESCRIPTION
        "The index of the Manual Route Table."
::= { apexManualRouteBlade8Entry 1 }

apexManualRouteBlade8Enable OBJECT-TYPE
    SYNTAX EnableDisableTYPE
    MAX-ACCESS read-write
    STATUS current
    DESCRIPTION
        "Indicates that this Manual Route is enabled or disabled.
        "
::= { apexManualRouteBlade8Entry 2 }

apexManualRouteBlade8InputInterface OBJECT-TYPE
    SYNTAX Integer32(0..12)
    MAX-ACCESS read-write
    STATUS current
    DESCRIPTION
        "Number of the input GigE interface from which to obtain data.
        "
::= { apexManualRouteBlade8Entry 3 }

apexManualRouteBlade8InputUdp OBJECT-TYPE
    SYNTAX Integer32(0..65535)
    MAX-ACCESS read-write
    STATUS current
    DESCRIPTION
        "Input UDP Port from which to obtain data.
        "
::= { apexManualRouteBlade8Entry 4 }

apexManualRouteBlade8InputMulticastIp OBJECT-TYPE
    SYNTAX IpAddress
    MAX-ACCESS read-write
    STATUS current
    DESCRIPTION
        "Input Multicast IP address from which to obtain data.

         An IP address of 0.0.0.0 indicates table entry not in use.

         Multicast IP addresses 224.0.0.0 to 224.0.0.255 are reserved.
        "
::= { apexManualRouteBlade8Entry 5 }

apexManualRouteBlade8InputSourceIp OBJECT-TYPE
    SYNTAX IpAddress
    MAX-ACCESS read-write
    STATUS current
    DESCRIPTION
        "Input IGMP v3 Source IP from which to obtain data.

         If the router supports IGMP v3 the GBE will only receive data from
         this source IP.  If Source IP is not specified or the router does not
         support IGMP v3 the GBE will receive data from any source device.
         Source IP address must be a valid singlecast address.
        "
::= { apexManualRouteBlade8Entry 6 }

apexManualRouteBlade8InputProgNum OBJECT-TYPE
    SYNTAX Integer32(0..65535)
    MAX-ACCESS read-write
    STATUS current
    DESCRIPTION
        "Input MPEG Program Number to multiplex. A value of 0 can be used as
         a wild card. This will cause the APEX to map the first program listed in
         the input PAT to the specified output (regardless of input program number).
         Input program number zero should only be used when mapping Single Program
         Transport Streams (SPTS).
        "
::= { apexManualRouteBlade8Entry 7 }

apexManualRouteBlade8InputPreEncryptCheck OBJECT-TYPE
    SYNTAX EnableDisableTYPE
    MAX-ACCESS read-write
    STATUS current
    DESCRIPTION
        "Manual Routing Pre-Encryption Checking.

         Indicates if the APEX is to check if the input service is pre-encrypted or
         clear. Pre-encrypted is determined by examining the input PMT for a CA ECM
         descriptor (any CA ECM descriptor). If pre-encrypted, setting this flag will
         cause the APEX to pass through ECM PID for this service. For input services
         that have a GI CA ECM descriptor, the APEX will also pass through the PIT
         message (extract and re-insert the PIT). The output PMT for pre-encrypted
         services will contain a CA ECM descriptor (referencing the ECM
         PID). When PID Remapping is enabled, pre-encryption for a service is
         only valid when the input ECM PID is on a different PID than the
         associated PMT PID. If this flag is set to pre-encryption and the
         input service is not pre-encrypted, then the setting of this flag has
         no affect on the output service.
        "
::= { apexManualRouteBlade8Entry 8 }

apexManualRouteBlade8OutputTsNum OBJECT-TYPE
    SYNTAX Integer32(0..256)
    MAX-ACCESS read-write
    STATUS current
    DESCRIPTION
        "Output Transport Stream Number of the output on which to place data.
         Zero = NotApplicable and is only valid if the apexManualRouteBlade8Table
         entry is not being used.
        "
::= { apexManualRouteBlade8Entry 9 }

apexManualRouteBlade8OutputProgNum OBJECT-TYPE
    SYNTAX Integer32(0..65535)
    MAX-ACCESS read-write
    STATUS current
    DESCRIPTION
        "Output Program number to use for the program.
         Zero = NotApplicable and is only valid if the apexManualRouteBlade8Table
         entry is not being used.
        "
::= { apexManualRouteBlade8Entry 10 }

apexManualRouteBlade8FollowDtcp OBJECT-TYPE
    SYNTAX EnableDisableTYPE
    MAX-ACCESS read-write
    STATUS current
    DESCRIPTION
        "Determines how the copy protection settings (CCI, APS, and CIT) within 
         the PRK will be set.
         For each service, will allow user to override the RDS or user 
         configured copy protection and force the service to follow 
         the input DTCP.
        
        - Disabled    - Use CTE configured settings if output in CTE encryption mode
        - Enabled     - Follow input DTCP.                                
        "
::= { apexManualRouteBlade8Entry 11 }


-- ------------------------------------------------------------------------------
--
-- apexManRtePassThruBlade8ApplyTable
--

apexManRtePassThruBlade8ApplyTable OBJECT-TYPE
    SYNTAX SEQUENCE OF ApexManRtePassThruBlade8ApplyEntry
    MAX-ACCESS not-accessible
    STATUS current
    DESCRIPTION
        "Table of Apply Change for the data for Manual Route Pass Through Table.

         A row in this table corresponds to the same row index in the
         Manual Route Pass Through table.
        "
::= { apexManualRouteBlade8 3 }

apexManRtePassThruBlade8ApplyEntry OBJECT-TYPE
    SYNTAX ApexManRtePassThruBlade8ApplyEntry
    MAX-ACCESS not-accessible
    STATUS current
    DESCRIPTION
        "Manual Route Pass Through Apply Table Entry."
    INDEX { apexManRtePassThruBlade8ApplyOutputTsNum }
::= { apexManRtePassThruBlade8ApplyTable 1 }

ApexManRtePassThruBlade8ApplyEntry ::= SEQUENCE
    {
     apexManRtePassThruBlade8ApplyOutputTsNum   Integer32,
     apexManRtePassThruBlade8ApplyChange        ApplyDataToDeviceTYPE
    }

apexManRtePassThruBlade8ApplyOutputTsNum OBJECT-TYPE
    SYNTAX Integer32(1..256)
    MAX-ACCESS not-accessible
    STATUS current
    DESCRIPTION
        "The index of the Manual Route Pass Through Apply Table."
::= { apexManRtePassThruBlade8ApplyEntry 1 }

apexManRtePassThruBlade8ApplyChange OBJECT-TYPE
    SYNTAX ApplyDataToDeviceTYPE
    MAX-ACCESS read-write
    STATUS current
    DESCRIPTION
        "The Apply for the row of data in the Manual Route Pass Through Table.

         A row in this table corresponds to the same row index in the
         Manual Route Pass Through table.

         This parameter MUST be set to 'apply' in order for any of the
         data in the Manual Route Pass Through Table row to take effect
         in the APEX.  This parameter MUST be set LAST after all other
         data in the Manual Route Pass Through Table row has been configured.

         @Config(config=no, reboot=no)
        "
::= { apexManRtePassThruBlade8ApplyEntry 2 }


-- ------------------------------------------------------------------------------
--
-- apexManRtePassThruBlade8Table
--

apexManRtePassThruBlade8Table OBJECT-TYPE
    SYNTAX SEQUENCE OF ApexManRtePassThruBlade8Entry
    MAX-ACCESS not-accessible
    STATUS current
    DESCRIPTION
        "Table of data for Manual Route Pass Through. This table is used to
         pass through an entire input stream to an output stream.

         Once written, the change to a row this table will only take
         immediate effect after the appropriate apexManRtePassThruBlade8ApplyChange
         is set to 'apply'.  In order for the change to persist through
         subsequent reboots or power cycles, the change must be saved via
         the apexSaveConfig parameter.

         @Config(config=yes, reboot=no)
         @Commit(param=apexManRtePassThruBlade8ApplyChange, value=2)
         @Save(apexSaveConfig, value=2)
         @File(manrout8.ini, type='ini')
        "
::= { apexManualRouteBlade8 4 }

apexManRtePassThruBlade8Entry OBJECT-TYPE
    SYNTAX ApexManRtePassThruBlade8Entry
    MAX-ACCESS not-accessible
    STATUS current
    DESCRIPTION
        "Manual Route Pass Through Table Entry."
    INDEX { apexManRtePassThruBlade8OutputTsNum }
::= { apexManRtePassThruBlade8Table 1 }

ApexManRtePassThruBlade8Entry ::= SEQUENCE
    {
     apexManRtePassThruBlade8OutputTsNum        Integer32,
     apexManRtePassThruBlade8Enable             EnableDisableTYPE,
     apexManRtePassThruBlade8InputInterface     Integer32,
     apexManRtePassThruBlade8InputUdp           Integer32,
     apexManRtePassThruBlade8InputMulticastIp   IpAddress,
     apexManRtePassThruBlade8InputSourceIp      IpAddress
    }

apexManRtePassThruBlade8OutputTsNum OBJECT-TYPE
    SYNTAX Integer32(1..256)
    MAX-ACCESS not-accessible
    STATUS current
    DESCRIPTION
        "The index of the Manual Route Pass Through Table."
::= { apexManRtePassThruBlade8Entry 1 }

apexManRtePassThruBlade8Enable OBJECT-TYPE
    SYNTAX EnableDisableTYPE
    MAX-ACCESS read-write
    STATUS current
    DESCRIPTION
        "Indicates that this Manual Route Pass Through is enabled or disabled.
         An input stream can only be passed through to an output stream when
         there are no active service or PID mappings to the output stream.
        "
::= { apexManRtePassThruBlade8Entry 2 }

apexManRtePassThruBlade8InputInterface OBJECT-TYPE
    SYNTAX Integer32(0..12)
    MAX-ACCESS read-write
    STATUS current
    DESCRIPTION
        "Number of the input GigE interface from which to obtain data.
        "
::= { apexManRtePassThruBlade8Entry 3 }

apexManRtePassThruBlade8InputUdp OBJECT-TYPE
    SYNTAX Integer32(0..65535)
    MAX-ACCESS read-write
    STATUS current
    DESCRIPTION
        "Input UDP Port from which to obtain data.
        "
::= { apexManRtePassThruBlade8Entry 4 }

apexManRtePassThruBlade8InputMulticastIp OBJECT-TYPE
    SYNTAX IpAddress
    MAX-ACCESS read-write
    STATUS current
    DESCRIPTION
        "Input Multicast IP address from which to obtain data.

         An IP address of 0.0.0.0 indicates table entry not in use.

         Multicast IP addresses 224.0.0.0 to 224.0.0.255 are reserved.
        "
::= { apexManRtePassThruBlade8Entry 5 }

apexManRtePassThruBlade8InputSourceIp OBJECT-TYPE
    SYNTAX IpAddress
    MAX-ACCESS read-write
    STATUS current
    DESCRIPTION
        "Input IGMP v3 Source IP address from which to obtain data.

         If the router supports IGMP v3 the GBE will only receive data from
         this source IP.  If Source IP is not specified or the router does not
         support IGMP v3 the GBE will receive data from any source device.
         Source IP address must be a valid singlecast address.
        "
::= { apexManRtePassThruBlade8Entry 6 }


-- ------------------------------------------------------------------------------
--
-- apexManualRoutingStatus
--
-- apexManualRoutingStatusGeneral
--
-- none


-- ------------------------------------------------------------------------------
--
-- apexManualRouteStatusTable
--

apexManualRouteStatusTable OBJECT-TYPE
    SYNTAX SEQUENCE OF ApexManualRouteStatusEntry 
    MAX-ACCESS not-accessible
    STATUS current
    DESCRIPTION
        "Table of status data for Manual Route Table and
         Manual Route Pass Through Table.
         There is 1 row for each blade.
        "
::= { apexManualRoutingStatus 2 }

apexManualRouteStatusEntry OBJECT-TYPE
    SYNTAX ApexManualRouteStatusEntry 
    MAX-ACCESS not-accessible
    STATUS current
    DESCRIPTION
        "Manual Route Status Table Entry."
    INDEX { apexManualRouteStatusBladeNum }
::= { apexManualRouteStatusTable 1 }

ApexManualRouteStatusEntry ::= SEQUENCE
    {
     apexManualRouteStatusBladeNum      Integer32,
     apexManualRouteInvalidApplyText    DisplayString,
     apexManRtePassThruInvalidApplyText DisplayString                               
    }

apexManualRouteStatusBladeNum OBJECT-TYPE
    SYNTAX Integer32(1..8)
    MAX-ACCESS not-accessible
    STATUS current
    DESCRIPTION
        "Blade Number."
::= { apexManualRouteStatusEntry 1 }

apexManualRouteInvalidApplyText OBJECT-TYPE
    SYNTAX DisplayString (SIZE (0..80))
    MAX-ACCESS read-only
    STATUS current
    DESCRIPTION
        "When apexManualRouteBlade#ApplyChange is set to applyNotInProgressInvalidData,
         this entry may contain a text description of what was wrong with the data.
         This entry contains the description for the most recent apply
         of a related entry that was invalid. 
        "
::= { apexManualRouteStatusEntry 2 }

apexManRtePassThruInvalidApplyText OBJECT-TYPE
    SYNTAX DisplayString (SIZE (0..80))
    MAX-ACCESS read-only
    STATUS current
    DESCRIPTION
        "When apexManRtePassThruBlade#ApplyChange is set to applyNotInProgressInvalidData,
         this entry may contain a text description of what was wrong with the data.
         This entry contains the description for the most recent apply
         of a related entry that was invalid. 
        "
::= { apexManualRouteStatusEntry 3 }


-- ------------------------------------------------------------------------------
--
-- apexAncillaryPidMapping
--
-- apexPidMapConfig
--
-- apexPidMapConfigGeneral
--

apexPidMapEnableDisableApply OBJECT-TYPE
    SYNTAX EnableDisableAllTYPE
    MAX-ACCESS read-write
    STATUS current
    DESCRIPTION
        "Setting this causes all ancillary PID routes on the specified blade
         or on all blades to be enabled or disabled. When enabling routes,
         only routes that have a valid GigE interface will be enabled. 
         This allows for all routes to quickly be enabled or disabled.
         
         This affects ancillary PID mappings only.
         
         Upon setting this field, no changes will take affect until after
         the APEX sets this field back to notInProgress.
         
         @Config(config=no, reboot=no)
        "
::= { apexPidMapConfigGeneral 1 }


-- ------------------------------------------------------------------------------
--
-- apexPidMapBlade1
--
-- apexPidMapBlade1ApplyTable
--

apexPidMapBlade1ApplyTable OBJECT-TYPE
    SYNTAX SEQUENCE OF ApexPidMapBlade1ApplyEntry
    MAX-ACCESS not-accessible
    STATUS current
    DESCRIPTION
        "Table of Apply Change for the data for PID Map Table.

         A row in this table corresponds to the same row index in the
         PID Map table.
        "
::= { apexPidMapBlade1 1 }

apexPidMapBlade1ApplyEntry OBJECT-TYPE
    SYNTAX ApexPidMapBlade1ApplyEntry
    MAX-ACCESS not-accessible
    STATUS current
    DESCRIPTION
        "PID Map Apply Table Entry."
    INDEX { apexPidMapBlade1ApplyIndex }
::= { apexPidMapBlade1ApplyTable 1 }

ApexPidMapBlade1ApplyEntry ::= SEQUENCE
    {
     apexPidMapBlade1ApplyIndex         Integer32,
     apexPidMapBlade1ApplyChange        ApplyDataToDeviceTYPE
    }

apexPidMapBlade1ApplyIndex OBJECT-TYPE
    SYNTAX Integer32(1..256)
    MAX-ACCESS not-accessible
    STATUS current
    DESCRIPTION
        "The index of the PID Map Apply Table."
::= { apexPidMapBlade1ApplyEntry 1 }

apexPidMapBlade1ApplyChange OBJECT-TYPE
    SYNTAX ApplyDataToDeviceTYPE
    MAX-ACCESS read-write
    STATUS current
    DESCRIPTION
        "The Apply for the row of data in the PID Map Table.

         A row in this table corresponds to the same row index in the
         PID Map table.

         This parameter MUST be set to 'apply' in order for any of the data
         in the PID Map Table row to take effect in the APEX.  This
         parameter MUST be set LAST after all other data in the PID Map
         Table row has been configured.

         @Config(config=no, reboot=no)
        "
::= { apexPidMapBlade1ApplyEntry 2 }
                                            

-- ------------------------------------------------------------------------------
--
-- apexPidMapBlade1Table
--

apexPidMapBlade1Table OBJECT-TYPE
    SYNTAX SEQUENCE OF ApexPidMapBlade1Entry
    MAX-ACCESS not-accessible
    STATUS current
    DESCRIPTION
        "Table of data for Ancillary Pid Mapping. 
         There are 256 rows in this table (i.e. 256 rows per Blade).

         Once written, the change to this table will only take immediate
         effect after apexPidMapBlade1ApplyChange is set to 'apply'.
         However, in order for the change to persist through subsequent
         reboots or power cycles, the change must be saved via apexSaveConfig.

         @Config(config=yes, reboot=no)
         @Commit(param=apexPidMapBlade1ApplyChange, value=2)
         @Save(apexSaveConfig, value=2)
         @File(manrout1.ini, type='ini')
        "
::= { apexPidMapBlade1 2 }

apexPidMapBlade1Entry OBJECT-TYPE
    SYNTAX ApexPidMapBlade1Entry
    MAX-ACCESS not-accessible
    STATUS current
    DESCRIPTION
        "Pid Mapping Table Entry."
    INDEX { apexPidMapBlade1Index }
::= { apexPidMapBlade1Table 1 }

ApexPidMapBlade1Entry ::= SEQUENCE
    {
     apexPidMapBlade1Index              Integer32,
     apexPidMapBlade1Enable             EnableDisableTYPE,
     apexPidMapBlade1InputInterface     Integer32,
     apexPidMapBlade1InputUdp           Integer32,
     apexPidMapBlade1InputMulticastIp   IpAddress,
     apexPidMapBlade1InputSourceIp      IpAddress,
     apexPidMapBlade1InputPid           Integer32,
     apexPidMapBlade1OutputTsNum        Integer32,
     apexPidMapBlade1OutputPid          Integer32
    }

apexPidMapBlade1Index OBJECT-TYPE
    SYNTAX Integer32(1..256)
    MAX-ACCESS not-accessible
    STATUS current
    DESCRIPTION
        "Index of Pid Mapping Table."
::= { apexPidMapBlade1Entry 1 }

apexPidMapBlade1Enable OBJECT-TYPE
    SYNTAX EnableDisableTYPE
    MAX-ACCESS read-write
    STATUS current
    DESCRIPTION
        "Indicates whether this PID Mapping is enabled or disabled.
        "
::= { apexPidMapBlade1Entry 2 }

apexPidMapBlade1InputInterface OBJECT-TYPE
    SYNTAX Integer32(0..12)
    MAX-ACCESS read-write
    STATUS current
    DESCRIPTION
        "Number of the input GigE interface from which to obtain data."
::= { apexPidMapBlade1Entry 3 }

apexPidMapBlade1InputUdp OBJECT-TYPE
SYNTAX Integer32(0..65535)
    MAX-ACCESS read-write
    STATUS current
    DESCRIPTION
        "Input UDP Port from which to obtain data."
::= { apexPidMapBlade1Entry 4 }

apexPidMapBlade1InputMulticastIp OBJECT-TYPE
    SYNTAX IpAddress
    MAX-ACCESS read-write
    STATUS current
    DESCRIPTION
        "The Multicast receive IP address on which to receive data.

         An IP address of 0.0.0.0 indicates singlecast only.

         Multicast IP addresses 224.0.0.0 to 224.0.0.255 are reserved.
        "
::= { apexPidMapBlade1Entry 5 }

apexPidMapBlade1InputSourceIp OBJECT-TYPE
    SYNTAX IpAddress
    MAX-ACCESS read-write
    STATUS current
    DESCRIPTION
        "This is the IP address of the source device.

         If the router supports IGMP v3 the GBE will only receive data from
         this source IP.  If Source IP is not specified or the router does not
         support IGMP v3 the GBE will receive data from any source device.
         Source IP address must be a valid singlecast address.
        "
::= { apexPidMapBlade1Entry 6 }

apexPidMapBlade1InputPid OBJECT-TYPE
    SYNTAX Integer32(0..8191)
    MAX-ACCESS read-write
    STATUS current
    DESCRIPTION
        "Input MPEG PID to multiplex. When PID Remapping for an output is
         enabled, the input PID value and output PID value can be different. When
         PID Remapping for an output is disabled, the input and output PIDs must
         be the same. Input PID 0 (PAT PID) cannot be mapped by the user.
        "
::= { apexPidMapBlade1Entry 7 }

apexPidMapBlade1OutputTsNum OBJECT-TYPE
    SYNTAX Integer32(0..256)
    MAX-ACCESS read-write
    STATUS current
    DESCRIPTION
        "Output Transport Stream Number of the output on which to place data.
         Zero is only valid if the apexPidMapTable entry is not being used.
        "
::= { apexPidMapBlade1Entry 8 }

apexPidMapBlade1OutputPid OBJECT-TYPE
    SYNTAX Integer32(0..8191)
    MAX-ACCESS read-write
    STATUS current
    DESCRIPTION
        "Output PID to use for the data. This output PID value must match the input
         PID value when PID Remapping for the output stream is disabled.
         Zero is only valid if the apexPidMapTable entry is not being used.
        "
::= { apexPidMapBlade1Entry 9 }


-- ------------------------------------------------------------------------------
--
-- apexPidMapBlade2
--
-- apexPidMapBlade2ApplyTable
--

apexPidMapBlade2ApplyTable OBJECT-TYPE
    SYNTAX SEQUENCE OF ApexPidMapBlade2ApplyEntry
    MAX-ACCESS not-accessible
    STATUS current
    DESCRIPTION
        "Table of Apply Change for the data for PID Map Table.

         A row in this table corresponds to the same row index in the
         PID Map table.
        "
::= { apexPidMapBlade2 1 }

apexPidMapBlade2ApplyEntry OBJECT-TYPE
    SYNTAX ApexPidMapBlade2ApplyEntry
    MAX-ACCESS not-accessible
    STATUS current
    DESCRIPTION
        "PID Map Apply Table Entry."
    INDEX { apexPidMapBlade2ApplyIndex }
::= { apexPidMapBlade2ApplyTable 1 }

ApexPidMapBlade2ApplyEntry ::= SEQUENCE
    {
     apexPidMapBlade2ApplyIndex         Integer32,
     apexPidMapBlade2ApplyChange        ApplyDataToDeviceTYPE
    }

apexPidMapBlade2ApplyIndex OBJECT-TYPE
    SYNTAX Integer32(1..256)
    MAX-ACCESS not-accessible
    STATUS current
    DESCRIPTION
        "The index of the PID Map Apply Table."
::= { apexPidMapBlade2ApplyEntry 1 }

apexPidMapBlade2ApplyChange OBJECT-TYPE
    SYNTAX ApplyDataToDeviceTYPE
    MAX-ACCESS read-write
    STATUS current
    DESCRIPTION
        "The Apply for the row of data in the PID Map Table.

         A row in this table corresponds to the same row index in the
         PID Map table.

         This parameter MUST be set to 'apply' in order for any of the data
         in the PID Map Table row to take effect in the APEX.  This
         parameter MUST be set LAST after all other data in the PID Map
         Table row has been configured.

         @Config(config=no, reboot=no)
        "
::= { apexPidMapBlade2ApplyEntry 2 }
                                            

-- ------------------------------------------------------------------------------
--
-- apexPidMapBlade2Table
--

apexPidMapBlade2Table OBJECT-TYPE
    SYNTAX SEQUENCE OF ApexPidMapBlade2Entry
    MAX-ACCESS not-accessible
    STATUS current
    DESCRIPTION
        "Table of data for Ancillary Pid Mapping. 
         There are 256 rows in this table (i.e. 256 rows per Blade).

         Once written, the change to this table will only take immediate
         effect after apexPidMapBlade2ApplyChange is set to 'apply'.
         However, in order for the change to persist through subsequent
         reboots or power cycles, the change must be saved via apexSaveConfig.

         @Config(config=yes, reboot=no)
         @Commit(param=apexPidMapBlade2ApplyChange, value=2)
         @Save(apexSaveConfig, value=2)
         @File(manrout2.ini, type='ini')
        "
::= { apexPidMapBlade2 2 }

apexPidMapBlade2Entry OBJECT-TYPE
    SYNTAX ApexPidMapBlade2Entry
    MAX-ACCESS not-accessible
    STATUS current
    DESCRIPTION
        "Pid Mapping Table Entry."
    INDEX { apexPidMapBlade2Index }
::= { apexPidMapBlade2Table 1 }

ApexPidMapBlade2Entry ::= SEQUENCE
    {
     apexPidMapBlade2Index              Integer32,
     apexPidMapBlade2Enable             EnableDisableTYPE,
     apexPidMapBlade2InputInterface     Integer32,
     apexPidMapBlade2InputUdp           Integer32,
     apexPidMapBlade2InputMulticastIp   IpAddress,
     apexPidMapBlade2InputSourceIp      IpAddress,
     apexPidMapBlade2InputPid           Integer32,
     apexPidMapBlade2OutputTsNum        Integer32,
     apexPidMapBlade2OutputPid          Integer32
    }

apexPidMapBlade2Index OBJECT-TYPE
    SYNTAX Integer32(1..256)
    MAX-ACCESS not-accessible
    STATUS current
    DESCRIPTION
        "Index of Pid Mapping Table."
::= { apexPidMapBlade2Entry 1 }

apexPidMapBlade2Enable OBJECT-TYPE
    SYNTAX EnableDisableTYPE
    MAX-ACCESS read-write
    STATUS current
    DESCRIPTION
        "Indicates whether this PID Mapping is enabled or disabled.
        "
::= { apexPidMapBlade2Entry 2 }

apexPidMapBlade2InputInterface OBJECT-TYPE
    SYNTAX Integer32(0..12)
    MAX-ACCESS read-write
    STATUS current
    DESCRIPTION
        "Number of the input GigE interface from which to obtain data."
::= { apexPidMapBlade2Entry 3 }

apexPidMapBlade2InputUdp OBJECT-TYPE
SYNTAX Integer32(0..65535)
    MAX-ACCESS read-write
    STATUS current
    DESCRIPTION
        "Input UDP Port from which to obtain data."
::= { apexPidMapBlade2Entry 4 }

apexPidMapBlade2InputMulticastIp OBJECT-TYPE
    SYNTAX IpAddress
    MAX-ACCESS read-write
    STATUS current
    DESCRIPTION
        "The Multicast receive IP address on which to receive data.

         An IP address of 0.0.0.0 indicates singlecast only.

         Multicast IP addresses 224.0.0.0 to 224.0.0.255 are reserved.
        "
::= { apexPidMapBlade2Entry 5 }

apexPidMapBlade2InputSourceIp OBJECT-TYPE
    SYNTAX IpAddress
    MAX-ACCESS read-write
    STATUS current
    DESCRIPTION
        "This is the IP address of the source device.

         If the router supports IGMP v3 the GBE will only receive data from
         this source IP.  If Source IP is not specified or the router does not
         support IGMP v3 the GBE will receive data from any source device.
         Source IP address must be a valid singlecast address.
        "
::= { apexPidMapBlade2Entry 6 }

apexPidMapBlade2InputPid OBJECT-TYPE
    SYNTAX Integer32(0..8191)
    MAX-ACCESS read-write
    STATUS current
    DESCRIPTION
        "Input MPEG PID to multiplex. When PID Remapping for an output is
         enabled, the input PID value and output PID value can be different. When
         PID Remapping for an output is disabled, the input and output PIDs must
         be the same. Input PID 0 (PAT PID) cannot be mapped by the user.
        "
::= { apexPidMapBlade2Entry 7 }

apexPidMapBlade2OutputTsNum OBJECT-TYPE
    SYNTAX Integer32(0..256)
    MAX-ACCESS read-write
    STATUS current
    DESCRIPTION
        "Output Transport Stream Number of the output on which to place data.
         Zero is only valid if the apexPidMapTable entry is not being used.
        "
::= { apexPidMapBlade2Entry 8 }

apexPidMapBlade2OutputPid OBJECT-TYPE
    SYNTAX Integer32(0..8191)
    MAX-ACCESS read-write
    STATUS current
    DESCRIPTION
        "Output PID to use for the data. This output PID value must match the input
         PID value when PID Remapping for the output stream is disabled.
         Zero is only valid if the apexPidMapTable entry is not being used.
        "
::= { apexPidMapBlade2Entry 9 }


-- ------------------------------------------------------------------------------
--
-- apexPidMapBlade3
--
-- apexPidMapBlade3ApplyTable
--

apexPidMapBlade3ApplyTable OBJECT-TYPE
    SYNTAX SEQUENCE OF ApexPidMapBlade3ApplyEntry
    MAX-ACCESS not-accessible
    STATUS current
    DESCRIPTION
        "Table of Apply Change for the data for PID Map Table.

         A row in this table corresponds to the same row index in the
         PID Map table.
        "
::= { apexPidMapBlade3 1 }

apexPidMapBlade3ApplyEntry OBJECT-TYPE
    SYNTAX ApexPidMapBlade3ApplyEntry
    MAX-ACCESS not-accessible
    STATUS current
    DESCRIPTION
        "PID Map Apply Table Entry."
    INDEX { apexPidMapBlade3ApplyIndex }
::= { apexPidMapBlade3ApplyTable 1 }

ApexPidMapBlade3ApplyEntry ::= SEQUENCE
    {
     apexPidMapBlade3ApplyIndex         Integer32,
     apexPidMapBlade3ApplyChange        ApplyDataToDeviceTYPE
    }

apexPidMapBlade3ApplyIndex OBJECT-TYPE
    SYNTAX Integer32(1..256)
    MAX-ACCESS not-accessible
    STATUS current
    DESCRIPTION
        "The index of the PID Map Apply Table."
::= { apexPidMapBlade3ApplyEntry 1 }

apexPidMapBlade3ApplyChange OBJECT-TYPE
    SYNTAX ApplyDataToDeviceTYPE
    MAX-ACCESS read-write
    STATUS current
    DESCRIPTION
        "The Apply for the row of data in the PID Map Table.

         A row in this table corresponds to the same row index in the
         PID Map table.

         This parameter MUST be set to 'apply' in order for any of the data
         in the PID Map Table row to take effect in the APEX.  This
         parameter MUST be set LAST after all other data in the PID Map
         Table row has been configured.

         @Config(config=no, reboot=no)
        "
::= { apexPidMapBlade3ApplyEntry 2 }
                                            

-- ------------------------------------------------------------------------------
--
-- apexPidMapBlade3Table
--

apexPidMapBlade3Table OBJECT-TYPE
    SYNTAX SEQUENCE OF ApexPidMapBlade3Entry
    MAX-ACCESS not-accessible
    STATUS current
    DESCRIPTION
        "Table of data for Ancillary Pid Mapping. 
         There are 256 rows in this table (i.e. 256 rows per Blade).

         Once written, the change to this table will only take immediate
         effect after apexPidMapBlade3ApplyChange is set to 'apply'.
         However, in order for the change to persist through subsequent
         reboots or power cycles, the change must be saved via apexSaveConfig.

         @Config(config=yes, reboot=no)
         @Commit(param=apexPidMapBlade3ApplyChange, value=2)
         @Save(apexSaveConfig, value=2)
         @File(manrout3.ini, type='ini')
        "
::= { apexPidMapBlade3 2 }

apexPidMapBlade3Entry OBJECT-TYPE
    SYNTAX ApexPidMapBlade3Entry
    MAX-ACCESS not-accessible
    STATUS current
    DESCRIPTION
        "Pid Mapping Table Entry."
    INDEX { apexPidMapBlade3Index }
::= { apexPidMapBlade3Table 1 }

ApexPidMapBlade3Entry ::= SEQUENCE
    {
     apexPidMapBlade3Index              Integer32,
     apexPidMapBlade3Enable             EnableDisableTYPE,
     apexPidMapBlade3InputInterface     Integer32,
     apexPidMapBlade3InputUdp           Integer32,
     apexPidMapBlade3InputMulticastIp   IpAddress,
     apexPidMapBlade3InputSourceIp      IpAddress,
     apexPidMapBlade3InputPid           Integer32,
     apexPidMapBlade3OutputTsNum        Integer32,
     apexPidMapBlade3OutputPid          Integer32
    }

apexPidMapBlade3Index OBJECT-TYPE
    SYNTAX Integer32(1..256)
    MAX-ACCESS not-accessible
    STATUS current
    DESCRIPTION
        "Index of Pid Mapping Table."
::= { apexPidMapBlade3Entry 1 }

apexPidMapBlade3Enable OBJECT-TYPE
    SYNTAX EnableDisableTYPE
    MAX-ACCESS read-write
    STATUS current
    DESCRIPTION
        "Indicates whether this PID Mapping is enabled or disabled.
        "
::= { apexPidMapBlade3Entry 2 }

apexPidMapBlade3InputInterface OBJECT-TYPE
    SYNTAX Integer32(0..12)
    MAX-ACCESS read-write
    STATUS current
    DESCRIPTION
        "Number of the input GigE interface from which to obtain data."
::= { apexPidMapBlade3Entry 3 }

apexPidMapBlade3InputUdp OBJECT-TYPE
SYNTAX Integer32(0..65535)
    MAX-ACCESS read-write
    STATUS current
    DESCRIPTION
        "Input UDP Port from which to obtain data."
::= { apexPidMapBlade3Entry 4 }

apexPidMapBlade3InputMulticastIp OBJECT-TYPE
    SYNTAX IpAddress
    MAX-ACCESS read-write
    STATUS current
    DESCRIPTION
        "The Multicast receive IP address on which to receive data.

         An IP address of 0.0.0.0 indicates singlecast only.

         Multicast IP addresses 224.0.0.0 to 224.0.0.255 are reserved.
        "
::= { apexPidMapBlade3Entry 5 }

apexPidMapBlade3InputSourceIp OBJECT-TYPE
    SYNTAX IpAddress
    MAX-ACCESS read-write
    STATUS current
    DESCRIPTION
        "This is the IP address of the source device.

         If the router supports IGMP v3 the GBE will only receive data from
         this source IP.  If Source IP is not specified or the router does not
         support IGMP v3 the GBE will receive data from any source device.
         Source IP address must be a valid singlecast address.
        "
::= { apexPidMapBlade3Entry 6 }

apexPidMapBlade3InputPid OBJECT-TYPE
    SYNTAX Integer32(0..8191)
    MAX-ACCESS read-write
    STATUS current
    DESCRIPTION
        "Input MPEG PID to multiplex. When PID Remapping for an output is
         enabled, the input PID value and output PID value can be different. When
         PID Remapping for an output is disabled, the input and output PIDs must
         be the same. Input PID 0 (PAT PID) cannot be mapped by the user.
        "
::= { apexPidMapBlade3Entry 7 }

apexPidMapBlade3OutputTsNum OBJECT-TYPE
    SYNTAX Integer32(0..256)
    MAX-ACCESS read-write
    STATUS current
    DESCRIPTION
        "Output Transport Stream Number of the output on which to place data.
         Zero is only valid if the apexPidMapTable entry is not being used.
        "
::= { apexPidMapBlade3Entry 8 }

apexPidMapBlade3OutputPid OBJECT-TYPE
    SYNTAX Integer32(0..8191)
    MAX-ACCESS read-write
    STATUS current
    DESCRIPTION
        "Output PID to use for the data. This output PID value must match the input
         PID value when PID Remapping for the output stream is disabled.
         Zero is only valid if the apexPidMapTable entry is not being used.
        "
::= { apexPidMapBlade3Entry 9 }

               
-- ------------------------------------------------------------------------------
--
-- apexPidMapBlade4
--
-- apexPidMapBlade4ApplyTable
--

apexPidMapBlade4ApplyTable OBJECT-TYPE
    SYNTAX SEQUENCE OF ApexPidMapBlade4ApplyEntry
    MAX-ACCESS not-accessible
    STATUS current
    DESCRIPTION
        "Table of Apply Change for the data for PID Map Table.

         A row in this table corresponds to the same row index in the
         PID Map table.
        "
::= { apexPidMapBlade4 1 }

apexPidMapBlade4ApplyEntry OBJECT-TYPE
    SYNTAX ApexPidMapBlade4ApplyEntry
    MAX-ACCESS not-accessible
    STATUS current
    DESCRIPTION
        "PID Map Apply Table Entry."
    INDEX { apexPidMapBlade4ApplyIndex }
::= { apexPidMapBlade4ApplyTable 1 }

ApexPidMapBlade4ApplyEntry ::= SEQUENCE
    {
     apexPidMapBlade4ApplyIndex         Integer32,
     apexPidMapBlade4ApplyChange        ApplyDataToDeviceTYPE
    }

apexPidMapBlade4ApplyIndex OBJECT-TYPE
    SYNTAX Integer32(1..256)
    MAX-ACCESS not-accessible
    STATUS current
    DESCRIPTION
        "The index of the PID Map Apply Table."
::= { apexPidMapBlade4ApplyEntry 1 }

apexPidMapBlade4ApplyChange OBJECT-TYPE
    SYNTAX ApplyDataToDeviceTYPE
    MAX-ACCESS read-write
    STATUS current
    DESCRIPTION
        "The Apply for the row of data in the PID Map Table.

         A row in this table corresponds to the same row index in the
         PID Map table.

         This parameter MUST be set to 'apply' in order for any of the data
         in the PID Map Table row to take effect in the APEX.  This
         parameter MUST be set LAST after all other data in the PID Map
         Table row has been configured.

         @Config(config=no, reboot=no)
        "
::= { apexPidMapBlade4ApplyEntry 2 }
                                            

-- ------------------------------------------------------------------------------
--
-- apexPidMapBlade4Table
--

apexPidMapBlade4Table OBJECT-TYPE
    SYNTAX SEQUENCE OF ApexPidMapBlade4Entry
    MAX-ACCESS not-accessible
    STATUS current
    DESCRIPTION
        "Table of data for Ancillary Pid Mapping. 
         There are 256 rows in this table (i.e. 256 rows per Blade).

         Once written, the change to this table will only take immediate
         effect after apexPidMapBlade4ApplyChange is set to 'apply'.
         However, in order for the change to persist through subsequent
         reboots or power cycles, the change must be saved via apexSaveConfig.

         @Config(config=yes, reboot=no)
         @Commit(param=apexPidMapBlade4ApplyChange, value=2)
         @Save(apexSaveConfig, value=2)
         @File(manrout4.ini, type='ini')
        "
::= { apexPidMapBlade4 2 }

apexPidMapBlade4Entry OBJECT-TYPE
    SYNTAX ApexPidMapBlade4Entry
    MAX-ACCESS not-accessible
    STATUS current
    DESCRIPTION
        "Pid Mapping Table Entry."
    INDEX { apexPidMapBlade4Index }
::= { apexPidMapBlade4Table 1 }

ApexPidMapBlade4Entry ::= SEQUENCE
    {
     apexPidMapBlade4Index              Integer32,
     apexPidMapBlade4Enable             EnableDisableTYPE,
     apexPidMapBlade4InputInterface     Integer32,
     apexPidMapBlade4InputUdp           Integer32,
     apexPidMapBlade4InputMulticastIp   IpAddress,
     apexPidMapBlade4InputSourceIp      IpAddress,
     apexPidMapBlade4InputPid           Integer32,
     apexPidMapBlade4OutputTsNum        Integer32,
     apexPidMapBlade4OutputPid          Integer32
    }

apexPidMapBlade4Index OBJECT-TYPE
    SYNTAX Integer32(1..256)
    MAX-ACCESS not-accessible
    STATUS current
    DESCRIPTION
        "Index of Pid Mapping Table."
::= { apexPidMapBlade4Entry 1 }

apexPidMapBlade4Enable OBJECT-TYPE
    SYNTAX EnableDisableTYPE
    MAX-ACCESS read-write
    STATUS current
    DESCRIPTION
        "Indicates whether this PID Mapping is enabled or disabled.
        "
::= { apexPidMapBlade4Entry 2 }

apexPidMapBlade4InputInterface OBJECT-TYPE
    SYNTAX Integer32(0..12)
    MAX-ACCESS read-write
    STATUS current
    DESCRIPTION
        "Number of the input GigE interface from which to obtain data."
::= { apexPidMapBlade4Entry 3 }

apexPidMapBlade4InputUdp OBJECT-TYPE
SYNTAX Integer32(0..65535)
    MAX-ACCESS read-write
    STATUS current
    DESCRIPTION
        "Input UDP Port from which to obtain data."
::= { apexPidMapBlade4Entry 4 }

apexPidMapBlade4InputMulticastIp OBJECT-TYPE
    SYNTAX IpAddress
    MAX-ACCESS read-write
    STATUS current
    DESCRIPTION
        "The Multicast receive IP address on which to receive data.

         An IP address of 0.0.0.0 indicates singlecast only.

         Multicast IP addresses 224.0.0.0 to 224.0.0.255 are reserved.
        "
::= { apexPidMapBlade4Entry 5 }

apexPidMapBlade4InputSourceIp OBJECT-TYPE
    SYNTAX IpAddress
    MAX-ACCESS read-write
    STATUS current
    DESCRIPTION
        "This is the IP address of the source device.

         If the router supports IGMP v3 the GBE will only receive data from
         this source IP.  If Source IP is not specified or the router does not
         support IGMP v3 the GBE will receive data from any source device.
         Source IP address must be a valid singlecast address.
        "
::= { apexPidMapBlade4Entry 6 }

apexPidMapBlade4InputPid OBJECT-TYPE
    SYNTAX Integer32(0..8191)
    MAX-ACCESS read-write
    STATUS current
    DESCRIPTION
        "Input MPEG PID to multiplex. When PID Remapping for an output is
         enabled, the input PID value and output PID value can be different. When
         PID Remapping for an output is disabled, the input and output PIDs must
         be the same. Input PID 0 (PAT PID) cannot be mapped by the user.
        "
::= { apexPidMapBlade4Entry 7 }

apexPidMapBlade4OutputTsNum OBJECT-TYPE
    SYNTAX Integer32(0..256)
    MAX-ACCESS read-write
    STATUS current
    DESCRIPTION
        "Output Transport Stream Number of the output on which to place data.
         Zero is only valid if the apexPidMapTable entry is not being used.
        "
::= { apexPidMapBlade4Entry 8 }

apexPidMapBlade4OutputPid OBJECT-TYPE
    SYNTAX Integer32(0..8191)
    MAX-ACCESS read-write
    STATUS current
    DESCRIPTION
        "Output PID to use for the data. This output PID value must match the input
         PID value when PID Remapping for the output stream is disabled.
         Zero is only valid if the apexPidMapTable entry is not being used.
        "
::= { apexPidMapBlade4Entry 9 }

               
-- ------------------------------------------------------------------------------
--
-- apexPidMapBlade5
--
-- apexPidMapBlade5ApplyTable
--

apexPidMapBlade5ApplyTable OBJECT-TYPE
    SYNTAX SEQUENCE OF ApexPidMapBlade5ApplyEntry
    MAX-ACCESS not-accessible
    STATUS current
    DESCRIPTION
        "Table of Apply Change for the data for PID Map Table.

         A row in this table corresponds to the same row index in the
         PID Map table.
        "
::= { apexPidMapBlade5 1 }

apexPidMapBlade5ApplyEntry OBJECT-TYPE
    SYNTAX ApexPidMapBlade5ApplyEntry
    MAX-ACCESS not-accessible
    STATUS current
    DESCRIPTION
        "PID Map Apply Table Entry."
    INDEX { apexPidMapBlade5ApplyIndex }
::= { apexPidMapBlade5ApplyTable 1 }

ApexPidMapBlade5ApplyEntry ::= SEQUENCE
    {
     apexPidMapBlade5ApplyIndex         Integer32,
     apexPidMapBlade5ApplyChange        ApplyDataToDeviceTYPE
    }

apexPidMapBlade5ApplyIndex OBJECT-TYPE
    SYNTAX Integer32(1..256)
    MAX-ACCESS not-accessible
    STATUS current
    DESCRIPTION
        "The index of the PID Map Apply Table."
::= { apexPidMapBlade5ApplyEntry 1 }

apexPidMapBlade5ApplyChange OBJECT-TYPE
    SYNTAX ApplyDataToDeviceTYPE
    MAX-ACCESS read-write
    STATUS current
    DESCRIPTION
        "The Apply for the row of data in the PID Map Table.

         A row in this table corresponds to the same row index in the
         PID Map table.

         This parameter MUST be set to 'apply' in order for any of the data
         in the PID Map Table row to take effect in the APEX.  This
         parameter MUST be set LAST after all other data in the PID Map
         Table row has been configured.

         @Config(config=no, reboot=no)
        "
::= { apexPidMapBlade5ApplyEntry 2 }
                                            

-- ------------------------------------------------------------------------------
--
-- apexPidMapBlade5Table
--

apexPidMapBlade5Table OBJECT-TYPE
    SYNTAX SEQUENCE OF ApexPidMapBlade5Entry
    MAX-ACCESS not-accessible
    STATUS current
    DESCRIPTION
        "Table of data for Ancillary Pid Mapping. 
         There are 256 rows in this table (i.e. 256 rows per Blade).

         Once written, the change to this table will only take immediate
         effect after apexPidMapBlade5ApplyChange is set to 'apply'.
         However, in order for the change to persist through subsequent
         reboots or power cycles, the change must be saved via apexSaveConfig.

         @Config(config=yes, reboot=no)
         @Commit(param=apexPidMapBlade5ApplyChange, value=2)
         @Save(apexSaveConfig, value=2)
         @File(manrout5.ini, type='ini')
        "
::= { apexPidMapBlade5 2 }

apexPidMapBlade5Entry OBJECT-TYPE
    SYNTAX ApexPidMapBlade5Entry
    MAX-ACCESS not-accessible
    STATUS current
    DESCRIPTION
        "Pid Mapping Table Entry."
    INDEX { apexPidMapBlade5Index }
::= { apexPidMapBlade5Table 1 }

ApexPidMapBlade5Entry ::= SEQUENCE
    {
     apexPidMapBlade5Index              Integer32,
     apexPidMapBlade5Enable             EnableDisableTYPE,
     apexPidMapBlade5InputInterface     Integer32,
     apexPidMapBlade5InputUdp           Integer32,
     apexPidMapBlade5InputMulticastIp   IpAddress,
     apexPidMapBlade5InputSourceIp      IpAddress,
     apexPidMapBlade5InputPid           Integer32,
     apexPidMapBlade5OutputTsNum        Integer32,
     apexPidMapBlade5OutputPid          Integer32
    }

apexPidMapBlade5Index OBJECT-TYPE
    SYNTAX Integer32(1..256)
    MAX-ACCESS not-accessible
    STATUS current
    DESCRIPTION
        "Index of Pid Mapping Table."
::= { apexPidMapBlade5Entry 1 }

apexPidMapBlade5Enable OBJECT-TYPE
    SYNTAX EnableDisableTYPE
    MAX-ACCESS read-write
    STATUS current
    DESCRIPTION
        "Indicates whether this PID Mapping is enabled or disabled.
        "
::= { apexPidMapBlade5Entry 2 }

apexPidMapBlade5InputInterface OBJECT-TYPE
    SYNTAX Integer32(0..12)
    MAX-ACCESS read-write
    STATUS current
    DESCRIPTION
        "Number of the input GigE interface from which to obtain data."
::= { apexPidMapBlade5Entry 3 }

apexPidMapBlade5InputUdp OBJECT-TYPE
SYNTAX Integer32(0..65535)
    MAX-ACCESS read-write
    STATUS current
    DESCRIPTION
        "Input UDP Port from which to obtain data."
::= { apexPidMapBlade5Entry 4 }

apexPidMapBlade5InputMulticastIp OBJECT-TYPE
    SYNTAX IpAddress
    MAX-ACCESS read-write
    STATUS current
    DESCRIPTION
        "The Multicast receive IP address on which to receive data.

         An IP address of 0.0.0.0 indicates singlecast only.

         Multicast IP addresses 224.0.0.0 to 224.0.0.255 are reserved.
        "
::= { apexPidMapBlade5Entry 5 }

apexPidMapBlade5InputSourceIp OBJECT-TYPE
    SYNTAX IpAddress
    MAX-ACCESS read-write
    STATUS current
    DESCRIPTION
        "This is the IP address of the source device.

         If the router supports IGMP v3 the GBE will only receive data from
         this source IP.  If Source IP is not specified or the router does not
         support IGMP v3 the GBE will receive data from any source device.
         Source IP address must be a valid singlecast address.
        "
::= { apexPidMapBlade5Entry 6 }

apexPidMapBlade5InputPid OBJECT-TYPE
    SYNTAX Integer32(0..8191)
    MAX-ACCESS read-write
    STATUS current
    DESCRIPTION
        "Input MPEG PID to multiplex. When PID Remapping for an output is
         enabled, the input PID value and output PID value can be different. When
         PID Remapping for an output is disabled, the input and output PIDs must
         be the same. Input PID 0 (PAT PID) cannot be mapped by the user.
        "
::= { apexPidMapBlade5Entry 7 }

apexPidMapBlade5OutputTsNum OBJECT-TYPE
    SYNTAX Integer32(0..256)
    MAX-ACCESS read-write
    STATUS current
    DESCRIPTION
        "Output Transport Stream Number of the output on which to place data.
         Zero is only valid if the apexPidMapTable entry is not being used.
        "
::= { apexPidMapBlade5Entry 8 }

apexPidMapBlade5OutputPid OBJECT-TYPE
    SYNTAX Integer32(0..8191)
    MAX-ACCESS read-write
    STATUS current
    DESCRIPTION
        "Output PID to use for the data. This output PID value must match the input
         PID value when PID Remapping for the output stream is disabled.
         Zero is only valid if the apexPidMapTable entry is not being used.
        "
::= { apexPidMapBlade5Entry 9 }


-- ------------------------------------------------------------------------------
--
-- apexPidMapBlade6
--
-- apexPidMapBlade6ApplyTable
--

apexPidMapBlade6ApplyTable OBJECT-TYPE
    SYNTAX SEQUENCE OF ApexPidMapBlade6ApplyEntry
    MAX-ACCESS not-accessible
    STATUS current
    DESCRIPTION
        "Table of Apply Change for the data for PID Map Table.

         A row in this table corresponds to the same row index in the
         PID Map table.
        "
::= { apexPidMapBlade6 1 }

apexPidMapBlade6ApplyEntry OBJECT-TYPE
    SYNTAX ApexPidMapBlade6ApplyEntry
    MAX-ACCESS not-accessible
    STATUS current
    DESCRIPTION
        "PID Map Apply Table Entry."
    INDEX { apexPidMapBlade6ApplyIndex }
::= { apexPidMapBlade6ApplyTable 1 }

ApexPidMapBlade6ApplyEntry ::= SEQUENCE
    {
     apexPidMapBlade6ApplyIndex         Integer32,
     apexPidMapBlade6ApplyChange        ApplyDataToDeviceTYPE
    }

apexPidMapBlade6ApplyIndex OBJECT-TYPE
    SYNTAX Integer32(1..256)
    MAX-ACCESS not-accessible
    STATUS current
    DESCRIPTION
        "The index of the PID Map Apply Table."
::= { apexPidMapBlade6ApplyEntry 1 }

apexPidMapBlade6ApplyChange OBJECT-TYPE
    SYNTAX ApplyDataToDeviceTYPE
    MAX-ACCESS read-write
    STATUS current
    DESCRIPTION
        "The Apply for the row of data in the PID Map Table.

         A row in this table corresponds to the same row index in the
         PID Map table.

         This parameter MUST be set to 'apply' in order for any of the data
         in the PID Map Table row to take effect in the APEX.  This
         parameter MUST be set LAST after all other data in the PID Map
         Table row has been configured.

         @Config(config=no, reboot=no)
        "
::= { apexPidMapBlade6ApplyEntry 2 }
                                            

-- ------------------------------------------------------------------------------
--
-- apexPidMapBlade6Table
--

apexPidMapBlade6Table OBJECT-TYPE
    SYNTAX SEQUENCE OF ApexPidMapBlade6Entry
    MAX-ACCESS not-accessible
    STATUS current
    DESCRIPTION
        "Table of data for Ancillary Pid Mapping. 
         There are 256 rows in this table (i.e. 256 rows per Blade).

         Once written, the change to this table will only take immediate
         effect after apexPidMapBlade6ApplyChange is set to 'apply'.
         However, in order for the change to persist through subsequent
         reboots or power cycles, the change must be saved via apexSaveConfig.

         @Config(config=yes, reboot=no)
         @Commit(param=apexPidMapBlade6ApplyChange, value=2)
         @Save(apexSaveConfig, value=2)
         @File(manrout6.ini, type='ini')
        "
::= { apexPidMapBlade6 2 }

apexPidMapBlade6Entry OBJECT-TYPE
    SYNTAX ApexPidMapBlade6Entry
    MAX-ACCESS not-accessible
    STATUS current
    DESCRIPTION
        "Pid Mapping Table Entry."
    INDEX { apexPidMapBlade6Index }
::= { apexPidMapBlade6Table 1 }

ApexPidMapBlade6Entry ::= SEQUENCE
    {
     apexPidMapBlade6Index              Integer32,
     apexPidMapBlade6Enable             EnableDisableTYPE,
     apexPidMapBlade6InputInterface     Integer32,
     apexPidMapBlade6InputUdp           Integer32,
     apexPidMapBlade6InputMulticastIp   IpAddress,
     apexPidMapBlade6InputSourceIp      IpAddress,
     apexPidMapBlade6InputPid           Integer32,
     apexPidMapBlade6OutputTsNum        Integer32,
     apexPidMapBlade6OutputPid          Integer32
    }

apexPidMapBlade6Index OBJECT-TYPE
    SYNTAX Integer32(1..256)
    MAX-ACCESS not-accessible
    STATUS current
    DESCRIPTION
        "Index of Pid Mapping Table."
::= { apexPidMapBlade6Entry 1 }

apexPidMapBlade6Enable OBJECT-TYPE
    SYNTAX EnableDisableTYPE
    MAX-ACCESS read-write
    STATUS current
    DESCRIPTION
        "Indicates whether this PID Mapping is enabled or disabled.
        "
::= { apexPidMapBlade6Entry 2 }

apexPidMapBlade6InputInterface OBJECT-TYPE
    SYNTAX Integer32(0..12)
    MAX-ACCESS read-write
    STATUS current
    DESCRIPTION
        "Number of the input GigE interface from which to obtain data."
::= { apexPidMapBlade6Entry 3 }

apexPidMapBlade6InputUdp OBJECT-TYPE
SYNTAX Integer32(0..65535)
    MAX-ACCESS read-write
    STATUS current
    DESCRIPTION
        "Input UDP Port from which to obtain data."
::= { apexPidMapBlade6Entry 4 }

apexPidMapBlade6InputMulticastIp OBJECT-TYPE
    SYNTAX IpAddress
    MAX-ACCESS read-write
    STATUS current
    DESCRIPTION
        "The Multicast receive IP address on which to receive data.

         An IP address of 0.0.0.0 indicates singlecast only.

         Multicast IP addresses 224.0.0.0 to 224.0.0.255 are reserved.
        "
::= { apexPidMapBlade6Entry 5 }

apexPidMapBlade6InputSourceIp OBJECT-TYPE
    SYNTAX IpAddress
    MAX-ACCESS read-write
    STATUS current
    DESCRIPTION
        "This is the IP address of the source device.

         If the router supports IGMP v3 the GBE will only receive data from
         this source IP.  If Source IP is not specified or the router does not
         support IGMP v3 the GBE will receive data from any source device.
         Source IP address must be a valid singlecast address.
        "
::= { apexPidMapBlade6Entry 6 }

apexPidMapBlade6InputPid OBJECT-TYPE
    SYNTAX Integer32(0..8191)
    MAX-ACCESS read-write
    STATUS current
    DESCRIPTION
        "Input MPEG PID to multiplex. When PID Remapping for an output is
         enabled, the input PID value and output PID value can be different. When
         PID Remapping for an output is disabled, the input and output PIDs must
         be the same. Input PID 0 (PAT PID) cannot be mapped by the user.
        "
::= { apexPidMapBlade6Entry 7 }

apexPidMapBlade6OutputTsNum OBJECT-TYPE
    SYNTAX Integer32(0..256)
    MAX-ACCESS read-write
    STATUS current
    DESCRIPTION
        "Output Transport Stream Number of the output on which to place data.
         Zero is only valid if the apexPidMapTable entry is not being used.
        "
::= { apexPidMapBlade6Entry 8 }

apexPidMapBlade6OutputPid OBJECT-TYPE
    SYNTAX Integer32(0..8191)
    MAX-ACCESS read-write
    STATUS current
    DESCRIPTION
        "Output PID to use for the data. This output PID value must match the input
         PID value when PID Remapping for the output stream is disabled.
         Zero is only valid if the apexPidMapTable entry is not being used.
        "
::= { apexPidMapBlade6Entry 9 }


-- ------------------------------------------------------------------------------
--
-- apexPidMapBlade7
--
-- apexPidMapBlade7ApplyTable
--

apexPidMapBlade7ApplyTable OBJECT-TYPE
    SYNTAX SEQUENCE OF ApexPidMapBlade7ApplyEntry
    MAX-ACCESS not-accessible
    STATUS current
    DESCRIPTION
        "Table of Apply Change for the data for PID Map Table.

         A row in this table corresponds to the same row index in the
         PID Map table.
        "
::= { apexPidMapBlade7 1 }

apexPidMapBlade7ApplyEntry OBJECT-TYPE
    SYNTAX ApexPidMapBlade7ApplyEntry
    MAX-ACCESS not-accessible
    STATUS current
    DESCRIPTION
        "PID Map Apply Table Entry."
    INDEX { apexPidMapBlade7ApplyIndex }
::= { apexPidMapBlade7ApplyTable 1 }

ApexPidMapBlade7ApplyEntry ::= SEQUENCE
    {
     apexPidMapBlade7ApplyIndex         Integer32,
     apexPidMapBlade7ApplyChange        ApplyDataToDeviceTYPE
    }

apexPidMapBlade7ApplyIndex OBJECT-TYPE
    SYNTAX Integer32(1..256)
    MAX-ACCESS not-accessible
    STATUS current
    DESCRIPTION
        "The index of the PID Map Apply Table."
::= { apexPidMapBlade7ApplyEntry 1 }

apexPidMapBlade7ApplyChange OBJECT-TYPE
    SYNTAX ApplyDataToDeviceTYPE
    MAX-ACCESS read-write
    STATUS current
    DESCRIPTION
        "The Apply for the row of data in the PID Map Table.

         A row in this table corresponds to the same row index in the
         PID Map table.

         This parameter MUST be set to 'apply' in order for any of the data
         in the PID Map Table row to take effect in the APEX.  This
         parameter MUST be set LAST after all other data in the PID Map
         Table row has been configured.

         @Config(config=no, reboot=no)
        "
::= { apexPidMapBlade7ApplyEntry 2 }
                                            

-- ------------------------------------------------------------------------------
--
-- apexPidMapBlade7Table
--

apexPidMapBlade7Table OBJECT-TYPE
    SYNTAX SEQUENCE OF ApexPidMapBlade7Entry
    MAX-ACCESS not-accessible
    STATUS current
    DESCRIPTION
        "Table of data for Ancillary Pid Mapping. 
         There are 256 rows in this table (i.e. 256 rows per Blade).

         Once written, the change to this table will only take immediate
         effect after apexPidMapBlade7ApplyChange is set to 'apply'.
         However, in order for the change to persist through subsequent
         reboots or power cycles, the change must be saved via apexSaveConfig.

         @Config(config=yes, reboot=no)
         @Commit(param=apexPidMapBlade7ApplyChange, value=2)
         @Save(apexSaveConfig, value=2)
         @File(manrout7.ini, type='ini')
        "
::= { apexPidMapBlade7 2 }

apexPidMapBlade7Entry OBJECT-TYPE
    SYNTAX ApexPidMapBlade7Entry
    MAX-ACCESS not-accessible
    STATUS current
    DESCRIPTION
        "Pid Mapping Table Entry."
    INDEX { apexPidMapBlade7Index }
::= { apexPidMapBlade7Table 1 }

ApexPidMapBlade7Entry ::= SEQUENCE
    {
     apexPidMapBlade7Index              Integer32,
     apexPidMapBlade7Enable             EnableDisableTYPE,
     apexPidMapBlade7InputInterface     Integer32,
     apexPidMapBlade7InputUdp           Integer32,
     apexPidMapBlade7InputMulticastIp   IpAddress,
     apexPidMapBlade7InputSourceIp      IpAddress,
     apexPidMapBlade7InputPid           Integer32,
     apexPidMapBlade7OutputTsNum        Integer32,
     apexPidMapBlade7OutputPid          Integer32
    }

apexPidMapBlade7Index OBJECT-TYPE
    SYNTAX Integer32(1..256)
    MAX-ACCESS not-accessible
    STATUS current
    DESCRIPTION
        "Index of Pid Mapping Table."
::= { apexPidMapBlade7Entry 1 }

apexPidMapBlade7Enable OBJECT-TYPE
    SYNTAX EnableDisableTYPE
    MAX-ACCESS read-write
    STATUS current
    DESCRIPTION
        "Indicates whether this PID Mapping is enabled or disabled.
        "
::= { apexPidMapBlade7Entry 2 }

apexPidMapBlade7InputInterface OBJECT-TYPE
    SYNTAX Integer32(0..12)
    MAX-ACCESS read-write
    STATUS current
    DESCRIPTION
        "Number of the input GigE interface from which to obtain data."
::= { apexPidMapBlade7Entry 3 }

apexPidMapBlade7InputUdp OBJECT-TYPE
SYNTAX Integer32(0..65535)
    MAX-ACCESS read-write
    STATUS current
    DESCRIPTION
        "Input UDP Port from which to obtain data."
::= { apexPidMapBlade7Entry 4 }

apexPidMapBlade7InputMulticastIp OBJECT-TYPE
    SYNTAX IpAddress
    MAX-ACCESS read-write
    STATUS current
    DESCRIPTION
        "The Multicast receive IP address on which to receive data.

         An IP address of 0.0.0.0 indicates singlecast only.

         Multicast IP addresses 224.0.0.0 to 224.0.0.255 are reserved.
        "
::= { apexPidMapBlade7Entry 5 }

apexPidMapBlade7InputSourceIp OBJECT-TYPE
    SYNTAX IpAddress
    MAX-ACCESS read-write
    STATUS current
    DESCRIPTION
        "This is the IP address of the source device.

         If the router supports IGMP v3 the GBE will only receive data from
         this source IP.  If Source IP is not specified or the router does not
         support IGMP v3 the GBE will receive data from any source device.
         Source IP address must be a valid singlecast address.
        "
::= { apexPidMapBlade7Entry 6 }

apexPidMapBlade7InputPid OBJECT-TYPE
    SYNTAX Integer32(0..8191)
    MAX-ACCESS read-write
    STATUS current
    DESCRIPTION
        "Input MPEG PID to multiplex. When PID Remapping for an output is
         enabled, the input PID value and output PID value can be different. When
         PID Remapping for an output is disabled, the input and output PIDs must
         be the same. Input PID 0 (PAT PID) cannot be mapped by the user.
        "
::= { apexPidMapBlade7Entry 7 }

apexPidMapBlade7OutputTsNum OBJECT-TYPE
    SYNTAX Integer32(0..256)
    MAX-ACCESS read-write
    STATUS current
    DESCRIPTION
        "Output Transport Stream Number of the output on which to place data.
         Zero is only valid if the apexPidMapTable entry is not being used.
        "
::= { apexPidMapBlade7Entry 8 }

apexPidMapBlade7OutputPid OBJECT-TYPE
    SYNTAX Integer32(0..8191)
    MAX-ACCESS read-write
    STATUS current
    DESCRIPTION
        "Output PID to use for the data. This output PID value must match the input
         PID value when PID Remapping for the output stream is disabled.
         Zero is only valid if the apexPidMapTable entry is not being used.
        "
::= { apexPidMapBlade7Entry 9 }


-- ------------------------------------------------------------------------------
--
-- apexPidMapBlade8
--
-- apexPidMapBlade8ApplyTable
--

apexPidMapBlade8ApplyTable OBJECT-TYPE
    SYNTAX SEQUENCE OF ApexPidMapBlade8ApplyEntry
    MAX-ACCESS not-accessible
    STATUS current
    DESCRIPTION
        "Table of Apply Change for the data for PID Map Table.

         A row in this table corresponds to the same row index in the
         PID Map table.
        "
::= { apexPidMapBlade8 1 }

apexPidMapBlade8ApplyEntry OBJECT-TYPE
    SYNTAX ApexPidMapBlade8ApplyEntry
    MAX-ACCESS not-accessible
    STATUS current
    DESCRIPTION
        "PID Map Apply Table Entry."
    INDEX { apexPidMapBlade8ApplyIndex }
::= { apexPidMapBlade8ApplyTable 1 }

ApexPidMapBlade8ApplyEntry ::= SEQUENCE
    {
     apexPidMapBlade8ApplyIndex         Integer32,
     apexPidMapBlade8ApplyChange        ApplyDataToDeviceTYPE
    }

apexPidMapBlade8ApplyIndex OBJECT-TYPE
    SYNTAX Integer32(1..256)
    MAX-ACCESS not-accessible
    STATUS current
    DESCRIPTION
        "The index of the PID Map Apply Table."
::= { apexPidMapBlade8ApplyEntry 1 }

apexPidMapBlade8ApplyChange OBJECT-TYPE
    SYNTAX ApplyDataToDeviceTYPE
    MAX-ACCESS read-write
    STATUS current
    DESCRIPTION
        "The Apply for the row of data in the PID Map Table.

         A row in this table corresponds to the same row index in the
         PID Map table.

         This parameter MUST be set to 'apply' in order for any of the data
         in the PID Map Table row to take effect in the APEX.  This
         parameter MUST be set LAST after all other data in the PID Map
         Table row has been configured.

         @Config(config=no, reboot=no)
        "
::= { apexPidMapBlade8ApplyEntry 2 }
                                            

-- ------------------------------------------------------------------------------
--
-- apexPidMapBlade8Table
--

apexPidMapBlade8Table OBJECT-TYPE
    SYNTAX SEQUENCE OF ApexPidMapBlade8Entry
    MAX-ACCESS not-accessible
    STATUS current
    DESCRIPTION
        "Table of data for Ancillary Pid Mapping. 
         There are 256 rows in this table (i.e. 256 rows per Blade).

         Once written, the change to this table will only take immediate
         effect after apexPidMapBlade8ApplyChange is set to 'apply'.
         However, in order for the change to persist through subsequent
         reboots or power cycles, the change must be saved via apexSaveConfig.

         @Config(config=yes, reboot=no)
         @Commit(param=apexPidMapBlade8ApplyChange, value=2)
         @Save(apexSaveConfig, value=2)
         @File(manrout8.ini, type='ini')
        "
::= { apexPidMapBlade8 2 }

apexPidMapBlade8Entry OBJECT-TYPE
    SYNTAX ApexPidMapBlade8Entry
    MAX-ACCESS not-accessible
    STATUS current
    DESCRIPTION
        "Pid Mapping Table Entry."
    INDEX { apexPidMapBlade8Index }
::= { apexPidMapBlade8Table 1 }

ApexPidMapBlade8Entry ::= SEQUENCE
    {
     apexPidMapBlade8Index              Integer32,
     apexPidMapBlade8Enable             EnableDisableTYPE,
     apexPidMapBlade8InputInterface     Integer32,
     apexPidMapBlade8InputUdp           Integer32,
     apexPidMapBlade8InputMulticastIp   IpAddress,
     apexPidMapBlade8InputSourceIp      IpAddress,
     apexPidMapBlade8InputPid           Integer32,
     apexPidMapBlade8OutputTsNum        Integer32,
     apexPidMapBlade8OutputPid          Integer32
    }

apexPidMapBlade8Index OBJECT-TYPE
    SYNTAX Integer32(1..256)
    MAX-ACCESS not-accessible
    STATUS current
    DESCRIPTION
        "Index of Pid Mapping Table."
::= { apexPidMapBlade8Entry 1 }

apexPidMapBlade8Enable OBJECT-TYPE
    SYNTAX EnableDisableTYPE
    MAX-ACCESS read-write
    STATUS current
    DESCRIPTION
        "Indicates whether this PID Mapping is enabled or disabled.
        "
::= { apexPidMapBlade8Entry 2 }

apexPidMapBlade8InputInterface OBJECT-TYPE
    SYNTAX Integer32(0..12)
    MAX-ACCESS read-write
    STATUS current
    DESCRIPTION
        "Number of the input GigE interface from which to obtain data."
::= { apexPidMapBlade8Entry 3 }

apexPidMapBlade8InputUdp OBJECT-TYPE
SYNTAX Integer32(0..65535)
    MAX-ACCESS read-write
    STATUS current
    DESCRIPTION
        "Input UDP Port from which to obtain data."
::= { apexPidMapBlade8Entry 4 }

apexPidMapBlade8InputMulticastIp OBJECT-TYPE
    SYNTAX IpAddress
    MAX-ACCESS read-write
    STATUS current
    DESCRIPTION
        "The Multicast receive IP address on which to receive data.

         An IP address of 0.0.0.0 indicates singlecast only.

         Multicast IP addresses 224.0.0.0 to 224.0.0.255 are reserved.
        "
::= { apexPidMapBlade8Entry 5 }

apexPidMapBlade8InputSourceIp OBJECT-TYPE
    SYNTAX IpAddress
    MAX-ACCESS read-write
    STATUS current
    DESCRIPTION
        "This is the IP address of the source device.

         If the router supports IGMP v3 the GBE will only receive data from
         this source IP.  If Source IP is not specified or the router does not
         support IGMP v3 the GBE will receive data from any source device.
         Source IP address must be a valid singlecast address.
        "
::= { apexPidMapBlade8Entry 6 }

apexPidMapBlade8InputPid OBJECT-TYPE
    SYNTAX Integer32(0..8191)
    MAX-ACCESS read-write
    STATUS current
    DESCRIPTION
        "Input MPEG PID to multiplex. When PID Remapping for an output is
         enabled, the input PID value and output PID value can be different. When
         PID Remapping for an output is disabled, the input and output PIDs must
         be the same. Input PID 0 (PAT PID) cannot be mapped by the user.
        "
::= { apexPidMapBlade8Entry 7 }

apexPidMapBlade8OutputTsNum OBJECT-TYPE
    SYNTAX Integer32(0..256)
    MAX-ACCESS read-write
    STATUS current
    DESCRIPTION
        "Output Transport Stream Number of the output on which to place data.
         Zero is only valid if the apexPidMapTable entry is not being used.
        "
::= { apexPidMapBlade8Entry 8 }

apexPidMapBlade8OutputPid OBJECT-TYPE
    SYNTAX Integer32(0..8191)
    MAX-ACCESS read-write
    STATUS current
    DESCRIPTION
        "Output PID to use for the data. This output PID value must match the input
         PID value when PID Remapping for the output stream is disabled.
         Zero is only valid if the apexPidMapTable entry is not being used.
        "
::= { apexPidMapBlade8Entry 9 }

              
-- ------------------------------------------------------------------------------
--
-- apexPidMapStatus
--
-- apexPidMapStatusGeneral
--

apexPidMapMaxPidMappings OBJECT-TYPE
    SYNTAX Integer32
    MAX-ACCESS read-only
    STATUS current
    DESCRIPTION
        "Maximum number of Ancillary PID mappings supported."
::= { apexPidMapStatusGeneral 1 }
                                        
                                        
-- ------------------------------------------------------------------------------
--
-- apexPidMapStatusTable
--

apexPidMapStatusTable OBJECT-TYPE
    SYNTAX SEQUENCE OF ApexPidMapStatusEntry
    MAX-ACCESS not-accessible
    STATUS current
    DESCRIPTION
        "Table of status data for PID Map Table. 
         There is 1 row for each blade.
        "
::= { apexPidMapStatus 2 }

apexPidMapStatusEntry OBJECT-TYPE
    SYNTAX ApexPidMapStatusEntry
    MAX-ACCESS not-accessible
    STATUS current
    DESCRIPTION
        "PID Map Status Table Entry."
    INDEX { apexPidMapBladeNum }
::= { apexPidMapStatusTable 1 }

ApexPidMapStatusEntry ::= SEQUENCE
    {
     apexPidMapBladeNum             Integer32,
     apexPidMapInvalidApplyText     DisplayString
    }

apexPidMapBladeNum OBJECT-TYPE
    SYNTAX Integer32(1..8)
    MAX-ACCESS not-accessible
    STATUS current
    DESCRIPTION
        "Blade Number."
::= { apexPidMapStatusEntry 1 }

apexPidMapInvalidApplyText OBJECT-TYPE
    SYNTAX DisplayString (SIZE (0..80))
    MAX-ACCESS read-only
    STATUS current
    DESCRIPTION
        "When apexPidMapBlade#ApplyChange is set to applyNotInProgressInvalidData,
         this entry may contain a text description of what was wrong with the data.
         This entry contains the description for the most recent apply
         of a related entry that was invalid. 
        "
::= { apexPidMapStatusEntry 2 }


-- ------------------------------------------------------------------------------
--
-- apexInsertion
--
-- apexInsertionConfig
--
-- apexInsertionConfigGeneral
--

-- none


-- ------------------------------------------------------------------------------
--
-- apexInsertionStatus
--
-- apexInsertionStatusGeneral
--

-- none


-- ------------------------------------------------------------------------------
--
-- apexInsertPacketStatisticsTable
--

apexInsertPacketStatisticsTable OBJECT-TYPE
    SYNTAX SEQUENCE OF ApexInsertPacketStatisticsEntry
    MAX-ACCESS not-accessible
    STATUS current
    DESCRIPTION
        "Table of Output Transport Stream Insert Packet Statistics.
         Indexed by Output Transport Stream number."
::= { apexInsertionStatus 2 }

apexInsertPacketStatisticsEntry OBJECT-TYPE
    SYNTAX ApexInsertPacketStatisticsEntry
    MAX-ACCESS not-accessible
    STATUS current
    DESCRIPTION
        "A row in the Output Transport Stream Insert Packet Statistics table."
    INDEX { apexInsertPacketStatBladeNum, apexInsertPacketStatOutputTsNum }
::= { apexInsertPacketStatisticsTable 1 }

ApexInsertPacketStatisticsEntry ::= SEQUENCE
    {
     apexInsertPacketStatBladeNum       Integer32,
     apexInsertPacketStatOutputTsNum    Integer32,
     apexInsertPacketStatTotPkts        Integer32,
     apexInsertPacketStatNumPkts        Integer32
    }

apexInsertPacketStatBladeNum OBJECT-TYPE
    SYNTAX Integer32 (1..8)
    MAX-ACCESS not-accessible
    STATUS current
    DESCRIPTION
        "Blade Number."
::= { apexInsertPacketStatisticsEntry 1 }

apexInsertPacketStatOutputTsNum OBJECT-TYPE
    SYNTAX Integer32 (1..256)
    MAX-ACCESS not-accessible
    STATUS current
    DESCRIPTION
        "Output Transport Stream Number."
::= { apexInsertPacketStatisticsEntry 2 }

apexInsertPacketStatTotPkts OBJECT-TYPE
    SYNTAX Integer32
    MAX-ACCESS read-only
    STATUS current
    DESCRIPTION
        "Total number of packets inserted."
::= { apexInsertPacketStatisticsEntry 3 }

apexInsertPacketStatNumPkts OBJECT-TYPE
    SYNTAX Integer32
    MAX-ACCESS read-only
    STATUS current
    DESCRIPTION
        "Number of packets inserted during the last monitoring
         period (currently 5 seconds)."
::= { apexInsertPacketStatisticsEntry 4 }


-- ------------------------------------------------------------------------------
--
-- apexOutputTransport
--
-- apexOutputTsConfig
--
-- apexOutputTsConfigGeneral
--

-- none


-- ------------------------------------------------------------------------------
--
-- apexOutputTsUtilizationMonitoring
--
-- apexOutputTsUtilizationMonitorGeneral
--

apexOutputTsUtilMonAlarmThreshold OBJECT-TYPE
    SYNTAX Integer32 (0..100)
    MAX-ACCESS read-write
    STATUS current
    DESCRIPTION
        "The threshold, in percent, used to produce the
         apexAlarmOutputUtilizationFault alarm 'minor' while
         monitoring Output Transport Stream Bandwidth Utilization.
         An alarm of 'minor' will occur when this threshold is met
         or exceeded for apexOutputTsUtilMonSetAlarmDelay.  The alarm
         will clear after remaining below this threshold for
         apexOutputTsUtilMonClearAlarmDelay.

         Once written, the change to this parameter will take immediate
         effect.  However, in order for the change to persist through
         subsequent reboots or power cycles, the change must be saved via
         the apexSaveConfig parameter.

         @Config(config=yes, reboot=no)
         @Save(apexSaveConfig, value=2)
         @File(config.ini, type='ini')
        "
::= { apexOutputTsUtilizationMonitorGeneral 1 }

apexOutputTsUtilMonSetAlarmDelay OBJECT-TYPE
    SYNTAX Integer32 (0..900)
    MAX-ACCESS read-write
    STATUS current
    DESCRIPTION
        "This is the time in seconds that the Output Transport Stream
         must be at or exceeding apexOutputTsUtilMonAlarmThreshold before
         setting the apexAlarmOutputUtilizationFault alarm.

         Once written, the change to this parameter will take immediate
         effect.  However, in order for the change to persist through
         subsequent reboots or power cycles, the change must be saved via
         the apexSaveConfig parameter.

         @Config(config=yes, reboot=no)
         @Save(apexSaveConfig, value=2)
         @File(config.ini, type='ini')
        "
::= { apexOutputTsUtilizationMonitorGeneral 2 }

apexOutputTsUtilMonClearAlarmDelay OBJECT-TYPE
    SYNTAX Integer32 (0..900)
    MAX-ACCESS read-write
    STATUS current
    DESCRIPTION
        "This is the time in seconds that the Output Transport Stream
         must be below apexOutputTsUtilMonAlarmThreshold before
         clearing the apexAlarmOutputUtilizationFault alarm.

         Once written, the change to this parameter will take immediate
         effect.  However, in order for the change to persist through
         subsequent reboots or power cycles, the change must be saved via
         the apexSaveConfig parameter.

         @Config(config=yes, reboot=no)
         @Save(apexSaveConfig, value=2)
         @File(config.ini, type='ini')
        "
::= { apexOutputTsUtilizationMonitorGeneral 3 }


-- ------------------------------------------------------------------------------
--
-- apexOutputTsConfigBlade1
--
-- apexOutputTsConfBlade1ApplyTable
--

apexOutputTsConfBlade1ApplyTable OBJECT-TYPE
    SYNTAX SEQUENCE OF ApexOutputTsConfBlade1ApplyEntry
    MAX-ACCESS not-accessible
    STATUS current
    DESCRIPTION
        "Table of Apply Change for Output Ts Config Table.
        
         This apply is only used for apexOutputTsConfBlade1OperatingMode, 
         apexOutputTsConfBlade1OutPatTsId, and 
         apexOutputTsConfBlade1EncryptionType."
::= { apexOutputTsConfigBlade1 1 }

apexOutputTsConfBlade1ApplyEntry OBJECT-TYPE
    SYNTAX ApexOutputTsConfBlade1ApplyEntry
    MAX-ACCESS not-accessible
    STATUS current
    DESCRIPTION
        "Output Transport Stream Apply Table Entry."
    INDEX { apexOutputTsConfBlade1ApplyIndex }
::= { apexOutputTsConfBlade1ApplyTable 1 }

ApexOutputTsConfBlade1ApplyEntry ::= SEQUENCE
    {
     apexOutputTsConfBlade1ApplyIndex           Integer32,
     apexOutputTsConfBlade1ApplyChange          ApplyDataToDeviceTYPE
    }
    
apexOutputTsConfBlade1ApplyIndex OBJECT-TYPE
    SYNTAX Integer32(1..256)
    MAX-ACCESS not-accessible
    STATUS current
    DESCRIPTION
        "Index of Output Transport Stream Apply Table."
::= { apexOutputTsConfBlade1ApplyEntry 1 }

apexOutputTsConfBlade1ApplyChange OBJECT-TYPE
    SYNTAX ApplyDataToDeviceTYPE
    MAX-ACCESS read-write
    STATUS current
    DESCRIPTION
        "The apply for Output Ts Config Table.  This apply is only used for:
           apexOutputTsConfBlade1OperatingMode
           apexOutputTsConfBlade1OutPatTsId
           apexOutputTsConfBlade1EncryptionType
           apexOutputTsConfBlade1SimulcryptMode
           apexOutputTsConfBlade1DepiRemoteId
           apexOutputTsConfBlade1QamReplicationRfPort
         
         A row in this table corresponds to the same row index in the
         Output Ts Config table.

         This parameter MUST be set to 'apply' in order for the items listed
         above to take effect in the APEX.  This parameter MUST be set LAST 
         after the relevant data in the Output Ts Config row has been configured.

         @Config(config=no, reboot=no)
        "
::= { apexOutputTsConfBlade1ApplyEntry 2 }     


-- ------------------------------------------------------------------------------
--
-- apexOutputTsConfigBlade1Table
--

apexOutputTsConfigBlade1Table OBJECT-TYPE
    SYNTAX SEQUENCE OF ApexOutputTsConfigBlade1Entry
    MAX-ACCESS not-accessible
    STATUS current
    DESCRIPTION
        "This is a table of configuration parameters for Output Transport
         Streams.

         Once written, a change to the following parameters will only take 
         effect after the appropriate apexOutputTsConfBlade1ApplyChange
         is set to 'apply':  
           apexOutputTsConfBlade1OperatingMode
           apexOutputTsConfBlade1OutPatTsId
           apexOutputTsConfBlade1EncryptionType
           apexOutputTsConfBlade1SimulcryptMode
           apexOutputTsConfBlade1DepiRemoteId
           apexOutputTsConfBlade1QamReplicationRfPort
         
         All other changes to this table will take immediate effect.
         In order for the change to persist through subsequent reboots or power
         cycles, the change must be saved via the apexSaveConfig parameter.

         @Config(config=yes, reboot=no)
         @Save(apexSaveConfig, value=2)
         @File(config.ini, type='ini')
        "
::= { apexOutputTsConfigBlade1 2 }

apexOutputTsConfigBlade1Entry OBJECT-TYPE
    SYNTAX ApexOutputTsConfigBlade1Entry
    MAX-ACCESS not-accessible
    STATUS current
    DESCRIPTION
        "Output Transport Stream Configuration Table Entry."
    INDEX { apexOutputTsConfBlade1OutputTsNum }
::= { apexOutputTsConfigBlade1Table 1 }

ApexOutputTsConfigBlade1Entry ::= SEQUENCE
    {
     apexOutputTsConfBlade1OutputTsNum          Integer32,
     apexOutputTsConfBlade1PidRemappingMode     INTEGER,
     apexOutputTsConfBlade1OperatingMode        INTEGER,
     apexOutputTsConfBlade1OutPatTsId           Integer32,
     apexOutputTsConfBlade1EncryptionType       INTEGER,
     apexOutputTsConfBlade1SimulcryptMode       INTEGER,
     apexOutputTsConfBlade1DepiRemoteId         Integer32,
     apexOutputTsConfBlade1QamReplicationRfPort MasterRfPortTYPE
    }

apexOutputTsConfBlade1OutputTsNum OBJECT-TYPE
    SYNTAX Integer32(1..256)
    MAX-ACCESS not-accessible
    STATUS current
    DESCRIPTION
        "Output Transport Stream Number."
::= { apexOutputTsConfigBlade1Entry 1 }

apexOutputTsConfBlade1PidRemappingMode OBJECT-TYPE
    SYNTAX INTEGER
        {
         disabled           (1),
         remapWithoutReuse  (2),
         remapProgramBased  (3),
         remapProgramBased2 (4)
        }
    MAX-ACCESS read-write
    STATUS current
    DESCRIPTION
        "The PID Remapping mode setting.

         When 'disabled', the output PIDs for all services and ancillary PIDs
         are the same as the input PID values. PID collisions can occur when 
         multiple inputs are mapped to the same output. User is responsible for
         ensuring PIDs mapped from multiple input streams are unique.

         When 'remapWithoutReuse', the APEX will determine the output PIDs
         from a predetermined range of PIDs for services and ancillary PIDs.
         The APEX will use a scheme to limit the reuse of service PIDs for each
         service mapping. UDP Port Mapping and Session Control outputs should 
         always have PID Remapping enabled (set to 'remapWithoutReuse').

         When 'remapProgramBased' or 'remapProgramBased2', the APEX will determine 
         the output PIDs from a predetermined range of PIDs for services and 
         ancillary PIDs. The APEX uses a scheme to select the PMT PID based on 
         the program number. The PMT PID is calculated as follows for each mode:
            remapProgramBased =  (Program Number + 1) * 16
            remapProgramBased2 = (Program Number * 16) + 2
         
         The component PIDs are sequential after the PMT PID. This scheme only
         allows for a total of 15 component PIDs per program. Output program
         numbers are also limited (1-255). This scheme is intended to be used
         when in UDP Port Mapping mode at specific sites.

         PID Remapping mode changes can only occur when the output is not in use
         (no service, PID, or stream mapping active to the output).
        "
::= { apexOutputTsConfigBlade1Entry 2 }

apexOutputTsConfBlade1OperatingMode OBJECT-TYPE
    SYNTAX INTEGER
        {
         notInUse       (0),
         rtspSession    (1),
         manualRouting  (2),
         udpMapping     (3),
         rpcSession     (4),
         depi           (5),
         qamReplication (6)
        }
    MAX-ACCESS read-write
    STATUS current
    DESCRIPTION
        "This parameter is used to set the operating mode of the output.

         Operating mode changes can only occur when the output is not in use
         (no service, PID, or stream mapping active to the output).
         RTSP Session
            - User must select either RTSP-R6/D6 or MHA-ERMI to communicate with external
              resource manager. All service mappings on output are controlled
              by the external manager.
            - Only valid when Encryption Type is set to CTE or None
            - Only valid when Simulcrypt Mode is set to None (2.0)
            - PID Remapping mode should be Enabled (Without Reuse)
            
         Manual Routing
            - User manually maps each service
            - Encryption Type can be any valid setting (none, CTE, or Broadcast)
            - Simulcrypt Mode must be None or Enabled
            
         UDP Port Mapping
            - Standard UDP Port Mapping for use with VOD servers. Uses specific
              algorithm based on UDP Port to determine output program mappings.
            - Encryption Type must be None or CTE (broadcast not supported)
            - Simulcrypt Mode must be None or Enabled
            
         RPC Session
            - All service mappings on output are controlled by external manager
              using the RPC protocol.  
            - Only valid when Encryption Type is set to CTE or None
            - Only valid when Simulcrypt Mode is set to None (2.0)
            - PID Remapping mode should be Enabled (Without Reuse)

         Operating mode changes can only occur when the output is not in use
         (no service, PID, or stream mapping active to the output).
         
         @Commit(param=apexOutputTsConfBlade1ApplyChange, value=2)
        "
::= { apexOutputTsConfigBlade1Entry 3 }

apexOutputTsConfBlade1OutPatTsId OBJECT-TYPE
    SYNTAX Integer32(0..65535)
    MAX-ACCESS read-write
    STATUS current
    DESCRIPTION
        "Output Transport Stream ID to use for the output PAT in this Output
         Transport Stream. Changes to the output PAT TS ID can be made at any
         time and will cause the output PAT to automatically be updated to
         reflect the new TS ID setting.
         
         @Commit(param=apexOutputTsConfBlade1ApplyChange, value=2)
        "
::= { apexOutputTsConfigBlade1Entry 4 }

apexOutputTsConfBlade1EncryptionType OBJECT-TYPE
    SYNTAX INTEGER
        {
         noEncryption             (0),
         cte                      (1)
        }
    MAX-ACCESS read-write
    STATUS current
    DESCRIPTION
        "This parameter is used to set the encryption type of the output.

         'noEncryption'
            - All services are output in the clear

         'cte'
            - Services on output use Common Tier Encryption. CTE parameters
              determine encryption mode, copy protection, and tiers. All services
              in CTE mode use the exact same configuration settings.
            - Valid for all operating modes.
            - Simulcrypt Mode must be set to None.

         @Commit(param=apexOutputTsConfBlade1ApplyChange, value=2)
        "
::= { apexOutputTsConfigBlade1Entry 5 }

apexOutputTsConfBlade1SimulcryptMode OBJECT-TYPE
    SYNTAX INTEGER
        {
         none             (0),
         enabledEmms      (1),
         enabledNoEmms    (2)
        }
    MAX-ACCESS read-write
    STATUS current
    DESCRIPTION
        "This parameter is used to set the Simulcrypt mode of the output. Changes to this
         parameter can only be done when there are no programs mapped to the output. All
         programs must be disabled on an output before this parameter can be changed.

         'none' 
            - Used for normal Mediacypher only encryption (CTE or session Encryption). 

         'enabledEmms'
            - Enabled with EMMs insertion.
            - Used to indicate an external or internal EIS will control the encryption of  
              all services on the output.
            - Only valid when:
               - Encryption Type is set to 'noEncryption'
               - Operating Mode is set to 'manualRouting' or 'udpMapping' (2.0)
               - Encryption Algorithm is set to 'dvb-csa'
               
         'enabledNoEmms'
            - Enabled without EMMs insertion.
            - Used to indicate an external or internal EIS will control the encryption of  
              all services on the output.
            - Only valid when:
               - Encryption Type is set to 'noEncryption'
               - Operating Mode is set to 'manualRouting' or 'udpMapping' (2.0)
               - Encryption Algorithm is set to 'dvb-csa'
   
         @Commit(param=apexOutputTsConfBlade1ApplyChange, value=2)
        "
::= { apexOutputTsConfigBlade1Entry 6 }

apexOutputTsConfBlade1DepiRemoteId OBJECT-TYPE
    SYNTAX Integer32(0..65535)
    MAX-ACCESS read-write
    STATUS current
    DESCRIPTION
        "Unique identifier within the systems. Allows communication with the CMTS-core 
         to establish the DEPI control plane.
         
         @Commit(param=apexOutputTsConfBlade1ApplyChange, value=2)
        "
::= { apexOutputTsConfigBlade1Entry 7 }

apexOutputTsConfBlade1QamReplicationRfPort OBJECT-TYPE
    SYNTAX MasterRfPortTYPE
    MAX-ACCESS read-write
    STATUS current
    DESCRIPTION
        "RF Port when operating mode set to QAM Replication. Must be set to None
         when operating mode is not set to QAM Replication. 
         
         The Master RF Port from which this slave port is to be replicated.
         
         Selection restricted as follows:
         
                                 Slave
                         ---------------------
            Master       RF1   RF2   RF3   RF4
            ------       ---   ---   ---   ---
            none          Y     Y     Y     Y
            port1         N     Y     Y     Y
            port2         N     N     Y     Y
            port3         N     N     N     Y
        
         @Commit(param=apexOutputTsConfBlade1ApplyChange, value=2)
        "
::= { apexOutputTsConfigBlade1Entry 8 }


-- ------------------------------------------------------------------------------
--
-- apexOutputTsConfigBlade2
--
-- apexOutputTsConfBlade2ApplyTable
--

apexOutputTsConfBlade2ApplyTable OBJECT-TYPE
    SYNTAX SEQUENCE OF ApexOutputTsConfBlade2ApplyEntry
    MAX-ACCESS not-accessible
    STATUS current
    DESCRIPTION
        "Table of Apply Change for Output Ts Config Table.
        
         This apply is only used for apexOutputTsConfBlade2OperatingMode, 
         apexOutputTsConfBlade2OutPatTsId, and 
         apexOutputTsConfBlade2EncryptionType."
::= { apexOutputTsConfigBlade2 1 }

apexOutputTsConfBlade2ApplyEntry OBJECT-TYPE
    SYNTAX ApexOutputTsConfBlade2ApplyEntry
    MAX-ACCESS not-accessible
    STATUS current
    DESCRIPTION
        "Output Transport Stream Apply Table Entry."
    INDEX { apexOutputTsConfBlade2ApplyIndex }
::= { apexOutputTsConfBlade2ApplyTable 1 }

ApexOutputTsConfBlade2ApplyEntry ::= SEQUENCE
    {
     apexOutputTsConfBlade2ApplyIndex           Integer32,
     apexOutputTsConfBlade2ApplyChange          ApplyDataToDeviceTYPE
    }
    
apexOutputTsConfBlade2ApplyIndex OBJECT-TYPE
    SYNTAX Integer32(1..256)
    MAX-ACCESS not-accessible
    STATUS current
    DESCRIPTION
        "Index of Output Transport Stream Apply Table."
::= { apexOutputTsConfBlade2ApplyEntry 1 }

apexOutputTsConfBlade2ApplyChange OBJECT-TYPE
    SYNTAX ApplyDataToDeviceTYPE
    MAX-ACCESS read-write
    STATUS current
    DESCRIPTION
        "The apply for Output Ts Config Table.  This apply is only used for:
           apexOutputTsConfBlade2OperatingMode
           apexOutputTsConfBlade2OutPatTsId
           apexOutputTsConfBlade2EncryptionType
           apexOutputTsConfBlade2SimulcryptMode
           apexOutputTsConfBlade2DepiRemoteId
           apexOutputTsConfBlade2QamReplicationRfPort 

         A row in this table corresponds to the same row index in the
         Output Ts Config table.

         This parameter MUST be set to 'apply' in order for the items listed
         above to take effect in the APEX.  This parameter MUST be set LAST 
         after the relevant data in the Output Ts Config row has been configured.

         @Config(config=no, reboot=no)
        "
::= { apexOutputTsConfBlade2ApplyEntry 2 }     


-- ------------------------------------------------------------------------------
--
-- apexOutputTsConfigBlade2Table
--

apexOutputTsConfigBlade2Table OBJECT-TYPE
    SYNTAX SEQUENCE OF ApexOutputTsConfigBlade2Entry
    MAX-ACCESS not-accessible
    STATUS current
    DESCRIPTION
        "This is a table of configuration parameters for Output Transport
         Streams.

         Once written, a change to the following parameters will only take 
         effect after the appropriate apexOutputTsConfBlade1ApplyChange
         is set to 'apply':  
           apexOutputTsConfBlade2OperatingMode
           apexOutputTsConfBlade2OutPatTsId
           apexOutputTsConfBlade2EncryptionType
           apexOutputTsConfBlade2SimulcryptMode
           apexOutputTsConfBlade2DepiRemoteId
           apexOutputTsConfBlade2QamReplicationRfPort
         
         All other changes to this table will take immediate effect.
         In order for the change to persist through subsequent reboots or power
         cycles, the change must be saved via the apexSaveConfig parameter.

         @Config(config=yes, reboot=no)
         @Save(apexSaveConfig, value=2)
         @File(config.ini, type='ini')
        "
::= { apexOutputTsConfigBlade2 2 }

apexOutputTsConfigBlade2Entry OBJECT-TYPE
    SYNTAX ApexOutputTsConfigBlade2Entry
    MAX-ACCESS not-accessible
    STATUS current
    DESCRIPTION
        "Output Transport Stream Configuration Table Entry."
    INDEX { apexOutputTsConfBlade2OutputTsNum }
::= { apexOutputTsConfigBlade2Table 1 }

ApexOutputTsConfigBlade2Entry ::= SEQUENCE
    {
     apexOutputTsConfBlade2OutputTsNum          Integer32,
     apexOutputTsConfBlade2PidRemappingMode     INTEGER,
     apexOutputTsConfBlade2OperatingMode        INTEGER,
     apexOutputTsConfBlade2OutPatTsId           Integer32,
     apexOutputTsConfBlade2EncryptionType       INTEGER,
     apexOutputTsConfBlade2SimulcryptMode       INTEGER,
     apexOutputTsConfBlade2DepiRemoteId         Integer32,
     apexOutputTsConfBlade2QamReplicationRfPort MasterRfPortTYPE
    }

apexOutputTsConfBlade2OutputTsNum OBJECT-TYPE
    SYNTAX Integer32(1..256)
    MAX-ACCESS not-accessible
    STATUS current
    DESCRIPTION
        "Output Transport Stream Number."
::= { apexOutputTsConfigBlade2Entry 1 }

apexOutputTsConfBlade2PidRemappingMode OBJECT-TYPE
    SYNTAX INTEGER
        {
         disabled           (1),
         remapWithoutReuse  (2),
         remapProgramBased  (3),
         remapProgramBased2 (4)
        }
    MAX-ACCESS read-write
    STATUS current
    DESCRIPTION
        "The PID Remapping mode setting.

         When 'disabled', the output PIDs for all services and ancillary PIDs
         are the same as the input PID values. PID collisions can occur when 
         multiple inputs are mapped to the same output. User is responsible for
         ensuring PIDs mapped from multiple input streams are unique.

         When 'remapWithoutReuse', the APEX will determine the output PIDs
         from a predetermined range of PIDs for services and ancillary PIDs.
         The APEX will use a scheme to limit the reuse of service PIDs for each
         service mapping. UDP Port Mapping and Session Control outputs should 
         always have PID Remapping enabled (set to 'remapWithoutReuse').

         When 'remapProgramBased' or 'remapProgramBased2', the APEX will determine 
         the output PIDs from a predetermined range of PIDs for services and 
         ancillary PIDs. The APEX uses a scheme to select the PMT PID based on 
         the program number. The PMT PID is calculated as follows for each mode:
            remapProgramBased =  (Program Number + 1) * 16
            remapProgramBased2 = (Program Number * 16) + 2
         
         The component PIDs are sequential after the PMT PID. This scheme only
         allows for a total of 15 component PIDs per program. Output program
         numbers are also limited (1-255). This scheme is intended to be used
         when in UDP Port Mapping mode at specific sites.

         PID Remapping mode changes can only occur when the output is not in use
         (no service, PID, or stream mapping active to the output).
        "
::= { apexOutputTsConfigBlade2Entry 2 }

apexOutputTsConfBlade2OperatingMode OBJECT-TYPE
    SYNTAX INTEGER
        {
         notInUse       (0),
         rtspSession    (1),
         manualRouting  (2),
         udpMapping     (3),
         rpcSession     (4),
         depi           (5),
         qamReplication (6)
        }
    MAX-ACCESS read-write
    STATUS current
    DESCRIPTION
        "This parameter is used to set the operating mode of the output.

         Operating mode changes can only occur when the output is not in use
         (no service, PID, or stream mapping active to the output).
         RTSP Session
            - User must select either RTSP-R6/D6 or MHA-ERMI to communicate with external
              resource manager. All service mappings on output are controlled
              by the external manager.
            - Only valid when Encryption Type is set to CTE or None
            - Only valid when Simulcrypt Mode is set to None (2.0)
            - PID Remapping mode should be Enabled (Without Reuse)
            
         Manual Routing
            - User manually maps each service
            - Encryption Type can be any valid setting (none, CTE, or Broadcast)
            - Simulcrypt Mode must be None or Enabled
            
         UDP Port Mapping
            - Standard UDP Port Mapping for use with VOD servers. Uses specific
              algorithm based on UDP Port to determine output program mappings.
            - Encryption Type must be None or CTE (broadcast not supported)
            - Simulcrypt Mode must be None or Enabled
            
         RPC Session
            - All service mappings on output are controlled by external manager
              using the RPC protocol.  
            - Only valid when Encryption Type is set to CTE or None
            - Only valid when Simulcrypt Mode is set to None (2.0)
            - PID Remapping mode should be Enabled (Without Reuse)

         Operating mode changes can only occur when the output is not in use
         (no service, PID, or stream mapping active to the output).
         
         @Commit(param=apexOutputTsConfBlade2ApplyChange, value=2)
        "
::= { apexOutputTsConfigBlade2Entry 3 }

apexOutputTsConfBlade2OutPatTsId OBJECT-TYPE
    SYNTAX Integer32(0..65535)
    MAX-ACCESS read-write
    STATUS current
    DESCRIPTION
        "Output Transport Stream ID to use for the output PAT in this Output
         Transport Stream. Changes to the output PAT TS ID can be made at any
         time and will cause the output PAT to automatically be updated to
         reflect the new TS ID setting.
         
         @Commit(param=apexOutputTsConfBlade2ApplyChange, value=2)
        "
::= { apexOutputTsConfigBlade2Entry 4 }

apexOutputTsConfBlade2EncryptionType OBJECT-TYPE
    SYNTAX INTEGER
        {
         noEncryption             (0),
         cte                      (1)
        }
    MAX-ACCESS read-write
    STATUS current
    DESCRIPTION
        "This parameter is used to set the encryption type of the output.

         'noEncryption'
            - All services are output in the clear

         'cte'
            - Services on output use Common Tier Encryption. CTE parameters
              determine encryption mode, copy protection, and tiers. All services
              in CTE mode use the exact same configuration settings.
            - Valid for all operating modes.
            - Simulcrypt Mode must be set to None.

         @Commit(param=apexOutputTsConfBlade2ApplyChange, value=2)
        "
::= { apexOutputTsConfigBlade2Entry 5 }

apexOutputTsConfBlade2SimulcryptMode OBJECT-TYPE
    SYNTAX INTEGER
        {
         none             (0),
         enabledEmms      (1),
         enabledNoEmms    (2)
        }
    MAX-ACCESS read-write
    STATUS current
    DESCRIPTION
        "This parameter is used to set the Simulcrypt mode of the output. Changes to this
         parameter can only be done when there are no programs mapped to the output. All
         programs must be disabled on an output before this parameter can be changed.
         'none' 
            - Used for normal Mediacypher only encryption (CTE or session Encryption). 

         'enabledEmms'
            - Enabled with EMMs insertion.
            - Used to indicate an external or internal EIS will control the encryption of  
              all services on the output.
            - Only valid when:
               - Encryption Type is set to 'noEncryption'
               - Operating Mode is set to 'manualRouting' or 'udpMapping' (2.0)
               - Encryption Algorithm is set to 'dvb-csa'
               
         'enabledNoEmms'
            - Enabled without EMMs insertion.
            - Used to indicate an external or internal EIS will control the encryption of  
              all services on the output.
            - Only valid when:
               - Encryption Type is set to 'noEncryption'
               - Operating Mode is set to 'manualRouting' or 'udpMapping' (2.0)
               - Encryption Algorithm is set to 'dvb-csa'
   
         @Commit(param=apexOutputTsConfBlade2ApplyChange, value=2)
        "
::= { apexOutputTsConfigBlade2Entry 6 }

apexOutputTsConfBlade2DepiRemoteId OBJECT-TYPE
    SYNTAX Integer32(0..65535)
    MAX-ACCESS read-write
    STATUS current
    DESCRIPTION
        "Unique identifier within the systems. Allows communication with the CMTS-core 
         to establish the DEPI control plane.
         
         @Commit(param=apexOutputTsConfBlade2ApplyChange, value=2)
        "
::= { apexOutputTsConfigBlade2Entry 7 }

apexOutputTsConfBlade2QamReplicationRfPort OBJECT-TYPE
    SYNTAX MasterRfPortTYPE
    MAX-ACCESS read-write
    STATUS current
    DESCRIPTION
        "RF Port when operating mode set to QAM Replication. Must be set to None
         when operating mode is not set to QAM Replication. 
         
         The Master RF Port from which this slave port is to be replicated.
         
         Selection restricted as follows:
         
                                 Slave
                         ---------------------
            Master       RF1   RF2   RF3   RF4
            ------       ---   ---   ---   ---
            none          Y     Y     Y     Y
            port1         N     Y     Y     Y
            port2         N     N     Y     Y
            port3         N     N     N     Y
        
         @Commit(param=apexOutputTsConfBlade2ApplyChange, value=2)
        "
::= { apexOutputTsConfigBlade2Entry 8 }


-- ------------------------------------------------------------------------------
--
-- apexOutputTsConfigBlade3
--
-- apexOutputTsConfBlade3ApplyTable
--

apexOutputTsConfBlade3ApplyTable OBJECT-TYPE
    SYNTAX SEQUENCE OF ApexOutputTsConfBlade3ApplyEntry
    MAX-ACCESS not-accessible
    STATUS current
    DESCRIPTION
        "Table of Apply Change for Output Ts Config Table.
        
         This apply is only used for apexOutputTsConfBlade3OperatingMode, 
         apexOutputTsConfBlade3OutPatTsId,  and 
         apexOutputTsConfBlade3EncryptionType."
::= { apexOutputTsConfigBlade3 1 }

apexOutputTsConfBlade3ApplyEntry OBJECT-TYPE
    SYNTAX ApexOutputTsConfBlade3ApplyEntry
    MAX-ACCESS not-accessible
    STATUS current
    DESCRIPTION
        "Output Transport Stream Apply Table Entry."
    INDEX { apexOutputTsConfBlade3ApplyIndex }
::= { apexOutputTsConfBlade3ApplyTable 1 }

ApexOutputTsConfBlade3ApplyEntry ::= SEQUENCE
    {
     apexOutputTsConfBlade3ApplyIndex           Integer32,
     apexOutputTsConfBlade3ApplyChange          ApplyDataToDeviceTYPE
    }
    
apexOutputTsConfBlade3ApplyIndex OBJECT-TYPE
    SYNTAX Integer32(1..256)
    MAX-ACCESS not-accessible
    STATUS current
    DESCRIPTION
        "Index of Output Transport Stream Apply Table."
::= { apexOutputTsConfBlade3ApplyEntry 1 }

apexOutputTsConfBlade3ApplyChange OBJECT-TYPE
    SYNTAX ApplyDataToDeviceTYPE
    MAX-ACCESS read-write
    STATUS current
    DESCRIPTION
        "The apply for Output Ts Config Table.  This apply is only used for:
           apexOutputTsConfBlade3OperatingMode
           apexOutputTsConfBlade3OutPatTsId
           apexOutputTsConfBlade3EncryptionType
           apexOutputTsConfBlade3SimulcryptMode
           apexOutputTsConfBlade3DepiRemoteId
           apexOutputTsConfBlade3QamReplicationRfPort

         A row in this table corresponds to the same row index in the
         Output Ts Config table.

         This parameter MUST be set to 'apply' in order for the items listed
         above to take effect in the APEX.  This parameter MUST be set LAST 
         after the relevant data in the Output Ts Config row has been configured.

         @Config(config=no, reboot=no)
        "
::= { apexOutputTsConfBlade3ApplyEntry 2 }     


-- ------------------------------------------------------------------------------
--
-- apexOutputTsConfigBlade3Table
--

apexOutputTsConfigBlade3Table OBJECT-TYPE
    SYNTAX SEQUENCE OF ApexOutputTsConfigBlade3Entry
    MAX-ACCESS not-accessible
    STATUS current
    DESCRIPTION
        "This is a table of configuration parameters for Output Transport
         Streams.

         Once written, a change to the following parameters will only take 
         effect after the appropriate apexOutputTsConfBlade1ApplyChange
         is set to 'apply':  
           apexOutputTsConfBlade3OperatingMode
           apexOutputTsConfBlade3OutPatTsId
           apexOutputTsConfBlade3EncryptionType
           apexOutputTsConfBlade3SimulcryptMode
           apexOutputTsConfBlade3DepiRemoteId
           apexOutputTsConfBlade3QamReplicationRfPort
         
         All other changes to this table will take immediate effect.
         In order for the change to persist through subsequent reboots or power
         cycles, the change must be saved via the apexSaveConfig parameter.

         @Config(config=yes, reboot=no)
         @Save(apexSaveConfig, value=2)
         @File(config.ini, type='ini')
        "
::= { apexOutputTsConfigBlade3 2 }

apexOutputTsConfigBlade3Entry OBJECT-TYPE
    SYNTAX ApexOutputTsConfigBlade3Entry
    MAX-ACCESS not-accessible
    STATUS current
    DESCRIPTION
        "Output Transport Stream Configuration Table Entry."
    INDEX { apexOutputTsConfBlade3OutputTsNum }
::= { apexOutputTsConfigBlade3Table 1 }

ApexOutputTsConfigBlade3Entry ::= SEQUENCE
    {
     apexOutputTsConfBlade3OutputTsNum          Integer32,
     apexOutputTsConfBlade3PidRemappingMode     INTEGER,
     apexOutputTsConfBlade3OperatingMode        INTEGER,
     apexOutputTsConfBlade3OutPatTsId           Integer32,
     apexOutputTsConfBlade3EncryptionType       INTEGER,
     apexOutputTsConfBlade3SimulcryptMode       INTEGER,
     apexOutputTsConfBlade3DepiRemoteId         Integer32,
     apexOutputTsConfBlade3QamReplicationRfPort MasterRfPortTYPE
    }

apexOutputTsConfBlade3OutputTsNum OBJECT-TYPE
    SYNTAX Integer32(1..256)
    MAX-ACCESS not-accessible
    STATUS current
    DESCRIPTION
        "Output Transport Stream Number."
::= { apexOutputTsConfigBlade3Entry 1 }

apexOutputTsConfBlade3PidRemappingMode OBJECT-TYPE
    SYNTAX INTEGER
        {
         disabled           (1),
         remapWithoutReuse  (2),
         remapProgramBased  (3),
         remapProgramBased2 (4)
        }
    MAX-ACCESS read-write
    STATUS current
    DESCRIPTION
        "The PID Remapping mode setting.

         When 'disabled', the output PIDs for all services and ancillary PIDs
         are the same as the input PID values. PID collisions can occur when 
         multiple inputs are mapped to the same output. User is responsible for
         ensuring PIDs mapped from multiple input streams are unique.

         When 'remapWithoutReuse', the APEX will determine the output PIDs
         from a predetermined range of PIDs for services and ancillary PIDs.
         The APEX will use a scheme to limit the reuse of service PIDs for each
         service mapping. UDP Port Mapping and Session Control outputs should 
         always have PID Remapping enabled (set to 'remapWithoutReuse').

         When 'remapProgramBased' or 'remapProgramBased2', the APEX will determine 
         the output PIDs from a predetermined range of PIDs for services and 
         ancillary PIDs. The APEX uses a scheme to select the PMT PID based on 
         the program number. The PMT PID is calculated as follows for each mode:
            remapProgramBased =  (Program Number + 1) * 16
            remapProgramBased2 = (Program Number * 16) + 2
         
         The component PIDs are sequential after the PMT PID. This scheme only
         allows for a total of 15 component PIDs per program. Output program
         numbers are also limited (1-255). This scheme is intended to be used
         when in UDP Port Mapping mode at specific sites.

         PID Remapping mode changes can only occur when the output is not in use
         (no service, PID, or stream mapping active to the output).
        "
::= { apexOutputTsConfigBlade3Entry 2 }

apexOutputTsConfBlade3OperatingMode OBJECT-TYPE
    SYNTAX INTEGER
        {
         notInUse       (0),
         rtspSession    (1),
         manualRouting  (2),
         udpMapping     (3),
         rpcSession     (4),
         depi           (5),
         qamReplication (6)
        }
    MAX-ACCESS read-write
    STATUS current
    DESCRIPTION
        "This parameter is used to set the operating mode of the output.

         Operating mode changes can only occur when the output is not in use
         (no service, PID, or stream mapping active to the output).
         RTSP Session
            - User must select either RTSP-R6/D6 or MHA-ERMI to communicate with external
              resource manager. All service mappings on output are controlled
              by the external manager.
            - Only valid when Encryption Type is set to CTE or None
            - Only valid when Simulcrypt Mode is set to None (2.0)
            - PID Remapping mode should be Enabled (Without Reuse)
            
         Manual Routing
            - User manually maps each service
            - Encryption Type can be any valid setting (none, CTE, or Broadcast)
            - Simulcrypt Mode must be None or Enabled
            
         UDP Port Mapping
            - Standard UDP Port Mapping for use with VOD servers. Uses specific
              algorithm based on UDP Port to determine output program mappings.
            - Encryption Type must be None or CTE (broadcast not supported)
            - Simulcrypt Mode must be None or Enabled
            
         RPC Session
            - All service mappings on output are controlled by external manager
              using the RPC protocol.  
            - Only valid when Encryption Type is set to CTE or None
            - Only valid when Simulcrypt Mode is set to None (2.0)
            - PID Remapping mode should be Enabled (Without Reuse)

         Operating mode changes can only occur when the output is not in use
         (no service, PID, or stream mapping active to the output).
         
         @Commit(param=apexOutputTsConfBlade3ApplyChange, value=2)
        "
::= { apexOutputTsConfigBlade3Entry 3 }

apexOutputTsConfBlade3OutPatTsId OBJECT-TYPE
    SYNTAX Integer32(0..65535)
    MAX-ACCESS read-write
    STATUS current
    DESCRIPTION
        "Output Transport Stream ID to use for the output PAT in this Output
         Transport Stream. Changes to the output PAT TS ID can be made at any
         time and will cause the output PAT to automatically be updated to
         reflect the new TS ID setting.
         
         @Commit(param=apexOutputTsConfBlade3ApplyChange, value=2)
        "
::= { apexOutputTsConfigBlade3Entry 4 }

apexOutputTsConfBlade3EncryptionType OBJECT-TYPE
    SYNTAX INTEGER
        {
         noEncryption             (0),
         cte                      (1)
        }
    MAX-ACCESS read-write
    STATUS current
    DESCRIPTION
        "This parameter is used to set the encryption type of the output.

         'noEncryption'
            - All services are output in the clear

         'cte'
            - Services on output use Common Tier Encryption. CTE parameters
              determine encryption mode, copy protection, and tiers. All services
              in CTE mode use the exact same configuration settings.
            - Valid for all operating modes.
            - Simulcrypt Mode must be set to None.

         @Commit(param=apexOutputTsConfBlade3ApplyChange, value=2)
        "
::= { apexOutputTsConfigBlade3Entry 5 }

apexOutputTsConfBlade3SimulcryptMode OBJECT-TYPE
    SYNTAX INTEGER
        {
         none             (0),
         enabledEmms      (1),
         enabledNoEmms    (2)
        }
    MAX-ACCESS read-write
    STATUS current
    DESCRIPTION
        "This parameter is used to set the Simulcrypt mode of the output. Changes to this
         parameter can only be done when there are no programs mapped to the output. All
         programs must be disabled on an output before this parameter can be changed.

         'none' 
            - Used for normal Mediacypher only encryption (CTE or session Encryption). 

         'enabledEmms'
            - Enabled with EMMs insertion.
            - Used to indicate an external or internal EIS will control the encryption of  
              all services on the output.
            - Only valid when:
               - Encryption Type is set to 'noEncryption'
               - Operating Mode is set to 'manualRouting' or 'udpMapping' (2.0)
               - Encryption Algorithm is set to 'dvb-csa'
               
         'enabledNoEmms'
            - Enabled without EMMs insertion.
            - Used to indicate an external or internal EIS will control the encryption of  
              all services on the output.
            - Only valid when:
               - Encryption Type is set to 'noEncryption'
               - Operating Mode is set to 'manualRouting' or 'udpMapping' (2.0)
               - Encryption Algorithm is set to 'dvb-csa'
   
         @Commit(param=apexOutputTsConfBlade3ApplyChange, value=2)
        "
::= { apexOutputTsConfigBlade3Entry 6 }

apexOutputTsConfBlade3DepiRemoteId OBJECT-TYPE
    SYNTAX Integer32(0..65535)
    MAX-ACCESS read-write
    STATUS current
    DESCRIPTION
        "Unique identifier within the systems. Allows communication with the CMTS-core 
         to establish the DEPI control plane.
         
         @Commit(param=apexOutputTsConfBlade3ApplyChange, value=2)
        "
::= { apexOutputTsConfigBlade3Entry 7 }

apexOutputTsConfBlade3QamReplicationRfPort OBJECT-TYPE
    SYNTAX MasterRfPortTYPE
    MAX-ACCESS read-write
    STATUS current
    DESCRIPTION
        "RF Port when operating mode set to QAM Replication. Must be set to None
         when operating mode is not set to QAM Replication. 
         
         The Master RF Port from which this slave port is to be replicated.
         
         Selection restricted as follows:
         
                                 Slave
                         ---------------------
            Master       RF1   RF2   RF3   RF4
            ------       ---   ---   ---   ---
            none          Y     Y     Y     Y
            port1         N     Y     Y     Y
            port2         N     N     Y     Y
            port3         N     N     N     Y
        
         @Commit(param=apexOutputTsConfBlade3ApplyChange, value=2)
        "
::= { apexOutputTsConfigBlade3Entry 8 }


-- ------------------------------------------------------------------------------
--
-- apexOutputTsConfigBlade4
--
-- apexOutputTsConfBlade4ApplyTable
--

apexOutputTsConfBlade4ApplyTable OBJECT-TYPE
    SYNTAX SEQUENCE OF ApexOutputTsConfBlade4ApplyEntry
    MAX-ACCESS not-accessible
    STATUS current
    DESCRIPTION
        "Table of Apply Change for Output Ts Config Table.
        
         This apply is only used for apexOutputTsConfBlade4OperatingMode, 
         apexOutputTsConfBlade4OutPatTsId, and 
         apexOutputTsConfBlade4EncryptionType."
::= { apexOutputTsConfigBlade4 1 }

apexOutputTsConfBlade4ApplyEntry OBJECT-TYPE
    SYNTAX ApexOutputTsConfBlade4ApplyEntry
    MAX-ACCESS not-accessible
    STATUS current
    DESCRIPTION
        "Output Transport Stream Apply Table Entry."
    INDEX { apexOutputTsConfBlade4ApplyIndex }
::= { apexOutputTsConfBlade4ApplyTable 1 }

ApexOutputTsConfBlade4ApplyEntry ::= SEQUENCE
    {
     apexOutputTsConfBlade4ApplyIndex           Integer32,
     apexOutputTsConfBlade4ApplyChange          ApplyDataToDeviceTYPE
    }
    
apexOutputTsConfBlade4ApplyIndex OBJECT-TYPE
    SYNTAX Integer32(1..256)
    MAX-ACCESS not-accessible
    STATUS current
    DESCRIPTION
        "Index of Output Transport Stream Apply Table."
::= { apexOutputTsConfBlade4ApplyEntry 1 }

apexOutputTsConfBlade4ApplyChange OBJECT-TYPE
    SYNTAX ApplyDataToDeviceTYPE
    MAX-ACCESS read-write
    STATUS current
    DESCRIPTION
        "The apply for Output Ts Config Table.  This apply is only used for:
           apexOutputTsConfBlade4OperatingMode
           apexOutputTsConfBlade4OutPatTsId
           apexOutputTsConfBlade4EncryptionType
           apexOutputTsConfBlade4SimulcryptMode
           apexOutputTsConfBlade4DepiRemoteId
           apexOutputTsConfBlade4QamReplicationRfPort
         
         A row in this table corresponds to the same row index in the
         Output Ts Config table.

         This parameter MUST be set to 'apply' in order for the items listed
         above to take effect in the APEX.  This parameter MUST be set LAST 
         after the relevant data in the Output Ts Config row has been configured.

         @Config(config=no, reboot=no)
        "
::= { apexOutputTsConfBlade4ApplyEntry 2 }     


-- ------------------------------------------------------------------------------
--
-- apexOutputTsConfigBlade4Table
--

apexOutputTsConfigBlade4Table OBJECT-TYPE
    SYNTAX SEQUENCE OF ApexOutputTsConfigBlade4Entry
    MAX-ACCESS not-accessible
    STATUS current
    DESCRIPTION
        "This is a table of configuration parameters for Output Transport
         Streams.

         Once written, a change to the following parameters will only take 
         effect after the appropriate apexOutputTsConfBlade1ApplyChange
         is set to 'apply':  
           apexOutputTsConfBlade4OperatingMode
           apexOutputTsConfBlade4OutPatTsId
           apexOutputTsConfBlade4EncryptionType
           apexOutputTsConfBlade4SimulcryptMode
           apexOutputTsConfBlade4DepiRemoteId
           apexOutputTsConfBlade4QamReplicationRfPort
         
         All other changes to this table will take immediate effect.
         In order for the change to persist through subsequent reboots or power
         cycles, the change must be saved via the apexSaveConfig parameter.

         @Config(config=yes, reboot=no)
         @Save(apexSaveConfig, value=2)
         @File(config.ini, type='ini')
        "
::= { apexOutputTsConfigBlade4 2 }

apexOutputTsConfigBlade4Entry OBJECT-TYPE
    SYNTAX ApexOutputTsConfigBlade4Entry
    MAX-ACCESS not-accessible
    STATUS current
    DESCRIPTION
        "Output Transport Stream Configuration Table Entry."
    INDEX { apexOutputTsConfBlade4OutputTsNum }
::= { apexOutputTsConfigBlade4Table 1 }

ApexOutputTsConfigBlade4Entry ::= SEQUENCE
    {
     apexOutputTsConfBlade4OutputTsNum          Integer32,
     apexOutputTsConfBlade4PidRemappingMode     INTEGER,
     apexOutputTsConfBlade4OperatingMode        INTEGER,
     apexOutputTsConfBlade4OutPatTsId           Integer32,
     apexOutputTsConfBlade4EncryptionType       INTEGER,
     apexOutputTsConfBlade4SimulcryptMode       INTEGER,
     apexOutputTsConfBlade4DepiRemoteId         Integer32,
     apexOutputTsConfBlade4QamReplicationRfPort MasterRfPortTYPE
    }

apexOutputTsConfBlade4OutputTsNum OBJECT-TYPE
    SYNTAX Integer32(1..256)
    MAX-ACCESS not-accessible
    STATUS current
    DESCRIPTION
        "Output Transport Stream Number."
::= { apexOutputTsConfigBlade4Entry 1 }

apexOutputTsConfBlade4PidRemappingMode OBJECT-TYPE
    SYNTAX INTEGER
        {
         disabled           (1),
         remapWithoutReuse  (2),
         remapProgramBased  (3),
         remapProgramBased2 (4)
        }
    MAX-ACCESS read-write
    STATUS current
    DESCRIPTION
        "The PID Remapping mode setting.

         When 'disabled', the output PIDs for all services and ancillary PIDs
         are the same as the input PID values. PID collisions can occur when 
         multiple inputs are mapped to the same output. User is responsible for
         ensuring PIDs mapped from multiple input streams are unique.

         When 'remapWithoutReuse', the APEX will determine the output PIDs
         from a predetermined range of PIDs for services and ancillary PIDs.
         The APEX will use a scheme to limit the reuse of service PIDs for each
         service mapping. UDP Port Mapping and Session Control outputs should 
         always have PID Remapping enabled (set to 'remapWithoutReuse').

         When 'remapProgramBased' or 'remapProgramBased2', the APEX will determine 
         the output PIDs from a predetermined range of PIDs for services and 
         ancillary PIDs. The APEX uses a scheme to select the PMT PID based on 
         the program number. The PMT PID is calculated as follows for each mode:
            remapProgramBased =  (Program Number + 1) * 16
            remapProgramBased2 = (Program Number * 16) + 2
         
         The component PIDs are sequential after the PMT PID. This scheme only
         allows for a total of 15 component PIDs per program. Output program
         numbers are also limited (1-255). This scheme is intended to be used
         when in UDP Port Mapping mode at specific sites.

         PID Remapping mode changes can only occur when the output is not in use
         (no service, PID, or stream mapping active to the output).
        "
::= { apexOutputTsConfigBlade4Entry 2 }

apexOutputTsConfBlade4OperatingMode OBJECT-TYPE
    SYNTAX INTEGER
        {
         notInUse       (0),
         rtspSession    (1),
         manualRouting  (2),
         udpMapping     (3),
         rpcSession     (4),
         depi           (5),
         qamReplication (6)
        }
    MAX-ACCESS read-write
    STATUS current
    DESCRIPTION
        "This parameter is used to set the operating mode of the output.

         Operating mode changes can only occur when the output is not in use
         (no service, PID, or stream mapping active to the output).
         RTSP Session
            - User must select either RTSP-R6/D6 or MHA-ERMI to communicate with external
              resource manager. All service mappings on output are controlled
              by the external manager.
            - Only valid when Encryption Type is set to CTE or None
            - Only valid when Simulcrypt Mode is set to None (2.0)
            - PID Remapping mode should be Enabled (Without Reuse)
            
         Manual Routing
            - User manually maps each service
            - Encryption Type can be any valid setting (none, CTE, or Broadcast)
            - Simulcrypt Mode must be None or Enabled
            
         UDP Port Mapping
            - Standard UDP Port Mapping for use with VOD servers. Uses specific
              algorithm based on UDP Port to determine output program mappings.
            - Encryption Type must be None or CTE (broadcast not supported)
            - Simulcrypt Mode must be None or Enabled
            
         RPC Session
            - All service mappings on output are controlled by external manager
              using the RPC protocol.  
            - Only valid when Encryption Type is set to CTE or None
            - Only valid when Simulcrypt Mode is set to None (2.0)
            - PID Remapping mode should be Enabled (Without Reuse)

         Operating mode changes can only occur when the output is not in use
         (no service, PID, or stream mapping active to the output).
         
         @Commit(param=apexOutputTsConfBlade4ApplyChange, value=2)
        "
::= { apexOutputTsConfigBlade4Entry 3 }

apexOutputTsConfBlade4OutPatTsId OBJECT-TYPE
    SYNTAX Integer32(0..65535)
    MAX-ACCESS read-write
    STATUS current
    DESCRIPTION
        "Output Transport Stream ID to use for the output PAT in this Output
         Transport Stream. Changes to the output PAT TS ID can be made at any
         time and will cause the output PAT to automatically be updated to
         reflect the new TS ID setting.
         
         @Commit(param=apexOutputTsConfBlade4ApplyChange, value=2)
        "
::= { apexOutputTsConfigBlade4Entry 4 }

apexOutputTsConfBlade4EncryptionType OBJECT-TYPE
    SYNTAX INTEGER
        {
         noEncryption             (0),
         cte                      (1)
        }
    MAX-ACCESS read-write
    STATUS current
    DESCRIPTION
        "This parameter is used to set the encryption type of the output.

         'noEncryption'
            - All services are output in the clear

         'cte'
            - Services on output use Common Tier Encryption. CTE parameters
              determine encryption mode, copy protection, and tiers. All services
              in CTE mode use the exact same configuration settings.
            - Valid for all operating modes.
            - Simulcrypt Mode must be set to None.

         @Commit(param=apexOutputTsConfBlade4ApplyChange, value=2)
        "
::= { apexOutputTsConfigBlade4Entry 5 }

apexOutputTsConfBlade4SimulcryptMode OBJECT-TYPE
    SYNTAX INTEGER
        {
         none             (0),
         enabledEmms      (1),
         enabledNoEmms    (2)
        }
    MAX-ACCESS read-write
    STATUS current
    DESCRIPTION
        "This parameter is used to set the Simulcrypt mode of the output. Changes to this
         parameter can only be done when there are no programs mapped to the output. All
         programs must be disabled on an output before this parameter can be changed.

         'none' 
            - Used for normal Mediacypher only encryption (CTE or session Encryption). 

         'enabledEmms'
            - Enabled with EMMs insertion.
            - Used to indicate an external or internal EIS will control the encryption of  
              all services on the output.
            - Only valid when:
               - Encryption Type is set to 'noEncryption'
               - Operating Mode is set to 'manualRouting' or 'udpMapping' (2.0)
               - Encryption Algorithm is set to 'dvb-csa'
               
         'enabledNoEmms'
            - Enabled without EMMs insertion.
            - Used to indicate an external or internal EIS will control the encryption of  
              all services on the output.
            - Only valid when:
               - Encryption Type is set to 'noEncryption'
               - Operating Mode is set to 'manualRouting' or 'udpMapping' (2.0)
               - Encryption Algorithm is set to 'dvb-csa'
   
         @Commit(param=apexOutputTsConfBlade4ApplyChange, value=2)
        "
::= { apexOutputTsConfigBlade4Entry 6 }

apexOutputTsConfBlade4DepiRemoteId OBJECT-TYPE
    SYNTAX Integer32(0..65535)
    MAX-ACCESS read-write
    STATUS current
    DESCRIPTION
        "Unique identifier within the systems. Allows communication with the CMTS-core 
         to establish the DEPI control plane.
         
         @Commit(param=apexOutputTsConfBlade4ApplyChange, value=2)
        "
::= { apexOutputTsConfigBlade4Entry 7 }

apexOutputTsConfBlade4QamReplicationRfPort OBJECT-TYPE
    SYNTAX MasterRfPortTYPE
    MAX-ACCESS read-write
    STATUS current
    DESCRIPTION
        "RF Port when operating mode set to QAM Replication. Must be set to None
         when operating mode is not set to QAM Replication. 
         
         The Master RF Port from which this slave port is to be replicated.
         
         Selection restricted as follows:
         
                                 Slave
                         ---------------------
            Master       RF1   RF2   RF3   RF4
            ------       ---   ---   ---   ---
            none          Y     Y     Y     Y
            port1         N     Y     Y     Y
            port2         N     N     Y     Y
            port3         N     N     N     Y
        
         @Commit(param=apexOutputTsConfBlade4ApplyChange, value=2)
        "
::= { apexOutputTsConfigBlade4Entry 8 }


-- ------------------------------------------------------------------------------
--
-- apexOutputTsConfigBlade5
--
-- apexOutputTsConfBlade5ApplyTable
--

apexOutputTsConfBlade5ApplyTable OBJECT-TYPE
    SYNTAX SEQUENCE OF ApexOutputTsConfBlade5ApplyEntry
    MAX-ACCESS not-accessible
    STATUS current
    DESCRIPTION
        "Table of Apply Change for Output Ts Config Table.
        
         This apply is only used for apexOutputTsConfBlade5OperatingMode, 
         apexOutputTsConfBlade5OutPatTsId, and 
         apexOutputTsConfBlade5EncryptionType."
::= { apexOutputTsConfigBlade5 1 }

apexOutputTsConfBlade5ApplyEntry OBJECT-TYPE
    SYNTAX ApexOutputTsConfBlade5ApplyEntry
    MAX-ACCESS not-accessible
    STATUS current
    DESCRIPTION
        "Output Transport Stream Apply Table Entry."
    INDEX { apexOutputTsConfBlade5ApplyIndex }
::= { apexOutputTsConfBlade5ApplyTable 1 }

ApexOutputTsConfBlade5ApplyEntry ::= SEQUENCE
    {
     apexOutputTsConfBlade5ApplyIndex           Integer32,
     apexOutputTsConfBlade5ApplyChange          ApplyDataToDeviceTYPE
    }
    
apexOutputTsConfBlade5ApplyIndex OBJECT-TYPE
    SYNTAX Integer32(1..256)
    MAX-ACCESS not-accessible
    STATUS current
    DESCRIPTION
        "Index of Output Transport Stream Apply Table."
::= { apexOutputTsConfBlade5ApplyEntry 1 }

apexOutputTsConfBlade5ApplyChange OBJECT-TYPE
    SYNTAX ApplyDataToDeviceTYPE
    MAX-ACCESS read-write
    STATUS current
    DESCRIPTION
        "The apply for Output Ts Config Table.  This apply is only used for:
           apexOutputTsConfBlade5OperatingMode
           apexOutputTsConfBlade5OutPatTsId
           apexOutputTsConfBlade5EncryptionType
           apexOutputTsConfBlade5SimulcryptMode
           apexOutputTsConfBlade5DepiRemoteId
           apexOutputTsConfBlade5QamReplicationRfPort

         A row in this table corresponds to the same row index in the
         Output Ts Config table.

         This parameter MUST be set to 'apply' in order for the items listed
         above to take effect in the APEX.  This parameter MUST be set LAST 
         after the relevant data in the Output Ts Config row has been configured.

         @Config(config=no, reboot=no)
        "
::= { apexOutputTsConfBlade5ApplyEntry 2 }     


-- ------------------------------------------------------------------------------
--
-- apexOutputTsConfigBlade5Table
--

apexOutputTsConfigBlade5Table OBJECT-TYPE
    SYNTAX SEQUENCE OF ApexOutputTsConfigBlade5Entry
    MAX-ACCESS not-accessible
    STATUS current
    DESCRIPTION
        "This is a table of configuration parameters for Output Transport
         Streams.

         Once written, a change to the following parameters will only take 
         effect after the appropriate apexOutputTsConfBlade1ApplyChange
         is set to 'apply':  
           apexOutputTsConfBlade5OperatingMode
           apexOutputTsConfBlade5OutPatTsId
           apexOutputTsConfBlade5EncryptionType
           apexOutputTsConfBlade5SimulcryptMode
           apexOutputTsConfBlade5DepiRemoteId
           apexOutputTsConfBlade5QamReplicationRfPort
         
         All other changes to this table will take immediate effect.
         In order for the change to persist through subsequent reboots or power
         cycles, the change must be saved via the apexSaveConfig parameter.

         @Config(config=yes, reboot=no)
         @Save(apexSaveConfig, value=2)
         @File(config.ini, type='ini')
        "
::= { apexOutputTsConfigBlade5 2 }

apexOutputTsConfigBlade5Entry OBJECT-TYPE
    SYNTAX ApexOutputTsConfigBlade5Entry
    MAX-ACCESS not-accessible
    STATUS current
    DESCRIPTION
        "Output Transport Stream Configuration Table Entry."
    INDEX { apexOutputTsConfBlade5OutputTsNum }
::= { apexOutputTsConfigBlade5Table 1 }

ApexOutputTsConfigBlade5Entry ::= SEQUENCE
    {
     apexOutputTsConfBlade5OutputTsNum          Integer32,
     apexOutputTsConfBlade5PidRemappingMode     INTEGER,
     apexOutputTsConfBlade5OperatingMode        INTEGER,
     apexOutputTsConfBlade5OutPatTsId           Integer32,
     apexOutputTsConfBlade5EncryptionType       INTEGER,
     apexOutputTsConfBlade5SimulcryptMode       INTEGER,
     apexOutputTsConfBlade5DepiRemoteId         Integer32,
     apexOutputTsConfBlade5QamReplicationRfPort MasterRfPortTYPE
    }

apexOutputTsConfBlade5OutputTsNum OBJECT-TYPE
    SYNTAX Integer32(1..256)
    MAX-ACCESS not-accessible
    STATUS current
    DESCRIPTION
        "Output Transport Stream Number."
::= { apexOutputTsConfigBlade5Entry 1 }

apexOutputTsConfBlade5PidRemappingMode OBJECT-TYPE
    SYNTAX INTEGER
        {
         disabled           (1),
         remapWithoutReuse  (2),
         remapProgramBased  (3),
         remapProgramBased2 (4)
        }
    MAX-ACCESS read-write
    STATUS current
    DESCRIPTION
        "The PID Remapping mode setting.

         When 'disabled', the output PIDs for all services and ancillary PIDs
         are the same as the input PID values. PID collisions can occur when 
         multiple inputs are mapped to the same output. User is responsible for
         ensuring PIDs mapped from multiple input streams are unique.

         When 'remapWithoutReuse', the APEX will determine the output PIDs
         from a predetermined range of PIDs for services and ancillary PIDs.
         The APEX will use a scheme to limit the reuse of service PIDs for each
         service mapping. UDP Port Mapping and Session Control outputs should 
         always have PID Remapping enabled (set to 'remapWithoutReuse').

         When 'remapProgramBased' or 'remapProgramBased2', the APEX will determine 
         the output PIDs from a predetermined range of PIDs for services and 
         ancillary PIDs. The APEX uses a scheme to select the PMT PID based on 
         the program number. The PMT PID is calculated as follows for each mode:
            remapProgramBased =  (Program Number + 1) * 16
            remapProgramBased2 = (Program Number * 16) + 2
         
         The component PIDs are sequential after the PMT PID. This scheme only
         allows for a total of 15 component PIDs per program. Output program
         numbers are also limited (1-255). This scheme is intended to be used
         when in UDP Port Mapping mode at specific sites.

         PID Remapping mode changes can only occur when the output is not in use
         (no service, PID, or stream mapping active to the output).
        "
::= { apexOutputTsConfigBlade5Entry 2 }

apexOutputTsConfBlade5OperatingMode OBJECT-TYPE
    SYNTAX INTEGER
        {
         notInUse       (0),
         rtspSession    (1),
         manualRouting  (2),
         udpMapping     (3),
         rpcSession     (4),
         depi           (5),
         qamReplication (6)
        }
    MAX-ACCESS read-write
    STATUS current
    DESCRIPTION
        "This parameter is used to set the operating mode of the output.

         Operating mode changes can only occur when the output is not in use
         (no service, PID, or stream mapping active to the output).
         RTSP Session
            - User must select either RTSP-R6/D6 or MHA-ERMI to communicate with external
              resource manager. All service mappings on output are controlled
              by the external manager.
            - Only valid when Encryption Type is set to CTE or None
            - Only valid when Simulcrypt Mode is set to None (2.0)
            - PID Remapping mode should be Enabled (Without Reuse)
            
         Manual Routing
            - User manually maps each service
            - Encryption Type can be any valid setting (none, CTE, or Broadcast)
            - Simulcrypt Mode must be None or Enabled
            
         UDP Port Mapping
            - Standard UDP Port Mapping for use with VOD servers. Uses specific
              algorithm based on UDP Port to determine output program mappings.
            - Encryption Type must be None or CTE (broadcast not supported)
            - Simulcrypt Mode must be None or Enabled
            
         RPC Session
            - All service mappings on output are controlled by external manager
              using the RPC protocol.  
            - Only valid when Encryption Type is set to CTE or None
            - Only valid when Simulcrypt Mode is set to None (2.0)
            - PID Remapping mode should be Enabled (Without Reuse)

         Operating mode changes can only occur when the output is not in use
         (no service, PID, or stream mapping active to the output).
         
         @Commit(param=apexOutputTsConfBlade5ApplyChange, value=2)
        "
::= { apexOutputTsConfigBlade5Entry 3 }

apexOutputTsConfBlade5OutPatTsId OBJECT-TYPE
    SYNTAX Integer32(0..65535)
    MAX-ACCESS read-write
    STATUS current
    DESCRIPTION
        "Output Transport Stream ID to use for the output PAT in this Output
         Transport Stream. Changes to the output PAT TS ID can be made at any
         time and will cause the output PAT to automatically be updated to
         reflect the new TS ID setting.
         
         @Commit(param=apexOutputTsConfBlade5ApplyChange, value=2)
        "
::= { apexOutputTsConfigBlade5Entry 4 }

apexOutputTsConfBlade5EncryptionType OBJECT-TYPE
    SYNTAX INTEGER
        {
         noEncryption             (0),
         cte                      (1)
        }
    MAX-ACCESS read-write
    STATUS current
    DESCRIPTION
        "This parameter is used to set the encryption type of the output.

         'noEncryption'
            - All services are output in the clear

         'cte'
            - Services on output use Common Tier Encryption. CTE parameters
              determine encryption mode, copy protection, and tiers. All services
              in CTE mode use the exact same configuration settings.
            - Valid for all operating modes.
            - Simulcrypt Mode must be set to None.

         @Commit(param=apexOutputTsConfBlade5ApplyChange, value=2)
        "
::= { apexOutputTsConfigBlade5Entry 5 }

apexOutputTsConfBlade5SimulcryptMode OBJECT-TYPE
    SYNTAX INTEGER
        {
         none             (0),
         enabledEmms      (1),
         enabledNoEmms    (2)
        }
    MAX-ACCESS read-write
    STATUS current
    DESCRIPTION
        "This parameter is used to set the Simulcrypt mode of the output. Changes to this
         parameter can only be done when there are no programs mapped to the output. All
         programs must be disabled on an output before this parameter can be changed.

         'none' 
            - Used for normal Mediacypher only encryption (CTE or session Encryption). 

         'enabledEmms'
            - Enabled with EMMs insertion.
            - Used to indicate an external or internal EIS will control the encryption of  
              all services on the output.
            - Only valid when:
               - Encryption Type is set to 'noEncryption'
               - Operating Mode is set to 'manualRouting' or 'udpMapping' (2.0)
               - Encryption Algorithm is set to 'dvb-csa'
               
         'enabledNoEmms'
            - Enabled without EMMs insertion.
            - Used to indicate an external or internal EIS will control the encryption of  
              all services on the output.
            - Only valid when:
               - Encryption Type is set to 'noEncryption'
               - Operating Mode is set to 'manualRouting' or 'udpMapping' (2.0)
               - Encryption Algorithm is set to 'dvb-csa'
   
         @Commit(param=apexOutputTsConfBlade5ApplyChange, value=2)
        "
::= { apexOutputTsConfigBlade5Entry 6 }

apexOutputTsConfBlade5DepiRemoteId OBJECT-TYPE
    SYNTAX Integer32(0..65535)
    MAX-ACCESS read-write
    STATUS current
    DESCRIPTION
        "Unique identifier within the systems. Allows communication with the CMTS-core 
         to establish the DEPI control plane.
         
         @Commit(param=apexOutputTsConfBlade5ApplyChange, value=2)
        "
::= { apexOutputTsConfigBlade5Entry 7 }

apexOutputTsConfBlade5QamReplicationRfPort OBJECT-TYPE
    SYNTAX MasterRfPortTYPE
    MAX-ACCESS read-write
    STATUS current
    DESCRIPTION
        "RF Port when operating mode set to QAM Replication. Must be set to None
         when operating mode is not set to QAM Replication. 
         
         The Master RF Port from which this slave port is to be replicated.
         
         Selection restricted as follows:
         
                                 Slave
                         ---------------------
            Master       RF1   RF2   RF3   RF4
            ------       ---   ---   ---   ---
            none          Y     Y     Y     Y
            port1         N     Y     Y     Y
            port2         N     N     Y     Y
            port3         N     N     N     Y
        
         @Commit(param=apexOutputTsConfBlade5ApplyChange, value=2)
        "
::= { apexOutputTsConfigBlade5Entry 8 }


-- ------------------------------------------------------------------------------
--
-- apexOutputTsConfigBlade6
--
-- apexOutputTsConfBlade6ApplyTable
--

apexOutputTsConfBlade6ApplyTable OBJECT-TYPE
    SYNTAX SEQUENCE OF ApexOutputTsConfBlade6ApplyEntry
    MAX-ACCESS not-accessible
    STATUS current
    DESCRIPTION
        "Table of Apply Change for Output Ts Config Table.
        
         This apply is only used for apexOutputTsConfBlade6OperatingMode, 
         apexOutputTsConfBlade6OutPatTsId, and 
         apexOutputTsConfBlade6EncryptionType."
::= { apexOutputTsConfigBlade6 1 }

apexOutputTsConfBlade6ApplyEntry OBJECT-TYPE
    SYNTAX ApexOutputTsConfBlade6ApplyEntry
    MAX-ACCESS not-accessible
    STATUS current
    DESCRIPTION
        "Output Transport Stream Apply Table Entry."
    INDEX { apexOutputTsConfBlade6ApplyIndex }
::= { apexOutputTsConfBlade6ApplyTable 1 }

ApexOutputTsConfBlade6ApplyEntry ::= SEQUENCE
    {
     apexOutputTsConfBlade6ApplyIndex           Integer32,
     apexOutputTsConfBlade6ApplyChange          ApplyDataToDeviceTYPE
    }
    
apexOutputTsConfBlade6ApplyIndex OBJECT-TYPE
    SYNTAX Integer32(1..256)
    MAX-ACCESS not-accessible
    STATUS current
    DESCRIPTION
        "Index of Output Transport Stream Apply Table."
::= { apexOutputTsConfBlade6ApplyEntry 1 }

apexOutputTsConfBlade6ApplyChange OBJECT-TYPE
    SYNTAX ApplyDataToDeviceTYPE
    MAX-ACCESS read-write
    STATUS current
    DESCRIPTION
        "The apply for Output Ts Config Table.  This apply is only used for:
           apexOutputTsConfBlade6OperatingMode
           apexOutputTsConfBlade6OutPatTsId
           apexOutputTsConfBlade6EncryptionType
           apexOutputTsConfBlade6SimulcryptMode
           apexOutputTsConfBlade6DepiRemoteId
           apexOutputTsConfBlade6QamReplicationRfPort
         
         A row in this table corresponds to the same row index in the
         Output Ts Config table.

         This parameter MUST be set to 'apply' in order for the items listed
         above to take effect in the APEX.  This parameter MUST be set LAST 
         after the relevant data in the Output Ts Config row has been configured.

         @Config(config=no, reboot=no)
        "
::= { apexOutputTsConfBlade6ApplyEntry 2 }     


-- ------------------------------------------------------------------------------
--
-- apexOutputTsConfigBlade6Table
--

apexOutputTsConfigBlade6Table OBJECT-TYPE
    SYNTAX SEQUENCE OF ApexOutputTsConfigBlade6Entry
    MAX-ACCESS not-accessible
    STATUS current
    DESCRIPTION
        "This is a table of configuration parameters for Output Transport
         Streams.

         Once written, a change to the following parameters will only take 
         effect after the appropriate apexOutputTsConfBlade1ApplyChange
         is set to 'apply':  
           apexOutputTsConfBlade6OperatingMode
           apexOutputTsConfBlade6OutPatTsId
           apexOutputTsConfBlade6EncryptionType
           apexOutputTsConfBlade6SimulcryptMode
           apexOutputTsConfBlade6DepiRemoteId
           apexOutputTsConfBlade6QamReplicationRfPort
         
         All other changes to this table will take immediate effect.
         In order for the change to persist through subsequent reboots or power
         cycles, the change must be saved via the apexSaveConfig parameter.

         @Config(config=yes, reboot=no)
         @Save(apexSaveConfig, value=2)
         @File(config.ini, type='ini')
        "
::= { apexOutputTsConfigBlade6 2 }

apexOutputTsConfigBlade6Entry OBJECT-TYPE
    SYNTAX ApexOutputTsConfigBlade6Entry
    MAX-ACCESS not-accessible
    STATUS current
    DESCRIPTION
        "Output Transport Stream Configuration Table Entry."
    INDEX { apexOutputTsConfBlade6OutputTsNum }
::= { apexOutputTsConfigBlade6Table 1 }

ApexOutputTsConfigBlade6Entry ::= SEQUENCE
    {
     apexOutputTsConfBlade6OutputTsNum          Integer32,
     apexOutputTsConfBlade6PidRemappingMode     INTEGER,
     apexOutputTsConfBlade6OperatingMode        INTEGER,
     apexOutputTsConfBlade6OutPatTsId           Integer32,
     apexOutputTsConfBlade6EncryptionType       INTEGER,
     apexOutputTsConfBlade6SimulcryptMode       INTEGER,
     apexOutputTsConfBlade6DepiRemoteId         Integer32,
     apexOutputTsConfBlade6QamReplicationRfPort MasterRfPortTYPE
    }

apexOutputTsConfBlade6OutputTsNum OBJECT-TYPE
    SYNTAX Integer32(1..256)
    MAX-ACCESS not-accessible
    STATUS current
    DESCRIPTION
        "Output Transport Stream Number."
::= { apexOutputTsConfigBlade6Entry 1 }

apexOutputTsConfBlade6PidRemappingMode OBJECT-TYPE
    SYNTAX INTEGER
        {
         disabled           (1),
         remapWithoutReuse  (2),
         remapProgramBased  (3),
         remapProgramBased2 (4)
        }
    MAX-ACCESS read-write
    STATUS current
    DESCRIPTION
        "The PID Remapping mode setting.

         When 'disabled', the output PIDs for all services and ancillary PIDs
         are the same as the input PID values. PID collisions can occur when 
         multiple inputs are mapped to the same output. User is responsible for
         ensuring PIDs mapped from multiple input streams are unique.

         When 'remapWithoutReuse', the APEX will determine the output PIDs
         from a predetermined range of PIDs for services and ancillary PIDs.
         The APEX will use a scheme to limit the reuse of service PIDs for each
         service mapping. UDP Port Mapping and Session Control outputs should 
         always have PID Remapping enabled (set to 'remapWithoutReuse').

         When 'remapProgramBased' or 'remapProgramBased2', the APEX will determine 
         the output PIDs from a predetermined range of PIDs for services and 
         ancillary PIDs. The APEX uses a scheme to select the PMT PID based on 
         the program number. The PMT PID is calculated as follows for each mode:
            remapProgramBased =  (Program Number + 1) * 16
            remapProgramBased2 = (Program Number * 16) + 2
         
         The component PIDs are sequential after the PMT PID. This scheme only
         allows for a total of 15 component PIDs per program. Output program
         numbers are also limited (1-255). This scheme is intended to be used
         when in UDP Port Mapping mode at specific sites.

         PID Remapping mode changes can only occur when the output is not in use
         (no service, PID, or stream mapping active to the output).
        "
::= { apexOutputTsConfigBlade6Entry 2 }

apexOutputTsConfBlade6OperatingMode OBJECT-TYPE
    SYNTAX INTEGER
        {
         notInUse       (0),
         rtspSession    (1),
         manualRouting  (2),
         udpMapping     (3),
         rpcSession     (4),
         depi           (5),
         qamReplication (6)
        }
    MAX-ACCESS read-write
    STATUS current
    DESCRIPTION
        "This parameter is used to set the operating mode of the output.

         Operating mode changes can only occur when the output is not in use
         (no service, PID, or stream mapping active to the output).
         RTSP Session
            - User must select either RTSP-R6/D6 or MHA-ERMI to communicate with external
              resource manager. All service mappings on output are controlled
              by the external manager.
            - Only valid when Encryption Type is set to CTE or None
            - Only valid when Simulcrypt Mode is set to None (2.0)
            - PID Remapping mode should be Enabled (Without Reuse)
            
         Manual Routing
            - User manually maps each service
            - Encryption Type can be any valid setting (none, CTE, or Broadcast)
            - Simulcrypt Mode must be None or Enabled
            
         UDP Port Mapping
            - Standard UDP Port Mapping for use with VOD servers. Uses specific
              algorithm based on UDP Port to determine output program mappings.
            - Encryption Type must be None or CTE (broadcast not supported)
            - Simulcrypt Mode must be None or Enabled
            
         RPC Session
            - All service mappings on output are controlled by external manager
              using the RPC protocol.  
            - Only valid when Encryption Type is set to CTE or None
            - Only valid when Simulcrypt Mode is set to None (2.0)
            - PID Remapping mode should be Enabled (Without Reuse)

         Operating mode changes can only occur when the output is not in use
         (no service, PID, or stream mapping active to the output).
         
         @Commit(param=apexOutputTsConfBlade6ApplyChange, value=2)
        "
::= { apexOutputTsConfigBlade6Entry 3 }

apexOutputTsConfBlade6OutPatTsId OBJECT-TYPE
    SYNTAX Integer32(0..65535)
    MAX-ACCESS read-write
    STATUS current
    DESCRIPTION
        "Output Transport Stream ID to use for the output PAT in this Output
         Transport Stream. Changes to the output PAT TS ID can be made at any
         time and will cause the output PAT to automatically be updated to
         reflect the new TS ID setting.
         
         @Commit(param=apexOutputTsConfBlade6ApplyChange, value=2)
        "
::= { apexOutputTsConfigBlade6Entry 4 }

apexOutputTsConfBlade6EncryptionType OBJECT-TYPE
    SYNTAX INTEGER
        {
         noEncryption             (0),
         cte                      (1)
        }
    MAX-ACCESS read-write
    STATUS current
    DESCRIPTION
        "This parameter is used to set the encryption type of the output.

         'noEncryption'
            - All services are output in the clear

         'cte'
            - Services on output use Common Tier Encryption. CTE parameters
              determine encryption mode, copy protection, and tiers. All services
              in CTE mode use the exact same configuration settings.
            - Valid for all operating modes.
            - Simulcrypt Mode must be set to None.

         @Commit(param=apexOutputTsConfBlade6ApplyChange, value=2)
        "
::= { apexOutputTsConfigBlade6Entry 5 }

apexOutputTsConfBlade6SimulcryptMode OBJECT-TYPE
    SYNTAX INTEGER
        {
         none             (0),
         enabledEmms      (1),
         enabledNoEmms    (2)
        }
    MAX-ACCESS read-write
    STATUS current
    DESCRIPTION
        "This parameter is used to set the Simulcrypt mode of the output. Changes to this
         parameter can only be done when there are no programs mapped to the output. All
         programs must be disabled on an output before this parameter can be changed.

         'none' 
            - Used for normal Mediacypher only encryption (CTE or session Encryption). 

         'enabledEmms'
            - Enabled with EMMs insertion.
            - Used to indicate an external or internal EIS will control the encryption of  
              all services on the output.
            - Only valid when:
               - Encryption Type is set to 'noEncryption'
               - Operating Mode is set to 'manualRouting' or 'udpMapping' (2.0)
               - Encryption Algorithm is set to 'dvb-csa'
               
         'enabledNoEmms'
            - Enabled without EMMs insertion.
            - Used to indicate an external or internal EIS will control the encryption of  
              all services on the output.
            - Only valid when:
               - Encryption Type is set to 'noEncryption'
               - Operating Mode is set to 'manualRouting' or 'udpMapping' (2.0)
               - Encryption Algorithm is set to 'dvb-csa'
   
         @Commit(param=apexOutputTsConfBlade6ApplyChange, value=2)
        "
::= { apexOutputTsConfigBlade6Entry 6 }

apexOutputTsConfBlade6DepiRemoteId OBJECT-TYPE
    SYNTAX Integer32(0..65535)
    MAX-ACCESS read-write
    STATUS current
    DESCRIPTION
        "Unique identifier within the systems. Allows communication with the CMTS-core 
         to establish the DEPI control plane.
         
         @Commit(param=apexOutputTsConfBlade6ApplyChange, value=2)
        "
::= { apexOutputTsConfigBlade6Entry 7 }

apexOutputTsConfBlade6QamReplicationRfPort OBJECT-TYPE
    SYNTAX MasterRfPortTYPE
    MAX-ACCESS read-write
    STATUS current
    DESCRIPTION
        "RF Port when operating mode set to QAM Replication. Must be set to None
         when operating mode is not set to QAM Replication. 
         
         The Master RF Port from which this slave port is to be replicated.
         
         Selection restricted as follows:
         
                                 Slave
                         ---------------------
            Master       RF1   RF2   RF3   RF4
            ------       ---   ---   ---   ---
            none          Y     Y     Y     Y
            port1         N     Y     Y     Y
            port2         N     N     Y     Y
            port3         N     N     N     Y
        
         @Commit(param=apexOutputTsConfBlade6ApplyChange, value=2)
        "
::= { apexOutputTsConfigBlade6Entry 8 }


-- ------------------------------------------------------------------------------
--
-- apexOutputTsConfigBlade7
--
-- apexOutputTsConfBlade7ApplyTable
--

apexOutputTsConfBlade7ApplyTable OBJECT-TYPE
    SYNTAX SEQUENCE OF ApexOutputTsConfBlade7ApplyEntry
    MAX-ACCESS not-accessible
    STATUS current
    DESCRIPTION
        "Table of Apply Change for Output Ts Config Table.
        
         This apply is only used for apexOutputTsConfBlade7OperatingMode, 
         apexOutputTsConfBlade7OutPatTsId, and 
         apexOutputTsConfBlade7EncryptionType."
::= { apexOutputTsConfigBlade7 1 }

apexOutputTsConfBlade7ApplyEntry OBJECT-TYPE
    SYNTAX ApexOutputTsConfBlade7ApplyEntry
    MAX-ACCESS not-accessible
    STATUS current
    DESCRIPTION
        "Output Transport Stream Apply Table Entry."
    INDEX { apexOutputTsConfBlade7ApplyIndex }
::= { apexOutputTsConfBlade7ApplyTable 1 }

ApexOutputTsConfBlade7ApplyEntry ::= SEQUENCE
    {
     apexOutputTsConfBlade7ApplyIndex           Integer32,
     apexOutputTsConfBlade7ApplyChange          ApplyDataToDeviceTYPE
    }
    
apexOutputTsConfBlade7ApplyIndex OBJECT-TYPE
    SYNTAX Integer32(1..256)
    MAX-ACCESS not-accessible
    STATUS current
    DESCRIPTION
        "Index of Output Transport Stream Apply Table."
::= { apexOutputTsConfBlade7ApplyEntry 1 }

apexOutputTsConfBlade7ApplyChange OBJECT-TYPE
    SYNTAX ApplyDataToDeviceTYPE
    MAX-ACCESS read-write
    STATUS current
    DESCRIPTION
        "The apply for Output Ts Config Table.  This apply is only used for:
           apexOutputTsConfBlade7OperatingMode
           apexOutputTsConfBlade7OutPatTsId
           apexOutputTsConfBlade7EncryptionType
           apexOutputTsConfBlade7SimulcryptMode
           apexOutputTsConfBlade7DepiRemoteId
           apexOutputTsConfBlade7QamReplicationRfPort
         
         A row in this table corresponds to the same row index in the
         Output Ts Config table.

         This parameter MUST be set to 'apply' in order for the items listed
         above to take effect in the APEX.  This parameter MUST be set LAST 
         after the relevant data in the Output Ts Config row has been configured.

         @Config(config=no, reboot=no)
        "
::= { apexOutputTsConfBlade7ApplyEntry 2 }     


-- ------------------------------------------------------------------------------
--
-- apexOutputTsConfigBlade7Table
--

apexOutputTsConfigBlade7Table OBJECT-TYPE
    SYNTAX SEQUENCE OF ApexOutputTsConfigBlade7Entry
    MAX-ACCESS not-accessible
    STATUS current
    DESCRIPTION
        "This is a table of configuration parameters for Output Transport
         Streams.

         Once written, a change to the following parameters will only take 
         effect after the appropriate apexOutputTsConfBlade1ApplyChange
         is set to 'apply':  
           apexOutputTsConfBlade7OperatingMode
           apexOutputTsConfBlade7OutPatTsId
           apexOutputTsConfBlade7EncryptionType
           apexOutputTsConfBlade7SimulcryptMode
           apexOutputTsConfBlade7DepiRemoteId
           apexOutputTsConfBlade7QamReplicationRfPort
         
         All other changes to this table will take immediate effect.
         In order for the change to persist through subsequent reboots or power
         cycles, the change must be saved via the apexSaveConfig parameter.

         @Config(config=yes, reboot=no)
         @Save(apexSaveConfig, value=2)
         @File(config.ini, type='ini')
        "
::= { apexOutputTsConfigBlade7 2 }

apexOutputTsConfigBlade7Entry OBJECT-TYPE
    SYNTAX ApexOutputTsConfigBlade7Entry
    MAX-ACCESS not-accessible
    STATUS current
    DESCRIPTION
        "Output Transport Stream Configuration Table Entry."
    INDEX { apexOutputTsConfBlade7OutputTsNum }
::= { apexOutputTsConfigBlade7Table 1 }

ApexOutputTsConfigBlade7Entry ::= SEQUENCE
    {
     apexOutputTsConfBlade7OutputTsNum          Integer32,
     apexOutputTsConfBlade7PidRemappingMode     INTEGER,
     apexOutputTsConfBlade7OperatingMode        INTEGER,
     apexOutputTsConfBlade7OutPatTsId           Integer32,
     apexOutputTsConfBlade7EncryptionType       INTEGER,
     apexOutputTsConfBlade7SimulcryptMode       INTEGER,
     apexOutputTsConfBlade7DepiRemoteId         Integer32,
     apexOutputTsConfBlade7QamReplicationRfPort MasterRfPortTYPE
    }

apexOutputTsConfBlade7OutputTsNum OBJECT-TYPE
    SYNTAX Integer32(1..256)
    MAX-ACCESS not-accessible
    STATUS current
    DESCRIPTION
        "Output Transport Stream Number."
::= { apexOutputTsConfigBlade7Entry 1 }

apexOutputTsConfBlade7PidRemappingMode OBJECT-TYPE
    SYNTAX INTEGER
        {
         disabled           (1),
         remapWithoutReuse  (2),
         remapProgramBased  (3),
         remapProgramBased2 (4)
        }
    MAX-ACCESS read-write
    STATUS current
    DESCRIPTION
        "The PID Remapping mode setting.

         When 'disabled', the output PIDs for all services and ancillary PIDs
         are the same as the input PID values. PID collisions can occur when 
         multiple inputs are mapped to the same output. User is responsible for
         ensuring PIDs mapped from multiple input streams are unique.

         When 'remapWithoutReuse', the APEX will determine the output PIDs
         from a predetermined range of PIDs for services and ancillary PIDs.
         The APEX will use a scheme to limit the reuse of service PIDs for each
         service mapping. UDP Port Mapping and Session Control outputs should 
         always have PID Remapping enabled (set to 'remapWithoutReuse').

         When 'remapProgramBased' or 'remapProgramBased2', the APEX will determine 
         the output PIDs from a predetermined range of PIDs for services and 
         ancillary PIDs. The APEX uses a scheme to select the PMT PID based on 
         the program number. The PMT PID is calculated as follows for each mode:
            remapProgramBased =  (Program Number + 1) * 16
            remapProgramBased2 = (Program Number * 16) + 2
         
         The component PIDs are sequential after the PMT PID. This scheme only
         allows for a total of 15 component PIDs per program. Output program
         numbers are also limited (1-255). This scheme is intended to be used
         when in UDP Port Mapping mode at specific sites.

         PID Remapping mode changes can only occur when the output is not in use
         (no service, PID, or stream mapping active to the output).
        "
::= { apexOutputTsConfigBlade7Entry 2 }

apexOutputTsConfBlade7OperatingMode OBJECT-TYPE
    SYNTAX INTEGER
        {
         notInUse       (0),
         rtspSession    (1),
         manualRouting  (2),
         udpMapping     (3),
         rpcSession     (4),
         depi           (5),
         qamReplication (6)
        }
    MAX-ACCESS read-write
    STATUS current
    DESCRIPTION
        "This parameter is used to set the operating mode of the output.

         Operating mode changes can only occur when the output is not in use
         (no service, PID, or stream mapping active to the output).
         RTSP Session
            - User must select either RTSP-R6/D6 or MHA-ERMI to communicate with external
              resource manager. All service mappings on output are controlled
              by the external manager.
            - Only valid when Encryption Type is set to CTE or None
            - Only valid when Simulcrypt Mode is set to None (2.0)
            - PID Remapping mode should be Enabled (Without Reuse)
            
         Manual Routing
            - User manually maps each service
            - Encryption Type can be any valid setting (none, CTE, or Broadcast)
            - Simulcrypt Mode must be None or Enabled
            
         UDP Port Mapping
            - Standard UDP Port Mapping for use with VOD servers. Uses specific
              algorithm based on UDP Port to determine output program mappings.
            - Encryption Type must be None or CTE (broadcast not supported)
            - Simulcrypt Mode must be None or Enabled
            
         RPC Session
            - All service mappings on output are controlled by external manager
              using the RPC protocol.  
            - Only valid when Encryption Type is set to CTE or None
            - Only valid when Simulcrypt Mode is set to None (2.0)
            - PID Remapping mode should be Enabled (Without Reuse)

         Operating mode changes can only occur when the output is not in use
         (no service, PID, or stream mapping active to the output).
         
         @Commit(param=apexOutputTsConfBlade7ApplyChange, value=2)
        "
::= { apexOutputTsConfigBlade7Entry 3 }

apexOutputTsConfBlade7OutPatTsId OBJECT-TYPE
    SYNTAX Integer32(0..65535)
    MAX-ACCESS read-write
    STATUS current
    DESCRIPTION
        "Output Transport Stream ID to use for the output PAT in this Output
         Transport Stream. Changes to the output PAT TS ID can be made at any
         time and will cause the output PAT to automatically be updated to
         reflect the new TS ID setting.
         
         @Commit(param=apexOutputTsConfBlade7ApplyChange, value=2)
        "
::= { apexOutputTsConfigBlade7Entry 4 }

apexOutputTsConfBlade7EncryptionType OBJECT-TYPE
    SYNTAX INTEGER
        {
         noEncryption             (0),
         cte                      (1)
        }
    MAX-ACCESS read-write
    STATUS current
    DESCRIPTION
        "This parameter is used to set the encryption type of the output.

         'noEncryption'
            - All services are output in the clear

         'cte'
            - Services on output use Common Tier Encryption. CTE parameters
              determine encryption mode, copy protection, and tiers. All services
              in CTE mode use the exact same configuration settings.
            - Valid for all operating modes.
            - Simulcrypt Mode must be set to None.

         @Commit(param=apexOutputTsConfBlade7ApplyChange, value=2)
        "
::= { apexOutputTsConfigBlade7Entry 5 }

apexOutputTsConfBlade7SimulcryptMode OBJECT-TYPE
    SYNTAX INTEGER
        {
         none             (0),
         enabledEmms      (1),
         enabledNoEmms    (2)
        }
    MAX-ACCESS read-write
    STATUS current
    DESCRIPTION
        "This parameter is used to set the Simulcrypt mode of the output. Changes to this
         parameter can only be done when there are no programs mapped to the output. All
         programs must be disabled on an output before this parameter can be changed.

         'none' 
            - Used for normal Mediacypher only encryption (CTE or session Encryption). 

         'enabledEmms'
            - Enabled with EMMs insertion.
            - Used to indicate an external or internal EIS will control the encryption of  
              all services on the output.
            - Only valid when:
               - Encryption Type is set to 'noEncryption'
               - Operating Mode is set to 'manualRouting' or 'udpMapping' (2.0)
               - Encryption Algorithm is set to 'dvb-csa'
               
         'enabledNoEmms'
            - Enabled without EMMs insertion.
            - Used to indicate an external or internal EIS will control the encryption of  
              all services on the output.
            - Only valid when:
               - Encryption Type is set to 'noEncryption'
               - Operating Mode is set to 'manualRouting' or 'udpMapping' (2.0)
               - Encryption Algorithm is set to 'dvb-csa'
   
         @Commit(param=apexOutputTsConfBlade7ApplyChange, value=2)
        "
::= { apexOutputTsConfigBlade7Entry 6 }

apexOutputTsConfBlade7DepiRemoteId OBJECT-TYPE
    SYNTAX Integer32(0..65535)
    MAX-ACCESS read-write
    STATUS current
    DESCRIPTION
        "Unique identifier within the systems. Allows communication with the CMTS-core 
         to establish the DEPI control plane.
         
         @Commit(param=apexOutputTsConfBlade7ApplyChange, value=2)
        "
::= { apexOutputTsConfigBlade7Entry 7 }

apexOutputTsConfBlade7QamReplicationRfPort OBJECT-TYPE
    SYNTAX MasterRfPortTYPE
    MAX-ACCESS read-write
    STATUS current
    DESCRIPTION
        "RF Port when operating mode set to QAM Replication. Must be set to None
         when operating mode is not set to QAM Replication. 
         
         The Master RF Port from which this slave port is to be replicated.
         
         Selection restricted as follows:
         
                                 Slave
                         ---------------------
            Master       RF1   RF2   RF3   RF4
            ------       ---   ---   ---   ---
            none          Y     Y     Y     Y
            port1         N     Y     Y     Y
            port2         N     N     Y     Y
            port3         N     N     N     Y
        
         @Commit(param=apexOutputTsConfBlade7ApplyChange, value=2)
        "
::= { apexOutputTsConfigBlade7Entry 8 }


-- ------------------------------------------------------------------------------
--
-- apexOutputTsConfigBlade8
--
-- apexOutputTsConfBlade8ApplyTable
--

apexOutputTsConfBlade8ApplyTable OBJECT-TYPE
    SYNTAX SEQUENCE OF ApexOutputTsConfBlade8ApplyEntry
    MAX-ACCESS not-accessible
    STATUS current
    DESCRIPTION
        "Table of Apply Change for Output Ts Config Table.
        
         This apply is only used for apexOutputTsConfBlade8OperatingMode, 
         apexOutputTsConfBlade8OutPatTsId, and 
         apexOutputTsConfBlade8EncryptionType."
::= { apexOutputTsConfigBlade8 1 }

apexOutputTsConfBlade8ApplyEntry OBJECT-TYPE
    SYNTAX ApexOutputTsConfBlade8ApplyEntry
    MAX-ACCESS not-accessible
    STATUS current
    DESCRIPTION
        "Output Transport Stream Apply Table Entry."
    INDEX { apexOutputTsConfBlade8ApplyIndex }
::= { apexOutputTsConfBlade8ApplyTable 1 }

ApexOutputTsConfBlade8ApplyEntry ::= SEQUENCE
    {
     apexOutputTsConfBlade8ApplyIndex           Integer32,
     apexOutputTsConfBlade8ApplyChange          ApplyDataToDeviceTYPE
    }
    
apexOutputTsConfBlade8ApplyIndex OBJECT-TYPE
    SYNTAX Integer32(1..256)
    MAX-ACCESS not-accessible
    STATUS current
    DESCRIPTION
        "Index of Output Transport Stream Apply Table."
::= { apexOutputTsConfBlade8ApplyEntry 1 }

apexOutputTsConfBlade8ApplyChange OBJECT-TYPE
    SYNTAX ApplyDataToDeviceTYPE
    MAX-ACCESS read-write
    STATUS current
    DESCRIPTION
        "The apply for Output Ts Config Table.  This apply is only used for:
           apexOutputTsConfBlade8OperatingMode
           apexOutputTsConfBlade8OutPatTsId
           apexOutputTsConfBlade8EncryptionType
           apexOutputTsConfBlade8SimulcryptMode
           apexOutputTsConfBlade8DepiRemoteId
           apexOutputTsConfBlade8QamReplicationRfPort
         
         A row in this table corresponds to the same row index in the
         Output Ts Config table.

         This parameter MUST be set to 'apply' in order for the items listed
         above to take effect in the APEX.  This parameter MUST be set LAST 
         after the relevant data in the Output Ts Config row has been configured.

         @Config(config=no, reboot=no)
        "
::= { apexOutputTsConfBlade8ApplyEntry 2 }     


-- ------------------------------------------------------------------------------
--
-- apexOutputTsConfigBlade8Table
--

apexOutputTsConfigBlade8Table OBJECT-TYPE
    SYNTAX SEQUENCE OF ApexOutputTsConfigBlade8Entry
    MAX-ACCESS not-accessible
    STATUS current
    DESCRIPTION
        "This is a table of configuration parameters for Output Transport
         Streams.

         Once written, a change to the following parameters will only take 
         effect after the appropriate apexOutputTsConfBlade1ApplyChange
         is set to 'apply':  
           apexOutputTsConfBlade8OperatingMode
           apexOutputTsConfBlade8OutPatTsId
           apexOutputTsConfBlade8EncryptionType
           apexOutputTsConfBlade8SimulcryptMode
           apexOutputTsConfBlade8DepiRemoteId
           apexOutputTsConfBlade8QamReplicationRfPort
         
         All other changes to this table will take immediate effect.
         In order for the change to persist through subsequent reboots or power
         cycles, the change must be saved via the apexSaveConfig parameter.

         @Config(config=yes, reboot=no)
         @Save(apexSaveConfig, value=2)
         @File(config.ini, type='ini')
        "
::= { apexOutputTsConfigBlade8 2 }

apexOutputTsConfigBlade8Entry OBJECT-TYPE
    SYNTAX ApexOutputTsConfigBlade8Entry
    MAX-ACCESS not-accessible
    STATUS current
    DESCRIPTION
        "Output Transport Stream Configuration Table Entry."
    INDEX { apexOutputTsConfBlade8OutputTsNum }
::= { apexOutputTsConfigBlade8Table 1 }

ApexOutputTsConfigBlade8Entry ::= SEQUENCE
    {
     apexOutputTsConfBlade8OutputTsNum          Integer32,
     apexOutputTsConfBlade8PidRemappingMode     INTEGER,
     apexOutputTsConfBlade8OperatingMode        INTEGER,
     apexOutputTsConfBlade8OutPatTsId           Integer32,
     apexOutputTsConfBlade8EncryptionType       INTEGER,
     apexOutputTsConfBlade8SimulcryptMode       INTEGER,
     apexOutputTsConfBlade8DepiRemoteId         Integer32,
     apexOutputTsConfBlade8QamReplicationRfPort MasterRfPortTYPE
    }

apexOutputTsConfBlade8OutputTsNum OBJECT-TYPE
    SYNTAX Integer32(1..256)
    MAX-ACCESS not-accessible
    STATUS current
    DESCRIPTION
        "Output Transport Stream Number."
::= { apexOutputTsConfigBlade8Entry 1 }

apexOutputTsConfBlade8PidRemappingMode OBJECT-TYPE
    SYNTAX INTEGER
        {
         disabled           (1),
         remapWithoutReuse  (2),
         remapProgramBased  (3),
         remapProgramBased2 (4)
        }
    MAX-ACCESS read-write
    STATUS current
    DESCRIPTION
        "The PID Remapping mode setting.

         When 'disabled', the output PIDs for all services and ancillary PIDs
         are the same as the input PID values. PID collisions can occur when 
         multiple inputs are mapped to the same output. User is responsible for
         ensuring PIDs mapped from multiple input streams are unique.

         When 'remapWithoutReuse', the APEX will determine the output PIDs
         from a predetermined range of PIDs for services and ancillary PIDs.
         The APEX will use a scheme to limit the reuse of service PIDs for each
         service mapping. UDP Port Mapping and Session Control outputs should 
         always have PID Remapping enabled (set to 'remapWithoutReuse').

         When 'remapProgramBased' or 'remapProgramBased2', the APEX will determine 
         the output PIDs from a predetermined range of PIDs for services and 
         ancillary PIDs. The APEX uses a scheme to select the PMT PID based on 
         the program number. The PMT PID is calculated as follows for each mode:
            remapProgramBased =  (Program Number + 1) * 16
            remapProgramBased2 = (Program Number * 16) + 2
         
         The component PIDs are sequential after the PMT PID. This scheme only
         allows for a total of 15 component PIDs per program. Output program
         numbers are also limited (1-255). This scheme is intended to be used
         when in UDP Port Mapping mode at specific sites.

         PID Remapping mode changes can only occur when the output is not in use
         (no service, PID, or stream mapping active to the output).
        "
::= { apexOutputTsConfigBlade8Entry 2 }

apexOutputTsConfBlade8OperatingMode OBJECT-TYPE
    SYNTAX INTEGER
        {
         notInUse       (0),
         rtspSession    (1),
         manualRouting  (2),
         udpMapping     (3),
         rpcSession     (4),
         depi           (5),
         qamReplication (6)
        }
    MAX-ACCESS read-write
    STATUS current
    DESCRIPTION
        "This parameter is used to set the operating mode of the output.

         Operating mode changes can only occur when the output is not in use
         (no service, PID, or stream mapping active to the output).
         RTSP Session
            - User must select either RTSP-R6/D6 or MHA-ERMI to communicate with external
              resource manager. All service mappings on output are controlled
              by the external manager.
            - Only valid when Encryption Type is set to CTE or None
            - Only valid when Simulcrypt Mode is set to None (2.0)
            - PID Remapping mode should be Enabled (Without Reuse)
            
         Manual Routing
            - User manually maps each service
            - Encryption Type can be any valid setting (none, CTE, or Broadcast)
            - Simulcrypt Mode must be None or Enabled
            
         UDP Port Mapping
            - Standard UDP Port Mapping for use with VOD servers. Uses specific
              algorithm based on UDP Port to determine output program mappings.
            - Encryption Type must be None or CTE (broadcast not supported)
            - Simulcrypt Mode must be None or Enabled
            
         RPC Session
            - All service mappings on output are controlled by external manager
              using the RPC protocol.  
            - Only valid when Encryption Type is set to CTE or None
            - Only valid when Simulcrypt Mode is set to None (2.0)
            - PID Remapping mode should be Enabled (Without Reuse)

         Operating mode changes can only occur when the output is not in use
         (no service, PID, or stream mapping active to the output).
         
         @Commit(param=apexOutputTsConfBlade8ApplyChange, value=2)
        "
::= { apexOutputTsConfigBlade8Entry 3 }

apexOutputTsConfBlade8OutPatTsId OBJECT-TYPE
    SYNTAX Integer32(0..65535)
    MAX-ACCESS read-write
    STATUS current
    DESCRIPTION
        "Output Transport Stream ID to use for the output PAT in this Output
         Transport Stream. Changes to the output PAT TS ID can be made at any
         time and will cause the output PAT to automatically be updated to
         reflect the new TS ID setting.
         
         @Commit(param=apexOutputTsConfBlade8ApplyChange, value=2)
        "
::= { apexOutputTsConfigBlade8Entry 4 }

apexOutputTsConfBlade8EncryptionType OBJECT-TYPE
    SYNTAX INTEGER
        {
         noEncryption             (0),
         cte                      (1)
        }
    MAX-ACCESS read-write
    STATUS current
    DESCRIPTION
        "This parameter is used to set the encryption type of the output.

         'noEncryption'
            - All services are output in the clear

         'cte'
            - Services on output use Common Tier Encryption. CTE parameters
              determine encryption mode, copy protection, and tiers. All services
              in CTE mode use the exact same configuration settings.
            - Valid for all operating modes.
            - Simulcrypt Mode must be set to None.

         @Commit(param=apexOutputTsConfBlade8ApplyChange, value=2)
        "
::= { apexOutputTsConfigBlade8Entry 5 }

apexOutputTsConfBlade8SimulcryptMode OBJECT-TYPE
    SYNTAX INTEGER
        {
         none             (0),
         enabledEmms      (1),
         enabledNoEmms    (2)
        }
    MAX-ACCESS read-write
    STATUS current
    DESCRIPTION
        "This parameter is used to set the Simulcrypt mode of the output. Changes to this
         parameter can only be done when there are no programs mapped to the output. All
         programs must be disabled on an output before this parameter can be changed.

         'none' 
            - Used for normal Mediacypher only encryption (CTE or session Encryption). 

         'enabledEmms'
            - Enabled with EMMs insertion.
            - Used to indicate an external or internal EIS will control the encryption of  
              all services on the output.
            - Only valid when:
               - Encryption Type is set to 'noEncryption'
               - Operating Mode is set to 'manualRouting' or 'udpMapping' (2.0)
               - Encryption Algorithm is set to 'dvb-csa'
               
         'enabledNoEmms'
            - Enabled without EMMs insertion.
            - Used to indicate an external or internal EIS will control the encryption of  
              all services on the output.
            - Only valid when:
               - Encryption Type is set to 'noEncryption'
               - Operating Mode is set to 'manualRouting' or 'udpMapping' (2.0)
               - Encryption Algorithm is set to 'dvb-csa'
   
         @Commit(param=apexOutputTsConfBlade8ApplyChange, value=2)
        "
::= { apexOutputTsConfigBlade8Entry 6 }

apexOutputTsConfBlade8DepiRemoteId OBJECT-TYPE
    SYNTAX Integer32(0..65535)
    MAX-ACCESS read-write
    STATUS current
    DESCRIPTION
        "Unique identifier within the systems. Allows communication with the CMTS-core 
         to establish the DEPI control plane.
         
         @Commit(param=apexOutputTsConfBlade8ApplyChange, value=2)
        "
::= { apexOutputTsConfigBlade8Entry 7 }

apexOutputTsConfBlade8QamReplicationRfPort OBJECT-TYPE
    SYNTAX MasterRfPortTYPE
    MAX-ACCESS read-write
    STATUS current
    DESCRIPTION
        "RF Port when operating mode set to QAM Replication. Must be set to None
         when operating mode is not set to QAM Replication. 
         
         The Master RF Port from which this slave port is to be replicated.
         
         Selection restricted as follows:
         
                                 Slave
                         ---------------------
            Master       RF1   RF2   RF3   RF4
            ------       ---   ---   ---   ---
            none          Y     Y     Y     Y
            port1         N     Y     Y     Y
            port2         N     N     Y     Y
            port3         N     N     N     Y
        
         @Commit(param=apexOutputTsConfBlade8ApplyChange, value=2)
        "
::= { apexOutputTsConfigBlade8Entry 8 }


-- ------------------------------------------------------------------------------
--
-- apexOutputTsStatus
--
-- apexOutputTsStatusGeneral
--
-- none


-- ------------------------------------------------------------------------------
--
-- apexOutputTsUtilization
--
-- apexOutputTsUtilizationGeneral
--

apexOutputTsUtilizationSamplePeriod OBJECT-TYPE
    SYNTAX Integer32
    MAX-ACCESS read-only
    STATUS current
    DESCRIPTION
        "Sample Period for Output Transport Stream Bandwidth Utilization
         Rate Monitoring.
         This parameter indicates the length of time in milliseconds the
         stream is monitored during a single sample.
         This can be used with apexOutputTsUtilizNumSamples to
         determine the amount of time or percent of time the stream was
         monitored during a fifteen minute sampling interval."
::= { apexOutputTsUtilizationGeneral 1 }


-- ------------------------------------------------------------------------------
--
-- apexOutputTsUtilizationTable
--

apexOutputTsUtilizationTable OBJECT-TYPE
    SYNTAX SEQUENCE OF ApexOutputTsUtilizationEntry
    MAX-ACCESS not-accessible
    STATUS current
    DESCRIPTION
        "This is a table of status parameters containing bandwidth
         utilization for Output Transport Streams.  The sampling
         interval is up to fifteen minutes.  There is a rolling
         average as well as last sample, peak, and minimum information.
         There is overflow information and dropped packet counts.

         This table is indexed by Blade Number and Output Stream Number."
::= { apexOutputTsUtilization 2 }

apexOutputTsUtilizationEntry OBJECT-TYPE
    SYNTAX ApexOutputTsUtilizationEntry
    MAX-ACCESS not-accessible
    STATUS current
    DESCRIPTION
        "Output Transport Stream Bandwidth Utilization Table Entry."
    INDEX { apexOutputTsUtilizBladeNum, apexOutputTsUtilizOutputTsNum }
::= { apexOutputTsUtilizationTable 1 }

ApexOutputTsUtilizationEntry ::= SEQUENCE
    {
     apexOutputTsUtilizBladeNum           Integer32,
     apexOutputTsUtilizOutputTsNum        Integer32,
     apexOutputTsUtilizDataFlag           INTEGER,
     apexOutputTsUtilizNumSamples         Unsigned32,
     apexOutputTsUtilizThreshold          INTEGER,
     apexOutputTsUtilizTime               Unsigned32,
     apexOutputTsUtilizCurPercent         Integer32,
     apexOutputTsUtilizAvgPercent         Integer32,
     apexOutputTsUtilizMinPercent         Integer32,
     apexOutputTsUtilizPeakPercent        Integer32,
     apexOutputTsUtilizCurRate            Unsigned32,
     apexOutputTsUtilizAvgRate            Unsigned32,
     apexOutputTsUtilizMinRate            Unsigned32,
     apexOutputTsUtilizPeakRate           Unsigned32,
     apexOutputTsUtilizThresholdAlarm     INTEGER
    }

apexOutputTsUtilizBladeNum OBJECT-TYPE
    SYNTAX Integer32(1..8)
    MAX-ACCESS not-accessible
    STATUS current
    DESCRIPTION
        "Blade Number."
::= { apexOutputTsUtilizationEntry 1 }

apexOutputTsUtilizOutputTsNum OBJECT-TYPE
    SYNTAX Integer32(1..256)
    MAX-ACCESS not-accessible
    STATUS current
    DESCRIPTION
        "Output Transport Stream Number."
::= { apexOutputTsUtilizationEntry 2 }

apexOutputTsUtilizDataFlag OBJECT-TYPE
    SYNTAX INTEGER
        {
         notApplicable      (0),
         samplingComplete   (1),
         samplingIncomplete (2)
        }
    MAX-ACCESS read-only
    STATUS current
    DESCRIPTION
        "Flag to indicate whether the Output Transport Stream was monitored
         a full fifteen minute sampling interval and a complete set of samples
         was obtained.

         'samplingComplete'   - indicates sampling complete with good samples.
         'samplingIncomplete' - indicates incomplete sampling due to APEX
                                startup or OTS rate changed during the period."
::= { apexOutputTsUtilizationEntry 3 }

apexOutputTsUtilizNumSamples OBJECT-TYPE
    SYNTAX Unsigned32
    MAX-ACCESS read-only
    STATUS current
    DESCRIPTION
        "Number of samples included in the data.
         This can be used with apexOutputTsUtilizationSamplePeriod
         to determine the amount of time or percent of time the
         stream was monitored during the sampling interval."
::= { apexOutputTsUtilizationEntry 4 }

apexOutputTsUtilizThreshold OBJECT-TYPE
    SYNTAX INTEGER
        {
         notApplicable         (0),
         noError               (1),
         alarmThresholdReached (2)
        }
    MAX-ACCESS read-only
    STATUS current
    DESCRIPTION
        "Indicates whether there is a utilization error has occurred.
         The error occurs when Output Utilization Alarm Threshold has
         been reached for Output Utilization Set Alarm Delay seconds
         and will clear after the output is below the Output Utilization
         Alarm Threshold for Output Utilization Clear Alarm Delay.  This
         field is also cleared when the QAM output is disabled."
::= { apexOutputTsUtilizationEntry 5 }

apexOutputTsUtilizTime OBJECT-TYPE
    SYNTAX Unsigned32
    MAX-ACCESS read-only
    STATUS current
    DESCRIPTION
        "Time in GPS seconds (apexSystemTime) that this table row was saved.
         When GPS time is not available to the apex (apexSystemTime=0) a clock
         maintained inside the APEX will be used.  This clock starts at GPS time
         zero when the apex is booted.  The APEX will use real GPS time if and
         when GPS time becomes available to the APEX."
::= { apexOutputTsUtilizationEntry 6 }

apexOutputTsUtilizCurPercent OBJECT-TYPE
    SYNTAX Integer32 (0..100)
    MAX-ACCESS read-only
    STATUS current
    DESCRIPTION
        "Percent utilization of most recently taken sample."
::= { apexOutputTsUtilizationEntry 7 }

apexOutputTsUtilizAvgPercent OBJECT-TYPE
    SYNTAX Integer32 (0..100)
    MAX-ACCESS read-only
    STATUS current
    DESCRIPTION
        "Average percent utilization over the rolling sampling interval."
::= { apexOutputTsUtilizationEntry 8 }

apexOutputTsUtilizMinPercent OBJECT-TYPE
    SYNTAX Integer32 (0..100)
    MAX-ACCESS read-only
    STATUS current
    DESCRIPTION
        "Minimum percent utilization for a sample during the rolling
         sampling interval."
::= { apexOutputTsUtilizationEntry 9 }

apexOutputTsUtilizPeakPercent OBJECT-TYPE
    SYNTAX Integer32 (0..100)
    MAX-ACCESS read-only
    STATUS current
    DESCRIPTION
        "Peak percent utilization for a sample during the rolling
         sampling interval."
::= { apexOutputTsUtilizationEntry 10 }

apexOutputTsUtilizCurRate OBJECT-TYPE
    SYNTAX Unsigned32
    MAX-ACCESS read-only
    STATUS current
    DESCRIPTION
        "Utilization of most recently taken sample
         in bits per second (bps)."
::= { apexOutputTsUtilizationEntry 11 }

apexOutputTsUtilizAvgRate OBJECT-TYPE
    SYNTAX Unsigned32
    MAX-ACCESS read-only
    STATUS current
    DESCRIPTION
        "Average utilization for the rolling sampling interval
         in bits per second (bps)."
::= { apexOutputTsUtilizationEntry 12 }

apexOutputTsUtilizMinRate OBJECT-TYPE
    SYNTAX Unsigned32
    MAX-ACCESS read-only
    STATUS current
    DESCRIPTION
        "Minimum utilization for a sample during this
         sampling interval in bits per second (bps)."
::= { apexOutputTsUtilizationEntry 13 }

apexOutputTsUtilizPeakRate OBJECT-TYPE
    SYNTAX Unsigned32
    MAX-ACCESS read-only
    STATUS current
    DESCRIPTION
        "Peak utilization for a sample during the rolling
         sampling interval in bits per second (bps)."
::= { apexOutputTsUtilizationEntry 14 }

apexOutputTsUtilizThresholdAlarm OBJECT-TYPE
    SYNTAX INTEGER
        {
         ok(1),
         indeterminate(2),
         warning(3),
         minor(4),
         major(5),
         critical(6)
        }
    MAX-ACCESS read-only
    STATUS current
    DESCRIPTION
        "Current fault condition of apexOutputTsUtilizThreshold.  This is
         the apexAlarmOutputUtilizationFault level for this output."
::= { apexOutputTsUtilizationEntry 15 }


-- ------------------------------------------------------------------------------
--
-- apexOutputTsStatusTable
--

apexOutputTsStatusTable OBJECT-TYPE
    SYNTAX SEQUENCE OF ApexOutputTsStatusEntry
    MAX-ACCESS not-accessible
    STATUS current
    DESCRIPTION
        "Table of Output Transport Status.
         Indexed by Blade Number and Output Transport Stream number."
::= { apexOutputTsStatus 5 }

apexOutputTsStatusEntry OBJECT-TYPE
    SYNTAX ApexOutputTsStatusEntry
    MAX-ACCESS not-accessible
    STATUS current
    DESCRIPTION
        "A row in the Output Transport Stream Status table."
    INDEX { apexOutputTsStatusBladeNum, apexOutputTsStatusOutputTsNum }
::= { apexOutputTsStatusTable 1 }

ApexOutputTsStatusEntry ::= SEQUENCE
    {
     apexOutputTsStatusBladeNum             Integer32,
     apexOutputTsStatusOutputTsNum          Integer32,
     apexOutputTsStatusFault                INTEGER
    }

apexOutputTsStatusBladeNum OBJECT-TYPE
    SYNTAX Integer32 (1..8)
    MAX-ACCESS not-accessible
    STATUS current
    DESCRIPTION
        "Blade Number."
::= { apexOutputTsStatusEntry 1 }

apexOutputTsStatusOutputTsNum OBJECT-TYPE
    SYNTAX Integer32 (1..256)
    MAX-ACCESS not-accessible
    STATUS current
    DESCRIPTION
        "Output Transport Stream Number."
::= { apexOutputTsStatusEntry 2 }

apexOutputTsStatusFault OBJECT-TYPE
    SYNTAX INTEGER
        {
         ok(1),
         indeterminate(2),
         warning(3),
         minor(4),
         major(5),
         critical(6)
        }
    MAX-ACCESS read-only
    STATUS current
    DESCRIPTION
        "Highest current fault condition associated with this Output
         Transport Stream.  The following Alarms are included:
            - apexAlarmOutputOverflow
            - apexAlarmOutputUtilizationFault
            - apexAlarmQamChannelFault
        "
::= { apexOutputTsStatusEntry 3 }


-- ------------------------------------------------------------------------------
--
-- apexOutputTsOverflowTable
--

apexOutputTsOverflowTable OBJECT-TYPE
    SYNTAX SEQUENCE OF ApexOutputTsOverflowEntry
    MAX-ACCESS not-accessible
    STATUS current
    DESCRIPTION
        "This is a table of status parameters containing dropped packet
         and overflow status for Output Transport Streams.

         This table is indexed by Blade Number and Output Transport Stream Number."
::= { apexOutputTsStatus 6 }

apexOutputTsOverflowEntry OBJECT-TYPE
    SYNTAX ApexOutputTsOverflowEntry
    MAX-ACCESS not-accessible
    STATUS current
    DESCRIPTION
        "Output Transport Stream Overflow Table Entry."
    INDEX { apexOutputTsOverflowBladeNum, apexOutputTsOverflowOutputTsNum }
::= { apexOutputTsOverflowTable 1 }

ApexOutputTsOverflowEntry ::= SEQUENCE
    {
     apexOutputTsOverflowBladeNum           Integer32,
     apexOutputTsOverflowOutputTsNum        Integer32,
     apexOutputTsOverflowCurDropPackets     Unsigned32,
     apexOutputTsOverflowTotalDropPackets   Unsigned32,
     apexOutputTsOverflowAlarm              INTEGER
    }

apexOutputTsOverflowBladeNum OBJECT-TYPE
    SYNTAX Integer32(1..8)
    MAX-ACCESS not-accessible
    STATUS current
    DESCRIPTION
        "Blade Number."
::= { apexOutputTsOverflowEntry 1 }

apexOutputTsOverflowOutputTsNum OBJECT-TYPE
    SYNTAX Integer32(1..256)
    MAX-ACCESS not-accessible
    STATUS current
    DESCRIPTION
        "Output Transport Stream Number."
::= { apexOutputTsOverflowEntry 2 }

apexOutputTsOverflowCurDropPackets OBJECT-TYPE
    SYNTAX Unsigned32
    MAX-ACCESS read-only
    STATUS current
    DESCRIPTION
        "MPEG packets dropped during the most recently taken sample."
::= { apexOutputTsOverflowEntry 3 }

apexOutputTsOverflowTotalDropPackets OBJECT-TYPE
    SYNTAX Unsigned32
    MAX-ACCESS read-only
    STATUS current
    DESCRIPTION
        "Total MPEG packets dropped on the Output.  Can be
         reset using apexOutputTsUtilMonResetTotDropPacket."
::= { apexOutputTsOverflowEntry 4 }

apexOutputTsOverflowAlarm OBJECT-TYPE
    SYNTAX INTEGER
        {
         ok(1),
         indeterminate(2),
         warning(3),
         minor(4),
         major(5),
         critical(6)
        }
    MAX-ACCESS read-only
    STATUS current
    DESCRIPTION
        "Current fault condition of apexOutputTsOverflowError.  This is
         the apexAlarmOutputOverflow level for this output."
::= { apexOutputTsOverflowEntry 5 }

                                     
-- ------------------------------------------------------------------------------
--
-- apexOutputTsStatApplyTable
--

apexOutputTsStatApplyTable OBJECT-TYPE
    SYNTAX SEQUENCE OF ApexOutputTsStatApplyEntry
    MAX-ACCESS not-accessible
    STATUS current
    DESCRIPTION
        "Table of status data for Output TS Apply Table. 
         There is 1 row for each blade.
        "
::= { apexOutputTsStatus 7 }

apexOutputTsStatApplyEntry OBJECT-TYPE
    SYNTAX ApexOutputTsStatApplyEntry
    MAX-ACCESS not-accessible
    STATUS current
    DESCRIPTION
        "Output TS Apply Status Table Entry."
    INDEX { apexOutputTsStatApplyBladeNum }
::= { apexOutputTsStatApplyTable 1 }

ApexOutputTsStatApplyEntry ::= SEQUENCE
    {
     apexOutputTsStatApplyBladeNum      Integer32,
     apexOutputTsStatusInvalidApplyText DisplayString
    }

apexOutputTsStatApplyBladeNum OBJECT-TYPE
    SYNTAX Integer32(1..8)
    MAX-ACCESS not-accessible
    STATUS current
    DESCRIPTION
        "Blade Number."
::= { apexOutputTsStatApplyEntry 1 }

apexOutputTsStatusInvalidApplyText OBJECT-TYPE
    SYNTAX DisplayString (SIZE (0..80))
    MAX-ACCESS read-only
    STATUS current
    DESCRIPTION
        "When apexOutputTsConfBlade#ApplyChange is set to applyNotInProgressInvalidData,
         this entry may contain a text description of what was wrong with the data.
         This entry contains the description for the most recent apply
         of a related entry that was invalid. 
        "
::= { apexOutputTsStatApplyEntry 2 }


-- ------------------------------------------------------------------------------
--
-- apexPsi
--
-- apexPsiConfig
--
-- apexPsiConfigGeneral
--

apexPsiDetectUnicastTimeout OBJECT-TYPE
    SYNTAX Integer32(0..21600)
    MAX-ACCESS read-write
    STATUS current
    DESCRIPTION
        "The loss of input PSI detection timeout value for all unicast mappings. 
         This is the number of seconds the APEX will use to determine if a unicast 
         mapping input PSI message (PAT or PMT) is missing. Each PSI message 
         previously extracted will be checked to determine that it is still 
         being received based on this setting.
         
         Unicast mappings are typically VOD mappings and generally require longer
         PSI timeout values due to VOD trick play (where the PSI is sometimes not
         sent by the server during FFWD, RWD, or Pause events). 
         
         A value of 0 will disable PSI detection for unicast mappings. This means 
         that once a PAT and PMT are discovered on the input stream, the APEX will
         not react to a loss of a PAT or PMT.

         Once written, the change to this parameter will take immediate effect.
         However, in order for the change to persist through subsequent reboots
         or power cycles, the change must be saved via the apexSaveConfig parameter.

         @Config(config=yes, reboot=no)
         @Save(apexSaveConfig, value=2)
         @File(config.ini, type='ini')
        "
::= { apexPsiConfigGeneral 1 }

apexPsiDetectMulticastTimeout OBJECT-TYPE
    SYNTAX Integer32(0..21600)
    MAX-ACCESS read-write
    STATUS current
    DESCRIPTION
        "The loss of input PSI detection timeout value for all multicast mappings. 
         This is the number of seconds the APEX will use to determine if a multicast 
         mapping input PSI message (PAT or PMT) is missing. Each PSI message 
         previously extracted will be checked to determine that it is still 
         being received based on this setting.
         
         A value of 0 will disable PSI detection for unicast mappings. This means 
         that once a PAT and PMT are discovered on the input stream, the APEX will
         not react to a loss of a PAT or PMT.

         Once written, the change to this parameter will take immediate effect.
         However, in order for the change to persist through subsequent reboots
         or power cycles, the change must be saved via the apexSaveConfig parameter.

         @Config(config=yes, reboot=no)
         @Save(apexSaveConfig, value=2)
         @File(config.ini, type='ini')
        "
::= { apexPsiConfigGeneral 2 }

apexPsiRangeStart OBJECT-TYPE
    SYNTAX Integer32(0..15)
    MAX-ACCESS read-write
    STATUS current
    DESCRIPTION
        "Minimum PSI version number. Used to limit the APEX to use a specific range
         of PSI numbers. Set this to 0 to allow the APEX to use the full range of
         PSI version numbers (requires apexPsiRangeStop to be set to 31).

         Once written, the change to this parameter will take immediate effect.
         However, in order for the change to persist through subsequent reboots
         or power cycles, the change must be saved via the apexSaveConfig parameter.

         @Config(config=yes, reboot=no)
         @Save(apexSaveConfig, value=2)
         @File(config.ini, type='ini')
        "
::= { apexPsiConfigGeneral 3 }

apexPsiRangeStop OBJECT-TYPE
    SYNTAX Integer32(1..31)
    MAX-ACCESS read-write
    STATUS current
    DESCRIPTION
        "Maximum PSI version number. Used to limit the APEX to use a specific range
         of PSI numbers. Set this to 31 to allow the APEX to use the full range of
         PSI version numbers (requires apexPsiRangeStart to be set to 0).

         Once written, the change to this parameter will take immediate effect.
         However, in order for the change to persist through subsequent reboots
         or power cycles, the change must be saved via the apexSaveConfig parameter.

         @Config(config=yes, reboot=no)
         @Save(apexSaveConfig, value=2)
         @File(config.ini, type='ini')
        "
::= { apexPsiConfigGeneral 4 }

apexPatVersionIncrement OBJECT-TYPE
    SYNTAX Integer32(1..15)
    MAX-ACCESS read-write
    STATUS current
    DESCRIPTION
        "Increment of PAT version upon reboot. Used to force the APEX to use a different
         PAT version number upon rebooting.

         Once written, the change to this parameter will take immediate effect.
         However, in order for the change to persist through subsequent reboots
         or power cycles, the change must be saved via the apexSaveConfig parameter.

         @Config(config=yes, reboot=no)
         @Save(apexSaveConfig, value=2)
         @File(config.ini, type='ini')
        "
::= { apexPsiConfigGeneral 5 }

apexPmtVersionIncrement OBJECT-TYPE
    SYNTAX Integer32(1..15)
    MAX-ACCESS read-write
    STATUS current
    DESCRIPTION
        "Increment of PMT version upon reboot. Used to force the APEX to use a different
         PMT version number upon rebooting.

         Once written, the change to this parameter will take immediate effect.
         However, in order for the change to persist through subsequent reboots
         or power cycles, the change must be saved via the apexSaveConfig parameter.

         @Config(config=yes, reboot=no)
         @Save(apexSaveConfig, value=2)
         @File(config.ini, type='ini')
        "
::= { apexPsiConfigGeneral 6 }

apexEcmEmmFirstPid OBJECT-TYPE
    SYNTAX Integer32(2..8190)
    MAX-ACCESS read-write
    STATUS current
    DESCRIPTION
        "First ECM-EMM PID when PID Remapping is disabled on an output stream.
         This PID along with the apexEcmEmmNumberPids defines a range of PIDs that
         the APEX will use for all ECMs and EMMs. These configuration settings allow
         a user to select a range that other service and ancillary PIDs will not 
         use. This allows the APEX to use PIDs for ECMs and EMMs without having PID
         collisions. PID collisions will cause the APEX to select another ECM or EMM
         PID causing momentary glitches of the output video and audio. 

         Once written, the change to this parameter will take immediate effect.
         However, in order for the change to persist through subsequent reboots
         or power cycles, the change must be saved via the apexSaveConfig parameter.

         @Config(config=yes, reboot=no)
         @Save(apexSaveConfig, value=2)
         @File(config.ini, type='ini')
        "
::= { apexPsiConfigGeneral 7 }

apexEcmEmmNumberPids OBJECT-TYPE
    SYNTAX Integer32(600..8188)
    MAX-ACCESS read-write
    STATUS current
    DESCRIPTION
        "Number of ECM-EMM PIDs to use when PID Remapping is disabled on an output stream.
         Refer to the apexEcmEmmFirstPid parameter for a complete description.

         Once written, the change to this parameter will take immediate effect.
         However, in order for the change to persist through subsequent reboots
         or power cycles, the change must be saved via the apexSaveConfig parameter.

         @Config(config=yes, reboot=no)
         @Save(apexSaveConfig, value=2)
         @File(config.ini, type='ini')
        "
::= { apexPsiConfigGeneral 8 }

apexProgramBasedPmtOffset OBJECT-TYPE
    SYNTAX Integer32(1 | 2)
    MAX-ACCESS read-write
    STATUS current
    DESCRIPTION
        "Program Based PID Remapping PMT PID offset. Determines the first
         PMT PID to use when Program Based algorithm selected. PMT PID
         is calculated as:
            (Program Number + Offset) * 16
         
         Program Numbers can range from 1 - 255, allowing for PMTs to start
         at 0x0020 or 0x0030 up to 0x1000 and 0x1010. 

         Changes to offset will NOT require a reboot, but if there are 
         any service mappings already in use on an output in 
         Program Based mode, then the change will NOT take effect and the 
         user will have to remove all mappings on outputs in Program 
         Based mode.
         
         Once written, the change to this parameter will take immediate effect.
         However, in order for the change to persist through subsequent reboots
         or power cycles, the change must be saved via the apexSaveConfig parameter.

         @Config(config=yes, reboot=no)
         @Save(apexSaveConfig, value=2)
         @File(config.ini, type='ini')
        "
::= { apexPsiConfigGeneral 9 }

apexSupportPreencryptedSimulcrypt OBJECT-TYPE
    SYNTAX EnableDisableTYPE
    MAX-ACCESS read-write
    STATUS current
    DESCRIPTION
        "Allows to configure the APEX to support services pre-encrypted with Simulcrypt.
         All the CA descriptors present in the input PMT will be copied to the output PMT,
         modifying the ECM PID references if needed. When set to disabled, the APEX will
         only support the processing of 1 CA ECM descriptor per service (for pre-encrypted
         content). When set to enabled, the APEX will support multiple CA ECM descriptors
         per service.
         
         @Config(config=yes, reboot=no)
         @Save(apexSaveConfig, value=2)
         @File(config.ini, type='ini')
        "
::= { apexPsiConfigGeneral 10 }


-- ------------------------------------------------------------------------------
--
-- apexPsiStatus
--
-- apexPsiStatusGeneral
--
-- none


-- ------------------------------------------------------------------------------
--
-- apexPsiStatusInputTable
--

apexPsiStatusInputTable OBJECT-TYPE
    SYNTAX SEQUENCE OF ApexPsiStatusInputEntry
    MAX-ACCESS not-accessible
    STATUS current
    DESCRIPTION
        "The following table contains a list of messages that are being extracted
         from the input side of the apex.  All extracted messages that are being used by the 
         APEX are displayed. "
::= { apexPsiStatus 2 }

apexPsiStatusInputEntry OBJECT-TYPE
    SYNTAX ApexPsiStatusInputEntry
    MAX-ACCESS not-accessible
    STATUS current
    DESCRIPTION
        "PSI Table Entry."
    INDEX { apexPsiStatusInputBladeNum, apexPsiStatusInputIndex, apexPsiStatusInputPid, 
            apexPsiStatusInputMessageType, apexPsiStatusInputProgramNumber, 
            apexPsiStatusInputSegment, apexPsiStatusInputPart }
::= { apexPsiStatusInputTable 1 }

ApexPsiStatusInputEntry ::= SEQUENCE
    {
     apexPsiStatusInputBladeNum         Integer32,
     apexPsiStatusInputIndex            Integer32,
     apexPsiStatusInputPid              Integer32,
     apexPsiStatusInputMessageType      Integer32,
     apexPsiStatusInputProgramNumber    Integer32,
     apexPsiStatusInputSegment          Integer32,
     apexPsiStatusInputPart             Integer32,
     apexPsiStatusInputBody             DisplayString,
     apexPsiStatusInputGpsTime          Integer32,
     apexPsiStatusInputMissingTime      Integer32,
     apexPsiStatusInputInfo             DisplayString
    }
                                           
apexPsiStatusInputBladeNum OBJECT-TYPE
    SYNTAX Integer32(1..8)
    MAX-ACCESS not-accessible
    STATUS current
    DESCRIPTION
        "Blade Number."
::= { apexPsiStatusInputEntry 1 }
                                          
apexPsiStatusInputIndex OBJECT-TYPE
    SYNTAX Integer32(1..1920)
    MAX-ACCESS not-accessible
    STATUS current
    DESCRIPTION
        "Indicates the input index for which this message applies.
         This is the index into the apexGbeStatusInputTsStatTable.
        "
::= { apexPsiStatusInputEntry 2 }

apexPsiStatusInputPid OBJECT-TYPE
    SYNTAX Integer32(0..8191)
    MAX-ACCESS not-accessible
    STATUS current
    DESCRIPTION
        "Indicates the PID that this message is contained in."
::= { apexPsiStatusInputEntry 3 }

apexPsiStatusInputMessageType OBJECT-TYPE
    SYNTAX Integer32(0..255)
    MAX-ACCESS not-accessible
    STATUS current
    DESCRIPTION
        "Indicates the MPEG message type of this message."
::= { apexPsiStatusInputEntry 4 }

apexPsiStatusInputProgramNumber OBJECT-TYPE
    SYNTAX Integer32(0..65535)
    MAX-ACCESS not-accessible
    STATUS current
    DESCRIPTION
        "Indicates the Program Number which this message is part of.  When a
         message is not specifically related to a program, this value is 0."
::= { apexPsiStatusInputEntry 5 }

apexPsiStatusInputSegment OBJECT-TYPE
    SYNTAX Integer32(0..256)
    MAX-ACCESS not-accessible
    STATUS current
    DESCRIPTION
        "Indicates the segment number of this message.  Useful for PAT messages.
         Otherwise this is 0."
::= { apexPsiStatusInputEntry 6 }

apexPsiStatusInputPart OBJECT-TYPE
    SYNTAX Integer32(1..16)
    MAX-ACCESS not-accessible
    STATUS current
    DESCRIPTION
        "Since a message can be 1024 bytes long the message may divided into parts.
         Each part of the message is indexed using this index."
::= { apexPsiStatusInputEntry 7 }

apexPsiStatusInputBody OBJECT-TYPE
    SYNTAX DisplayString
    MAX-ACCESS read-only
    STATUS current
    DESCRIPTION
        "Raw ASCII hex of the PSI message."
::= { apexPsiStatusInputEntry 8 }

apexPsiStatusInputGpsTime OBJECT-TYPE
    SYNTAX Integer32
    MAX-ACCESS read-only
    STATUS current
    DESCRIPTION
        "The GPS time when the PSI was added to the table."
::= { apexPsiStatusInputEntry 9 }

apexPsiStatusInputMissingTime OBJECT-TYPE
    SYNTAX Integer32
    MAX-ACCESS read-only
    STATUS current
    DESCRIPTION
        "GPS time when the PSI went missing."
::= { apexPsiStatusInputEntry 10 }

apexPsiStatusInputInfo OBJECT-TYPE
    SYNTAX DisplayString
    MAX-ACCESS read-only
    STATUS current
    DESCRIPTION
        "Comma-separated string showing Input Interface, UDP port, 
         Multicast IP, and Source IP for this PSI message."
::= { apexPsiStatusInputEntry 11 }


-- ------------------------------------------------------------------------------
--
-- apexPsiStatusOutputTable
--

apexPsiStatusOutputTable OBJECT-TYPE
    SYNTAX SEQUENCE OF ApexPsiStatusOutputEntry
    MAX-ACCESS not-accessible
    STATUS current
    DESCRIPTION
        "The following table contains a list of messages that are being inserted to the 
         output side of the apex.  Only PATs, PMTs, and CATs are displayed.  These messages
         were either given to the apex when it is in external mode or created by the apex
         when it is in internal mode."
::= { apexPsiStatus 3 }

apexPsiStatusOutputEntry OBJECT-TYPE
    SYNTAX ApexPsiStatusOutputEntry
    MAX-ACCESS not-accessible
    STATUS current
    DESCRIPTION
        "PSI Table Entry."
    INDEX { apexPsiStatusOutputBladeNum, apexPsiStatusOutputIndex, apexPsiStatusOutputPid, 
            apexPsiStatusOutputMessageType, apexPsiStatusOutputProgramNumber, 
            apexPsiStatusOutputSegment, apexPsiStatusOutputPart }
::= { apexPsiStatusOutputTable 1 }

ApexPsiStatusOutputEntry ::= SEQUENCE
    {
     apexPsiStatusOutputBladeNum        Integer32,
     apexPsiStatusOutputIndex           Integer32,
     apexPsiStatusOutputPid             Integer32,
     apexPsiStatusOutputMessageType     Integer32,
     apexPsiStatusOutputProgramNumber   Integer32,
     apexPsiStatusOutputSegment         Integer32,
     apexPsiStatusOutputPart            Integer32,
     apexPsiStatusOutputBody            DisplayString,
     apexPsiStatusOutputGpsTime         Integer32
    }

apexPsiStatusOutputBladeNum OBJECT-TYPE
    SYNTAX Integer32(1..8)
    MAX-ACCESS not-accessible
    STATUS current
    DESCRIPTION
        "Blade Number."
::= { apexPsiStatusOutputEntry 1 }

apexPsiStatusOutputIndex OBJECT-TYPE
    SYNTAX Integer32(1..256)
    MAX-ACCESS not-accessible
    STATUS current
    DESCRIPTION
        "Indicates the Output index for which this message applies.
         This is the Output Transport Stream number. 
        "
::= { apexPsiStatusOutputEntry 2 }

apexPsiStatusOutputPid OBJECT-TYPE
    SYNTAX Integer32(0..8191)
    MAX-ACCESS not-accessible
    STATUS current
    DESCRIPTION
        "Indicates the PID that this message is contained in."
::= { apexPsiStatusOutputEntry 3 }

apexPsiStatusOutputMessageType OBJECT-TYPE
    SYNTAX Integer32(0..255)
    MAX-ACCESS not-accessible
    STATUS current
    DESCRIPTION
        "Indicates the MPEG message type of this message."
::= { apexPsiStatusOutputEntry 4 }

apexPsiStatusOutputProgramNumber OBJECT-TYPE
    SYNTAX Integer32(0..65535)
    MAX-ACCESS not-accessible
    STATUS current
    DESCRIPTION
        "Indicates the Program Number which this message is part of.  When a
         message is not specifically related to a program, this value is 0."
::= { apexPsiStatusOutputEntry 5 }

apexPsiStatusOutputSegment OBJECT-TYPE
    SYNTAX Integer32(0..256)
    MAX-ACCESS not-accessible
    STATUS current
    DESCRIPTION
        "Indicates the segment number of this message.  Useful for PAT messages.
         Otherwise this is 0."
::= { apexPsiStatusOutputEntry 6 }

apexPsiStatusOutputPart OBJECT-TYPE
    SYNTAX Integer32(1..16)
    MAX-ACCESS not-accessible
    STATUS current
    DESCRIPTION
        "Since a message can be 1024 bytes long the message may divided into parts.
         Each part of the message is indexed using this index."
::= { apexPsiStatusOutputEntry 7 }

apexPsiStatusOutputBody OBJECT-TYPE
    SYNTAX DisplayString
    MAX-ACCESS read-only
    STATUS current
    DESCRIPTION
        "Raw ASCII hex of the PSI message."
::= { apexPsiStatusOutputEntry 8 }

apexPsiStatusOutputGpsTime OBJECT-TYPE
    SYNTAX Integer32
    MAX-ACCESS read-only
    STATUS current
    DESCRIPTION
        "The GPS time when the PSI was added to the table."
::= { apexPsiStatusOutputEntry 9 }


-- ------------------------------------------------------------------------------
--
-- apexOutputProgram
--
-- apexOutputProgramConfig
--
-- apexOutputProgramConfigGeneral
--

-- none


-- ------------------------------------------------------------------------------
--
-- apexOutputProgramStatus
--
-- apexOutputProgramStatusGeneral
--

-- none


-- ------------------------------------------------------------------------------
--
-- apexOutputProgramTable
--

apexOutputProgramTable OBJECT-TYPE
    SYNTAX SEQUENCE OF ApexOutputProgramEntry
    MAX-ACCESS not-accessible
    STATUS current
    DESCRIPTION
        "This table shows the input program to output program
         mapping status."
::= { apexOutputProgramStatus 2 }

apexOutputProgramEntry OBJECT-TYPE
    SYNTAX ApexOutputProgramEntry
    MAX-ACCESS not-accessible
    STATUS current
    DESCRIPTION
        "Output Program Table Entry."
    INDEX { apexOutputProgramBladeNum, apexOutputProgramOutputTsNum, apexOutputProgramOutputProgNum }           
::= { apexOutputProgramTable 1 }

ApexOutputProgramEntry ::= SEQUENCE
    {
     apexOutputProgramBladeNum          Integer32,
     apexOutputProgramOutputTsNum       Integer32,
     apexOutputProgramOutputProgNum     Integer32,
     apexOutputProgramInputTsIndex      Integer32,
     apexOutputProgramInputProgNum      Integer32,
     apexOutputProgramRoutingStatus     DisplayString,
     apexOutputProgramInputPreEncrypted INTEGER,
     apexOutputProgramError             INTEGER,
     apexOutputProgramEncryptionMode    INTEGER,
     apexOutputProgramEncryptionStatus  DisplayString,
     apexOutputProgramEcmServiceId      Integer32,
     apexOutputProgramCciLevel          INTEGER,
     apexOutputProgramApsLevel          INTEGER,
     apexOutputProgramCitSetting        INTEGER,
     apexOutputProgramNumberTiers       Integer32,
     apexOutputProgramTierData          DisplayString,
     apexOutputProgramInputInfo         DisplayString,
     apexOutputProgramSourceId          Integer32,
     apexOutputProgramProviderId        Integer32,
     apexOutputProgramSourceDescription DisplayString
    }

apexOutputProgramBladeNum OBJECT-TYPE
    SYNTAX Integer32(1..8)
    MAX-ACCESS not-accessible
    STATUS current
    DESCRIPTION
        "Blade Number."
::= { apexOutputProgramEntry 1 }

apexOutputProgramOutputTsNum OBJECT-TYPE
    SYNTAX Integer32(0..256)
    MAX-ACCESS not-accessible
    STATUS current
    DESCRIPTION
        "Output Transport Stream Number."
::= { apexOutputProgramEntry 2 }

apexOutputProgramOutputProgNum OBJECT-TYPE
    SYNTAX Integer32
    MAX-ACCESS not-accessible
    STATUS current
    DESCRIPTION
        "Output MPEG Program Number."
::= { apexOutputProgramEntry 3 }

apexOutputProgramInputTsIndex OBJECT-TYPE
    SYNTAX Integer32
    MAX-ACCESS read-only
    STATUS current
    DESCRIPTION
        "The index into the apexGbeStatusInputTsStatTable."
::= { apexOutputProgramEntry 4 }

apexOutputProgramInputProgNum OBJECT-TYPE
    SYNTAX Integer32
    MAX-ACCESS read-only
    STATUS current
    DESCRIPTION
        "Input MPEG Program Number."
::= { apexOutputProgramEntry 5 }

apexOutputProgramRoutingStatus OBJECT-TYPE
    SYNTAX DisplayString (SIZE (0..64))
    MAX-ACCESS read-only
    STATUS current
    DESCRIPTION
        "Current Program Routing Status."
::= { apexOutputProgramEntry 6 }

apexOutputProgramInputPreEncrypted OBJECT-TYPE
    SYNTAX INTEGER
        {
         notApplicable (0),
         clear         (1),
         preEncrypted  (2)
        }
    MAX-ACCESS read-only
    STATUS current
    DESCRIPTION
        "Indicates whether the program was pre-encrypted.
         Pre-encryption status is determined by the presence or
         absence of a CA ECM descriptor within the input PMT."
::= { apexOutputProgramEntry 7 }

apexOutputProgramError OBJECT-TYPE
    SYNTAX INTEGER
        {
         notApplicable (0),
         ok            (1),
         error         (2)
        }
    MAX-ACCESS read-only
    STATUS current
    DESCRIPTION
        "Indicates if the program is in error."
::= { apexOutputProgramEntry 8 }

apexOutputProgramEncryptionMode OBJECT-TYPE
    SYNTAX INTEGER
        {
         none               (0),
         full               (1),
         fwk                (2),
         fpk                (3),
         clear              (4),
         unencrypted        (5),
         preEncrypted       (6),
         unencryptedWithCci (7)
         }
    MAX-ACCESS read-only
    STATUS current
    DESCRIPTION
        "Currently configured encryption mode for the program.
         none - indicates the program is not being encrypted for
           CTE or Session encryption.
         unencrypted - Applies to Broadcast services only. Unencrypted
           services are treated the same as clear services (no encryption).
         preEncrypted - Applies to Broadcast services only. Input
           program pre-encryption checking is applied. Output program is
           not encrypted by the APEX, regardless if input encrypted or not.
         unencryptedWithCci - True unencrypted mode where packets are not
           scrambled, but ECMs are inserted and ECM CA reference is added
           to output PMT (PRK contains Copy Protection information)."
::= { apexOutputProgramEntry 9 }

apexOutputProgramEncryptionStatus OBJECT-TYPE
    SYNTAX DisplayString (SIZE (0..64))
    MAX-ACCESS read-only
    STATUS current
    DESCRIPTION
        "Current Program Encryption Status."
::= { apexOutputProgramEntry 10 }

apexOutputProgramEcmServiceId OBJECT-TYPE
    SYNTAX Integer32
    MAX-ACCESS read-only
    STATUS current
    DESCRIPTION
        "The ECM service ID used when this program is encrypted. This
         is the service ID used in all ECM messages for this program."
::= { apexOutputProgramEntry 11 }

apexOutputProgramCciLevel OBJECT-TYPE
    SYNTAX INTEGER
        {
         notApplicable (0),
         notDefined    (1),
         copyFreely    (2),
         copyOnce      (3),
         copyNever     (4),
         noMoreCopies  (5)
        }
    MAX-ACCESS read-only
    STATUS current
    DESCRIPTION
        "Copy protection CCI Level. This is only applicable when the
         program is being encrypted."
::= { apexOutputProgramEntry 12 }

apexOutputProgramApsLevel OBJECT-TYPE
    SYNTAX INTEGER
        {
         notApplicable   (0),
         notDefined      (1),
         off             (2),
         splitBurstOff   (3),
         splitBurst2Line (4),
         splitBurst4Line (5)
        }
    MAX-ACCESS read-only
    STATUS current
    DESCRIPTION
        "Copy protection Analog Protection Services Level. This is only
         applicable when the program is being encrypted."
::= { apexOutputProgramEntry 13 }

apexOutputProgramCitSetting OBJECT-TYPE
    SYNTAX INTEGER
        {
         notApplicable (0),
         disabled      (1),
         enabled       (2)
        }
    MAX-ACCESS read-only
    STATUS current
    DESCRIPTION
        "Copy protection Constraint Image Trigger setting. This is only
         applicable when the program is being encrypted."
::= { apexOutputProgramEntry 14 }

apexOutputProgramNumberTiers OBJECT-TYPE
    SYNTAX Integer32
    MAX-ACCESS read-only
    STATUS current
    DESCRIPTION
        "The number of program tiers. This is only applicable when the
         program is being encrypted."
::= { apexOutputProgramEntry 15 }

apexOutputProgramTierData OBJECT-TYPE
    SYNTAX DisplayString
    MAX-ACCESS read-only
    STATUS current
    DESCRIPTION
        "Current Program Tier Data. Tier information is in
         hexadecimal format. Up to 7 tiers of information are
         provided for each program. Tier information for each
         program consists of 8 bytes of information.
         First 4 bytes are the program tier value in hexadecimal.
         Next 4 bytes are the tier type in hexadecimal format.
         This is only applicable when the program is being encrypted."
::= { apexOutputProgramEntry 16 }

apexOutputProgramInputInfo OBJECT-TYPE
    SYNTAX DisplayString
    MAX-ACCESS read-only
    STATUS current
    DESCRIPTION
        "Comma-separated string showing input stream information
         in following order:
            Input Interface, UDP port, Multicast IP, and Source IP.
        "
::= { apexOutputProgramEntry 17 }

apexOutputProgramSourceId OBJECT-TYPE
    SYNTAX Integer32(0..65535)
    MAX-ACCESS read-only
    STATUS current
    DESCRIPTION
        "Encryption Source ID. 
        "
::= { apexOutputProgramEntry 18 }

apexOutputProgramProviderId OBJECT-TYPE
    SYNTAX Integer32(0..65535)
    MAX-ACCESS read-only
    STATUS current
    DESCRIPTION
        "Encryption Provider ID.
        "
::= { apexOutputProgramEntry 19 }

apexOutputProgramSourceDescription OBJECT-TYPE
    SYNTAX DisplayString (SIZE (0..128))
    MAX-ACCESS read-only
    STATUS current
    DESCRIPTION
        "Source Name associated with Source ID and Provider ID.
         Text Description of the service provided by the Rights Data Server
        "
::= { apexOutputProgramEntry 20 }


-- ------------------------------------------------------------------------------
--
-- apexAcp
--
-- apexAcpConfig
--
-- apexAcpConfigGeneral
--

-- none


-- ------------------------------------------------------------------------------
--
-- apexAcpStatus
--
-- apexAcpStatusGeneral
--

-- none


-- ------------------------------------------------------------------------------
--
-- apexAcpStatusTable
--

apexAcpStatusTable OBJECT-TYPE
    SYNTAX SEQUENCE OF ApexAcpStatusEntry
    MAX-ACCESS not-accessible
    STATUS current
    DESCRIPTION
        "This table shows the status of the Control Word Generating ACPs."
::= { apexAcpStatus 2 }

apexAcpStatusEntry OBJECT-TYPE
    SYNTAX ApexAcpStatusEntry
    MAX-ACCESS not-accessible
    STATUS current
    DESCRIPTION
        "ACP Status Table Entry."
    INDEX { apexAcpStatusBladeNum, apexAcpStatusIndex }
::= { apexAcpStatusTable 1 }

ApexAcpStatusEntry ::= SEQUENCE
    {
     apexAcpStatusBladeNum      Integer32,
     apexAcpStatusIndex         Integer32,
     apexAcpUnitAddress         DisplayString,
     apexAcpHealthByte          Integer32,
     apexAcpEvenCsn             Integer32,
     apexAcpOddCsn              Integer32,
     apexAcpUnitAttribute       Integer32
    }

apexAcpStatusBladeNum OBJECT-TYPE
    SYNTAX Integer32(1..8)
    MAX-ACCESS not-accessible
    STATUS current
    DESCRIPTION
        "Blade Number."
::= { apexAcpStatusEntry 1 }

apexAcpStatusIndex OBJECT-TYPE
    SYNTAX Integer32(1..4)
    MAX-ACCESS not-accessible
    STATUS current
    DESCRIPTION
        "ACP Status Index (index of the MC2.1)."
::= { apexAcpStatusEntry 2 }

apexAcpUnitAddress OBJECT-TYPE
    SYNTAX DisplayString (SIZE (0..11))
    MAX-ACCESS read-only
    STATUS current
    DESCRIPTION
        "The unit address of the ACP in ASCII Hex.  The Unit address is a 5 byte value."
::= { apexAcpStatusEntry 3 }

apexAcpHealthByte OBJECT-TYPE
    SYNTAX Integer32
    MAX-ACCESS read-only
    STATUS current
    DESCRIPTION
        "The health byte of the ACP.  Indicates whether the ACP has intact fuses.  The
         health should read 255 (hex 0xFF) for all APEX ACPs.  Otherwise, the ACP will
         not properly function."
::= { apexAcpStatusEntry 4 }

apexAcpEvenCsn OBJECT-TYPE
    SYNTAX Integer32
    MAX-ACCESS read-only
    STATUS current
    DESCRIPTION
        "The Even Category Sequence Number of the ACP.
         Should match the even CSN assigned by DAC,
         if not may indicate a communications problem."
::= { apexAcpStatusEntry 5 }

apexAcpOddCsn OBJECT-TYPE
    SYNTAX Integer32
    MAX-ACCESS read-only
    STATUS current
    DESCRIPTION
        "The Odd Category Sequence Number of the ACP.
         Should match the odd CSN assigned by DAC,
         if not may indicate a communications problem."
::= { apexAcpStatusEntry 6 }

apexAcpUnitAttribute OBJECT-TYPE
    SYNTAX Integer32
    MAX-ACCESS read-only
    STATUS current
    DESCRIPTION
        "Unit attribute byte is made available to verify that the MC2.1 was
         properly unit created during factory production."
::= { apexAcpStatusEntry 7 }


-- ------------------------------------------------------------------------------
--
--  apexAcpStatusModuleTable
--

apexAcpStatusModuleTable OBJECT-TYPE
    SYNTAX SEQUENCE OF ApexAcpStatusModuleEntry
    MAX-ACCESS not-accessible
    STATUS current
    DESCRIPTION
        "This table shows the module status of the ACP module on each
         QAM blade."
::= { apexAcpStatus 3 }

apexAcpStatusModuleEntry OBJECT-TYPE
    SYNTAX ApexAcpStatusModuleEntry
    MAX-ACCESS not-accessible
    STATUS current
    DESCRIPTION
        "ACP Module Status Table Entry."
    INDEX { apexAcpStatusModuleBladeNum }
::= { apexAcpStatusModuleTable 1 }

ApexAcpStatusModuleEntry ::= SEQUENCE
    {
     apexAcpStatusModuleBladeNum      Integer32,
     apexAcpStatusModulePresent       ModulePresentTYPE,
     apexAcpStatusModuleInitState     INTEGER
    }

apexAcpStatusModuleBladeNum OBJECT-TYPE
    SYNTAX Integer32(1..8)
    MAX-ACCESS not-accessible
    STATUS current
    DESCRIPTION
        "Blade Number."
::= { apexAcpStatusModuleEntry 1 }

apexAcpStatusModulePresent OBJECT-TYPE
    SYNTAX ModulePresentTYPE
    MAX-ACCESS read-only
    STATUS current
    DESCRIPTION
        "Indicates whether the module is Present or Missing on the QAM Blade."
::= { apexAcpStatusModuleEntry 2 }

apexAcpStatusModuleInitState OBJECT-TYPE
    SYNTAX INTEGER
        {
         notInitialized           (0),
         initializationFailed     (1),
         initializedNoSeeds       (2),
         initializedDataRetention (3),
         initializedHealthGood    (4),
         initializedHealthBad     (5)
        }    
    MAX-ACCESS read-only
    STATUS current
    DESCRIPTION
        "ACP initialization state of entire ACP module."
::= { apexAcpStatusModuleEntry 3 }


-- ------------------------------------------------------------------------------
--
-- apexUdpPortMapping
--
-- apexUdpMapConfig
--
-- apexUdpMapConfigGeneral
--

apexUdpMapPreEncryptCheck OBJECT-TYPE
    SYNTAX EnableDisableTYPE
    MAX-ACCESS read-write
    STATUS current
    DESCRIPTION
        "UDP Mapping pre-encryption checking.

         Indicates if the APEX is to check if input services are pre-encrypted or
         clear. Pre-encrypted is determined by examining the input PMT for a CA ECM
         descriptor (any CA ECM descriptor). If pre-encrypted, setting this flag will
         cause the APEX to pass through ECM PID for the service. For input services
         that have a GI CA ECM descriptor, the APEX will also pass through the PIT
         message (extract and re-insert the PIT). The output PMT for pre-encrypted
         services will contain a CA ECM descriptor (referencing the ECM
         PID). When PID Remapping is enabled, pre-encryption for a service is
         only valid when the input ECM PID is on a different PID than the
         associated PMT PID. If this flag is set to pre-encryption and the
         input service is not pre-encrypted, then the setting of this flag has
         no affect on the output service.

         Once written, the change to this parameter will take immediate
         effect and all mappings will be removed.  Mappings will not be
         re-added until apexUdpMapApplyChange is set to 'apply' for
         all transport streams.  In order for the change to persist through
         subsequent reboots or power cycles, the change must be saved via
         the apexSaveConfig parameter.

         @Config(config=yes, reboot=no)
         @Save(apexSaveConfig, value=2)
         @File(udpmap.ini, type='ini')
        "
::= { apexUdpMapConfigGeneral 1 }

apexUdpMapTsStartingIndex OBJECT-TYPE
    SYNTAX Integer32 (0..192)
    MAX-ACCESS read-write
    STATUS current
    DESCRIPTION
        "Starting transport stream index for calculating UDP Port value.
         This replaces the previous mode bits and TS offset values. The
         UDP port for a mapping is calculated as follows:
         
         Port = ((TS_Index + Start_TS_Index) << 8) | Output_Program_Number
         
         This starting TS index can be from 0 - 192 to allow any combination
         of output TS index and UDP port value. Typically the normal values
         for this starting index will be:
         
         0, 1, 64, 65, 128, 129, 192
         
         Once written, the change to this parameter will take immediate
         effect and all mappings will be removed.  Mappings will not be
         re-added until apexUdpMapApplyChange is set to 'apply' for
         all transport streams.  In order for the change to persist through
         subsequent reboots or power cycles, the change must be saved via
         the apexSaveConfig parameter.

         @Config(config=yes, reboot=no)
         @Save(apexSaveConfig, value=2)
         @File(udpmap.ini, type='ini')
        "
::= { apexUdpMapConfigGeneral 2 }

apexUdpMapFollowDtcp OBJECT-TYPE
    SYNTAX EnableDisableTYPE
    MAX-ACCESS read-write
    STATUS current
    DESCRIPTION
        "Determines how the copy protection settings (CCI, APS, and CIT) within 
         the PRK will be set.  All outputs in UDP Port Mapping mode will use  
         this setting for following input DTCP. 
           Disabled - Use CTE configured settings if output in CTE encryption mode
           Enabled - Follow input DTCP
         
         Once written, the change to this parameter will take immediate effect.
         However, in order for the change to persist through subsequent reboots
         or power cycles, the change must be saved via the apexSaveConfig parameter.

         @Config(config=yes, reboot=no)
         @Save(apexSaveConfig, value=2)
         @File(udpmap.ini, type='ini')
        "
::= { apexUdpMapConfigGeneral 3 }

apexUdpMapVirtualIpApplyChange OBJECT-TYPE
    SYNTAX ApplyDataToDeviceTYPE
    MAX-ACCESS read-write
    STATUS current
    DESCRIPTION
        "The Apply for the Virtual IP Configuration Table. This parameter
         MUST be set to 'apply' in order for any of the data in the
         apexUdpMapVirtualIpTable to take effect.  This parameter
         MUST be set LAST after all other data in the apexUdpMapVirtualIpTable
         has been configured.

         @Config(config=no, reboot=no)
        "
::= { apexUdpMapConfigGeneral 4 }

apexUdpMapAlgorithm OBJECT-TYPE
    SYNTAX INTEGER
        {
         standardMethod          (0),
         modifiedMethod10-6      (1)
        }
    MAX-ACCESS read-write
    STATUS current
    DESCRIPTION
        "Sets the Port mapping algorithm to be used for the entire chassis.
         The Standard Method uses the 8 most significant bits of the 
         UDP Port to map to a specific output TS number.  The 8 least significant
         bits are used to determine the output program number.  The 10/6 method
         uses the 10 most significant bits to determine the output TS number and 
         the 6 least significant bits for the output program number.  When 
         changing this parameter they may not be any active UDP Port mappings.
         
         This setting must be set to 10/6 when reporting UDP Port mappings via the 
         RTSP D6 interface. When reporting UDP Port Mappings, this parameter cannot
         be changed to standard method until the report UDP Port mappings is Disabled.
         
         Once written, the change to this parameter will take immediate effect.
         However, in order for the change to persist through subsequent reboots
         or power cycles, the change must be saved via the apexSaveConfig parameter.

         @Config(config=yes, reboot=no)
         @Save(apexSaveConfig, value=2)
         @File(udpmap.ini, type='ini')
        "
::= { apexUdpMapConfigGeneral 5 }
   

-- ------------------------------------------------------------------------------
--
-- apexUdpMapBlade1
--
-- apexUdpMapBlade1ApplyTable
--

apexUdpMapBlade1ApplyTable OBJECT-TYPE
    SYNTAX SEQUENCE OF ApexUdpMapBlade1ApplyEntry
    MAX-ACCESS not-accessible
    STATUS current
    DESCRIPTION
        "Table of Apply Change for the data for UDP Map Table.

         A row in this table corresponds to the same row index in the
         UDP Map table.
        "
::= { apexUdpMapBlade1 1 }

apexUdpMapBlade1ApplyEntry OBJECT-TYPE
    SYNTAX ApexUdpMapBlade1ApplyEntry
    MAX-ACCESS not-accessible
    STATUS current
    DESCRIPTION
        "UDP Map Apply Table Entry."
    INDEX { apexUdpMapBlade1ApplyOutputTsNum }
::= { apexUdpMapBlade1ApplyTable 1 }

ApexUdpMapBlade1ApplyEntry ::= SEQUENCE
    {
     apexUdpMapBlade1ApplyOutputTsNum   Integer32,
     apexUdpMapBlade1ApplyChange        ApplyDataToDeviceTYPE,
     apexUdpMapBlade1InvalidApplyText   DisplayString
    }

apexUdpMapBlade1ApplyOutputTsNum OBJECT-TYPE
    SYNTAX Integer32(1..256)
    MAX-ACCESS not-accessible
    STATUS current
    DESCRIPTION
        "The index of the Udp Map Apply Table."
::= { apexUdpMapBlade1ApplyEntry 1 }

apexUdpMapBlade1ApplyChange OBJECT-TYPE
    SYNTAX ApplyDataToDeviceTYPE
    MAX-ACCESS read-write
    STATUS current
    DESCRIPTION
        "The Apply for the row of data in the Udp Map Table.

         A row in this table corresponds to the same row index in the
         Udp Map table.

         This parameter MUST be set to 'apply' in order for any of the data
         in the Udp Map Table row to take effect in the APEX.  This
         parameter MUST be set LAST after all other data in the Udp Map
         Table row has been configured.

         @Config(config=no, reboot=no)
        "
::= { apexUdpMapBlade1ApplyEntry 2 }

apexUdpMapBlade1InvalidApplyText OBJECT-TYPE
    SYNTAX DisplayString (SIZE (0..80))
    MAX-ACCESS read-only
    STATUS current
    DESCRIPTION
        "When apexUdpMapBlade1ApplyChange is set to applyNotInProgressInvalidData
         this entry may contain a text description of what was wrong with the data.
         This entry contains the description for the most recent apply of a
         table entry that was invalid."
::= { apexUdpMapBlade1ApplyEntry 3 }


-- ------------------------------------------------------------------------------
--
-- apexUdpMapBlade1Table
--

apexUdpMapBlade1Table OBJECT-TYPE
    SYNTAX SEQUENCE OF ApexUdpMapBlade1Entry
    MAX-ACCESS not-accessible
    STATUS current
    DESCRIPTION
        "Table of data for Udp Mapping. There are
         256 rows per blade.  Each row corresponds to one QAM channel.

         Once written, the change to this table will only take immediate
         effect after apexUdpMapBlade1ApplyChange is set to 'apply'.
         However, in order for the change to persist through subsequent
         reboots or power cycles, the change must be saved via apexSaveConfig.

         @Config(config=yes, reboot=no)
         @Commit(param=apexUdpMapBlade1ApplyChange, value=2)
         @Save(apexSaveConfig, value=2)
         @File(udpmap.ini, type='ini')
        "
::= { apexUdpMapBlade1 2 }

apexUdpMapBlade1Entry OBJECT-TYPE
    SYNTAX ApexUdpMapBlade1Entry
    MAX-ACCESS not-accessible
    STATUS current
    DESCRIPTION
        "Udp Mapping Table Entry."
    INDEX { apexUdpMapBlade1OutputTsNum }
::= { apexUdpMapBlade1Table 1 }

ApexUdpMapBlade1Entry ::= SEQUENCE
    {
     apexUdpMapBlade1OutputTsNum        Integer32,
     apexUdpMapBlade1StartProgNum       Integer32,
     apexUdpMapBlade1NumberProgs        Integer32,
     apexUdpMapBlade1VirtualIpIndex     Integer32,
     apexUdpMapBlade1ConfOutputTsNum    Integer32,
     apexUdpMapBlade1ConfInputInterface Integer32
    }

apexUdpMapBlade1OutputTsNum OBJECT-TYPE
    SYNTAX Integer32(1..256)
    MAX-ACCESS not-accessible
    STATUS current
    DESCRIPTION
        "Index of Udp Mapping Table.
        "
::= { apexUdpMapBlade1Entry 1 }

apexUdpMapBlade1StartProgNum OBJECT-TYPE
    SYNTAX Integer32(1..255)
    MAX-ACCESS read-write
    STATUS current
    DESCRIPTION
        "Indicates the first program number in a sequential range of programs
         that are to be routed to the same output transport stream.
        "
::= { apexUdpMapBlade1Entry 2 }

apexUdpMapBlade1NumberProgs OBJECT-TYPE
    SYNTAX Integer32(0..200)
    MAX-ACCESS read-write
    STATUS current
    DESCRIPTION
        "Indicates the number of programs that are to be mapped to the output
         transport stream.  One UDP port is opened for each program mapped to
         the output transport stream.
        "
::= { apexUdpMapBlade1Entry 3 }

apexUdpMapBlade1VirtualIpIndex OBJECT-TYPE
    SYNTAX Integer32(0..32)
    MAX-ACCESS read-write
    STATUS current
    DESCRIPTION
        "The index of the Virtual IP Table associated with this output TS. 
         This value is only used when configured for the 10-6 Modified UDP 
         Mapping Algorithm.  
         
         Range:
            '0'              = Not Applicable
            Virtual IP Index = 1-32 (valid IP must already be configured)
            
         The Virtual IP can only be selected when a GigE Input Interface index
         is not already selected. UDP port mappings will be assigned to either the
         configured Virtual IP or Physical GigE interface, but not both.
         
         When using a GigE Input Interface for UDP Port Mappings, this setting must be 
         set to 0. When Reporting UDP Port Mappings via RTSP D6, then the IP address is
         automatically allocated, and neither a Virtual IP or GigE interface can be
         selected. Both must be set to 0 in this case.
        "
::= { apexUdpMapBlade1Entry 4 }

apexUdpMapBlade1ConfOutputTsNum OBJECT-TYPE
    SYNTAX Integer32(0..1023)
    MAX-ACCESS read-write
    STATUS current
    DESCRIPTION
        "The configured output TS number for this output TS.  This value 
         is only used when configured for the 10-6 Modified UDP Mapping
         Algorithm.  Based on the 10-6 UDP Mapping Algorithm, this value 
         is used to calculate the UDP Port opened on the configured virtual 
         IP.  The upper 10 bits of the UDP port are based on this number
         and the lower 6 bits are based on the configured output program number.
        "
::= { apexUdpMapBlade1Entry 5 }

apexUdpMapBlade1ConfInputInterface OBJECT-TYPE
    SYNTAX Integer32(0..12)
    MAX-ACCESS read-write
    STATUS current
    DESCRIPTION
        "The configured GigE interface port number for this output TS.  This value 
         is only used when configured for the 10-6 Modified UDP Mapping
         Algorithm. The GigE interface can only be selected when a Virtual IP index
         is not already selected. UDP port mappings will be assigned to either the
         configured Virtual IP or Physical GigE interface, but not both.
         
         When using a Virtual IP for UDP Port Mappings, this setting must be set to
         0. When Reporting UDP Port Mappings via RTSP D6, then the IP address is
         automatically allocated, and neither a Virtual IP or GigE interface can be
         selected. Both must be set to 0 in this case.
         
         Range:
            '0'             = Not Applicable
            Input Interface = 1-12 (only interfaces in primary mode can be selected)
           
        "
::= { apexUdpMapBlade1Entry 6 }


-- ------------------------------------------------------------------------------
--
-- apexUdpMapBlade1MulticastTable
--

apexUdpMapBlade1MulticastTable OBJECT-TYPE
    SYNTAX SEQUENCE OF ApexUdpMapBlade1MulticastEntry
    MAX-ACCESS not-accessible
    STATUS current
    DESCRIPTION
        "Table of data for UDP Map Multicast. Each entry in
         this table identifies a Gigabit Ethernet input stream that is
         used for multicast UDP Port Mapping.
         
         Once written, the change to this table will only take immediate
         effect after apexUdpMapBlade1MulticastApplyChange is set to 'apply'.
         However, in order for the change to persist through subsequent
         reboots or power cycles, the change must be saved via apexSaveConfig.

         @Config(config=yes, reboot=no)
         @Commit(param=apexUdpMapBlade1MulticastApplyChange, value=2)
         @Save(apexSaveConfig, value=2)
         @File(udpmap.ini, type='ini')
        "
::= { apexUdpMapBlade1 3 }

apexUdpMapBlade1MulticastEntry OBJECT-TYPE
    SYNTAX ApexUdpMapBlade1MulticastEntry
    MAX-ACCESS not-accessible
    STATUS current
    DESCRIPTION
        "UDP Map Multicast Table Entry."
    INDEX { apexUdpMapBlade1MulticastIndex }
::= { apexUdpMapBlade1MulticastTable 1 }

ApexUdpMapBlade1MulticastEntry ::= SEQUENCE
    {
     apexUdpMapBlade1MulticastIndex           Integer32,
     apexUdpMapBlade1MulticastEnable          EnableDisableTYPE,
     apexUdpMapBlade1MulticastVirtualIpIndex  Integer32,
     apexUdpMapBlade1MulticastUdp             Integer32,
     apexUdpMapBlade1MulticastMcastIp         IpAddress,
     apexUdpMapBlade1MulticastSourceIp        IpAddress
    }

apexUdpMapBlade1MulticastIndex OBJECT-TYPE
    SYNTAX Integer32(1..256)
    MAX-ACCESS not-accessible
    STATUS current
    DESCRIPTION
        "Index of UDP Map Multicast Stream Table."
::= { apexUdpMapBlade1MulticastEntry 1 }

apexUdpMapBlade1MulticastEnable OBJECT-TYPE
    SYNTAX EnableDisableTYPE
    MAX-ACCESS read-write
    STATUS current
    DESCRIPTION
        "Indicates whether this UDP Map Multicast entry is enabled or disabled.
        "
::= { apexUdpMapBlade1MulticastEntry 2 }

apexUdpMapBlade1MulticastVirtualIpIndex OBJECT-TYPE
    SYNTAX Integer32(0..32)
    MAX-ACCESS read-write
    STATUS current
    DESCRIPTION
        "Index of the Virtual IP Table that corresponds to this entry.

         Range:
            '0'              = Not Applicable
            Virtual IP Index = 1-32
        "
::= { apexUdpMapBlade1MulticastEntry 3 }

apexUdpMapBlade1MulticastUdp OBJECT-TYPE
    SYNTAX Integer32(0..65535)
    MAX-ACCESS read-write
    STATUS current
    DESCRIPTION
        "GBE Input UDP Port.

         Range: 0-65535
        "
::= { apexUdpMapBlade1MulticastEntry 4 }

apexUdpMapBlade1MulticastMcastIp OBJECT-TYPE
    SYNTAX IpAddress
    MAX-ACCESS read-write
    STATUS current
    DESCRIPTION
        "The Multicast receive IP address.
         An IP address of 0.0.0.0 indicates singlecast only.

         Multicast IP addresses 224.0.0.0 to 224.0.0.255 are reserved.
        "
::= { apexUdpMapBlade1MulticastEntry 5 }

apexUdpMapBlade1MulticastSourceIp OBJECT-TYPE
    SYNTAX IpAddress
    MAX-ACCESS read-write
    STATUS current
    DESCRIPTION
        "This is the IP address of the source device. This field is only
         used when a multicast IP address is also specified.
        "
::= { apexUdpMapBlade1MulticastEntry 6 }


-- ------------------------------------------------------------------------------
--
-- apexUdpMapBlade1MulticastApplyTable
--

apexUdpMapBlade1MulticastApplyTable OBJECT-TYPE
    SYNTAX SEQUENCE OF ApexUdpMapBlade1MulticastApplyEntry
    MAX-ACCESS not-accessible
    STATUS current
    DESCRIPTION
        "Table of Apply Change for the UDP Map Multicast Table.

         A row in this table corresponds to the same row index in the
         UDP Map Multicast Table (apexUdpMapBlade1MulticastTable).
        "
::= { apexUdpMapBlade1 4 }

apexUdpMapBlade1MulticastApplyEntry OBJECT-TYPE
    SYNTAX ApexUdpMapBlade1MulticastApplyEntry
    MAX-ACCESS not-accessible
    STATUS current
    DESCRIPTION
        "UDP Map Multicast Apply Table Entry."
    INDEX { apexUdpMapBlade1MulticastApplyIndex }
::= { apexUdpMapBlade1MulticastApplyTable 1 }

ApexUdpMapBlade1MulticastApplyEntry ::= SEQUENCE
    {
     apexUdpMapBlade1MulticastApplyIndex  Integer32,
     apexUdpMapBlade1MulticastApplyChange ApplyDataToDeviceTYPE
    }

apexUdpMapBlade1MulticastApplyIndex OBJECT-TYPE
    SYNTAX Integer32(1..256)
    MAX-ACCESS not-accessible
    STATUS current
    DESCRIPTION
        "The index of the UDP Map Multicast Table."
::= { apexUdpMapBlade1MulticastApplyEntry 1 }

apexUdpMapBlade1MulticastApplyChange OBJECT-TYPE
    SYNTAX ApplyDataToDeviceTYPE
    MAX-ACCESS read-write
    STATUS current
    DESCRIPTION
        "The Apply for the row of data in the UDP Map Multicast Table.

         A row in this table corresponds to the same row index in the
         UDP Map Multicast Table.

         This parameter MUST be set to 'apply' in order for any of the data
         in the UDP Map Multicast Table row to take effect in the APEX.  This
         parameter MUST be set LAST after all other data in the UDP Map Multicast 
         Table row has been configured.

         @Config(config=no, reboot=no)
        "
::= { apexUdpMapBlade1MulticastApplyEntry 2 }


-- ------------------------------------------------------------------------------
--
-- apexUdpMapBlade2
--
-- apexUdpMapBlade2ApplyTable
--

apexUdpMapBlade2ApplyTable OBJECT-TYPE
    SYNTAX SEQUENCE OF ApexUdpMapBlade2ApplyEntry
    MAX-ACCESS not-accessible
    STATUS current
    DESCRIPTION
        "Table of Apply Change for the data for UDP Map Table.

         A row in this table corresponds to the same row index in the
         UDP Map table.
        "
::= { apexUdpMapBlade2 1 }

apexUdpMapBlade2ApplyEntry OBJECT-TYPE
    SYNTAX ApexUdpMapBlade2ApplyEntry
    MAX-ACCESS not-accessible
    STATUS current
    DESCRIPTION
        "UDP Map Apply Table Entry."
    INDEX { apexUdpMapBlade2ApplyOutputTsNum }
::= { apexUdpMapBlade2ApplyTable 1 }

ApexUdpMapBlade2ApplyEntry ::= SEQUENCE
    {
     apexUdpMapBlade2ApplyOutputTsNum   Integer32,
     apexUdpMapBlade2ApplyChange        ApplyDataToDeviceTYPE,
     apexUdpMapBlade2InvalidApplyText   DisplayString
    }

apexUdpMapBlade2ApplyOutputTsNum OBJECT-TYPE
    SYNTAX Integer32(1..256)
    MAX-ACCESS not-accessible
    STATUS current
    DESCRIPTION
        "The index of the Udp Map Apply Table."
::= { apexUdpMapBlade2ApplyEntry 1 }

apexUdpMapBlade2ApplyChange OBJECT-TYPE
    SYNTAX ApplyDataToDeviceTYPE
    MAX-ACCESS read-write
    STATUS current
    DESCRIPTION
        "The Apply for the row of data in the Udp Map Table.

         A row in this table corresponds to the same row index in the
         Udp Map table.

         This parameter MUST be set to 'apply' in order for any of the data
         in the Udp Map Table row to take effect in the APEX.  This
         parameter MUST be set LAST after all other data in the Udp Map
         Table row has been configured.

         @Config(config=no, reboot=no)
        "
::= { apexUdpMapBlade2ApplyEntry 2 }

apexUdpMapBlade2InvalidApplyText OBJECT-TYPE
    SYNTAX DisplayString (SIZE (0..80))
    MAX-ACCESS read-only
    STATUS current
    DESCRIPTION
        "When apexUdpMapBlade2ApplyChange is set to applyNotInProgressInvalidData
         this entry may contain a text description of what was wrong with the data.
         This entry contains the description for the most recent apply of a
         table entry that was invalid."
::= { apexUdpMapBlade2ApplyEntry 3 }


-- ------------------------------------------------------------------------------
--
-- apexUdpMapBlade2Table
--

apexUdpMapBlade2Table OBJECT-TYPE
    SYNTAX SEQUENCE OF ApexUdpMapBlade2Entry
    MAX-ACCESS not-accessible
    STATUS current
    DESCRIPTION
        "Table of data for Udp Mapping. There are
         256 rows per blade.  Each row corresponds to one QAM channel.

         Once written, the change to this table will only take immediate
         effect after apexUdpMapBlade2ApplyChange is set to 'apply'.
         However, in order for the change to persist through subsequent
         reboots or power cycles, the change must be saved via apexSaveConfig.

         @Config(config=yes, reboot=no)
         @Commit(param=apexUdpMapBlade2ApplyChange, value=2)
         @Save(apexSaveConfig, value=2)
         @File(udpmap.ini, type='ini')
        "
::= { apexUdpMapBlade2 2 }

apexUdpMapBlade2Entry OBJECT-TYPE
    SYNTAX ApexUdpMapBlade2Entry
    MAX-ACCESS not-accessible
    STATUS current
    DESCRIPTION
        "Udp Mapping Table Entry."
    INDEX { apexUdpMapBlade2OutputTsNum }
::= { apexUdpMapBlade2Table 1 }

ApexUdpMapBlade2Entry ::= SEQUENCE
    {
     apexUdpMapBlade2OutputTsNum        Integer32,
     apexUdpMapBlade2StartProgNum       Integer32,
     apexUdpMapBlade2NumberProgs        Integer32,
     apexUdpMapBlade2VirtualIpIndex     Integer32,
     apexUdpMapBlade2ConfOutputTsNum    Integer32,
     apexUdpMapBlade2ConfInputInterface Integer32
    }

apexUdpMapBlade2OutputTsNum OBJECT-TYPE
    SYNTAX Integer32(1..256)
    MAX-ACCESS not-accessible
    STATUS current
    DESCRIPTION
        "Index of Udp Mapping Table.
        "
::= { apexUdpMapBlade2Entry 1 }

apexUdpMapBlade2StartProgNum OBJECT-TYPE
    SYNTAX Integer32(1..255)
    MAX-ACCESS read-write
    STATUS current
    DESCRIPTION
        "Indicates the first program number in a sequential range of programs
         that are to be routed to the same output transport stream.
        "
::= { apexUdpMapBlade2Entry 2 }

apexUdpMapBlade2NumberProgs OBJECT-TYPE
    SYNTAX Integer32(0..200)
    MAX-ACCESS read-write
    STATUS current
    DESCRIPTION
        "Indicates the number of programs that are to be mapped to the output
         transport stream.  One UDP port is opened for each program mapped to
         the output transport stream.
        "
::= { apexUdpMapBlade2Entry 3 }

apexUdpMapBlade2VirtualIpIndex OBJECT-TYPE
    SYNTAX Integer32(0..32)
    MAX-ACCESS read-write
    STATUS current
    DESCRIPTION
        "The index of the Virtual IP Table associated with this output TS. 
         This value is only used when configured for the 10-6 Modified UDP 
         Mapping Algorithm.  
         
         Range:
            '0'              = Not Applicable
            Virtual IP Index = 1-32 (valid IP must already be configured)
            
         The Virtual IP can only be selected when a GigE Input Interface index
         is not already selected. UDP port mappings will be assigned to either the
         configured Virtual IP or Physical GigE interface, but not both.
         
         When using a GigE Input Interface for UDP Port Mappings, this setting must be 
         set to 0. When Reporting UDP Port Mappings via RTSP D6, then the IP address is
         automatically allocated, and neither a Virtual IP or GigE interface can be
         selected. Both must be set to 0 in this case.
        "
::= { apexUdpMapBlade2Entry 4 }

apexUdpMapBlade2ConfOutputTsNum OBJECT-TYPE
    SYNTAX Integer32(0..1023)
    MAX-ACCESS read-write
    STATUS current
    DESCRIPTION
        "The configured output TS number for this output TS.  This value 
         is only used when configured for the 10-6 Modified UDP Mapping
         Algorithm.  Based on the 10-6 UDP Mapping Algorithm, this value 
         is used to calculate the UDP Port opened on the configured virtual 
         IP.  The upper 10 bits of the UDP port are based on this number
         and the lower 6 bits are based on the configured output program number.
        "
::= { apexUdpMapBlade2Entry 5 }

apexUdpMapBlade2ConfInputInterface OBJECT-TYPE
    SYNTAX Integer32(0..12)
    MAX-ACCESS read-write
    STATUS current
    DESCRIPTION
        "The configured GigE interface port number for this output TS.  This value 
         is only used when configured for the 10-6 Modified UDP Mapping
         Algorithm. The GigE interface can only be selected when a Virtual IP index
         is not already selected. UDP port mappings will be assigned to either the
         configured Virtual IP or Physical GigE interface, but not both.
         
         When using a Virtual IP for UDP Port Mappings, this setting must be set to
         0. When Reporting UDP Port Mappings via RTSP D6, then the IP address is
         automatically allocated, and neither a Virtual IP or GigE interface can be
         selected. Both must be set to 0 in this case.
         
         Range:
            '0'             = Not Applicable
            Input Interface = 1-12 (only interfaces in primary mode can be selected)
           
        "
::= { apexUdpMapBlade2Entry 6 }


-- ------------------------------------------------------------------------------
--
-- apexUdpMapBlade2MulticastTable
--

apexUdpMapBlade2MulticastTable OBJECT-TYPE
    SYNTAX SEQUENCE OF ApexUdpMapBlade2MulticastEntry
    MAX-ACCESS not-accessible
    STATUS current
    DESCRIPTION
        "Table of data for UDP Map Multicast. Each entry in
         this table identifies a Gigabit Ethernet input stream that is
         used for multicast UDP Port Mapping.
         
         Once written, the change to this table will only take immediate
         effect after apexUdpMapBlade2MulticastApplyChange is set to 'apply'.
         However, in order for the change to persist through subsequent
         reboots or power cycles, the change must be saved via apexSaveConfig.

         @Config(config=yes, reboot=no)
         @Commit(param=apexUdpMapBlade2MulticastApplyChange, value=2)
         @Save(apexSaveConfig, value=2)
         @File(udpmap.ini, type='ini')
        "
::= { apexUdpMapBlade2 3 }

apexUdpMapBlade2MulticastEntry OBJECT-TYPE
    SYNTAX ApexUdpMapBlade2MulticastEntry
    MAX-ACCESS not-accessible
    STATUS current
    DESCRIPTION
        "UDP Map Multicast Table Entry."
    INDEX { apexUdpMapBlade2MulticastIndex }
::= { apexUdpMapBlade2MulticastTable 1 }

ApexUdpMapBlade2MulticastEntry ::= SEQUENCE
    {
     apexUdpMapBlade2MulticastIndex           Integer32,
     apexUdpMapBlade2MulticastEnable          EnableDisableTYPE,
     apexUdpMapBlade2MulticastVirtualIpIndex  Integer32,
     apexUdpMapBlade2MulticastUdp             Integer32,
     apexUdpMapBlade2MulticastMcastIp         IpAddress,
     apexUdpMapBlade2MulticastSourceIp        IpAddress
    }

apexUdpMapBlade2MulticastIndex OBJECT-TYPE
    SYNTAX Integer32(1..256)
    MAX-ACCESS not-accessible
    STATUS current
    DESCRIPTION
        "Index of UDP Map Multicast Stream Table."
::= { apexUdpMapBlade2MulticastEntry 1 }

apexUdpMapBlade2MulticastEnable OBJECT-TYPE
    SYNTAX EnableDisableTYPE
    MAX-ACCESS read-write
    STATUS current
    DESCRIPTION
        "Indicates whether this UDP Map Multicast entry is enabled or disabled.
        "
::= { apexUdpMapBlade2MulticastEntry 2 }

apexUdpMapBlade2MulticastVirtualIpIndex OBJECT-TYPE
    SYNTAX Integer32(0..32)
    MAX-ACCESS read-write
    STATUS current
    DESCRIPTION
        "Index of the Virtual IP Table that corresponds to this entry.

         Range:
            '0'              = Not Applicable
            Virtual IP Index = 1-32
        "
::= { apexUdpMapBlade2MulticastEntry 3 }

apexUdpMapBlade2MulticastUdp OBJECT-TYPE
    SYNTAX Integer32(0..65535)
    MAX-ACCESS read-write
    STATUS current
    DESCRIPTION
        "GBE Input UDP Port.

         Range: 0-65535
        "
::= { apexUdpMapBlade2MulticastEntry 4 }

apexUdpMapBlade2MulticastMcastIp OBJECT-TYPE
    SYNTAX IpAddress
    MAX-ACCESS read-write
    STATUS current
    DESCRIPTION
        "The Multicast receive IP address.
         An IP address of 0.0.0.0 indicates singlecast only.

         Multicast IP addresses 224.0.0.0 to 224.0.0.255 are reserved.
        "
::= { apexUdpMapBlade2MulticastEntry 5 }

apexUdpMapBlade2MulticastSourceIp OBJECT-TYPE
    SYNTAX IpAddress
    MAX-ACCESS read-write
    STATUS current
    DESCRIPTION
        "This is the IP address of the source device. This field is only
         used when a multicast IP address is also specified.
        "
::= { apexUdpMapBlade2MulticastEntry 6 }


-- ------------------------------------------------------------------------------
--
-- apexUdpMapBlade2MulticastApplyTable
--

apexUdpMapBlade2MulticastApplyTable OBJECT-TYPE
    SYNTAX SEQUENCE OF ApexUdpMapBlade2MulticastApplyEntry
    MAX-ACCESS not-accessible
    STATUS current
    DESCRIPTION
        "Table of Apply Change for the UDP Map Multicast Table.

         A row in this table corresponds to the same row index in the
         UDP Map Multicast Table (apexUdpMapBlade2MulticastTable).
        "
::= { apexUdpMapBlade2 4 }

apexUdpMapBlade2MulticastApplyEntry OBJECT-TYPE
    SYNTAX ApexUdpMapBlade2MulticastApplyEntry
    MAX-ACCESS not-accessible
    STATUS current
    DESCRIPTION
        "UDP Map Multicast Apply Table Entry."
    INDEX { apexUdpMapBlade2MulticastApplyIndex }
::= { apexUdpMapBlade2MulticastApplyTable 1 }

ApexUdpMapBlade2MulticastApplyEntry ::= SEQUENCE
    {
     apexUdpMapBlade2MulticastApplyIndex  Integer32,
     apexUdpMapBlade2MulticastApplyChange ApplyDataToDeviceTYPE
    }

apexUdpMapBlade2MulticastApplyIndex OBJECT-TYPE
    SYNTAX Integer32(1..256)
    MAX-ACCESS not-accessible
    STATUS current
    DESCRIPTION
        "The index of the UDP Map Multicast Table."
::= { apexUdpMapBlade2MulticastApplyEntry 1 }

apexUdpMapBlade2MulticastApplyChange OBJECT-TYPE
    SYNTAX ApplyDataToDeviceTYPE
    MAX-ACCESS read-write
    STATUS current
    DESCRIPTION
        "The Apply for the row of data in the UDP Map Multicast Table.

         A row in this table corresponds to the same row index in the
         UDP Map Multicast Table.

         This parameter MUST be set to 'apply' in order for any of the data
         in the UDP Map Multicast Table row to take effect in the APEX.  This
         parameter MUST be set LAST after all other data in the UDP Map Multicast 
         Table row has been configured.

         @Config(config=no, reboot=no)
        "
::= { apexUdpMapBlade2MulticastApplyEntry 2 }


-- ------------------------------------------------------------------------------
--
-- apexUdpMapBlade3
--
-- apexUdpMapBlade3ApplyTable
--

apexUdpMapBlade3ApplyTable OBJECT-TYPE
    SYNTAX SEQUENCE OF ApexUdpMapBlade3ApplyEntry
    MAX-ACCESS not-accessible
    STATUS current
    DESCRIPTION
        "Table of Apply Change for the data for UDP Map Table.

         A row in this table corresponds to the same row index in the
         UDP Map table.
        "
::= { apexUdpMapBlade3 1 }

apexUdpMapBlade3ApplyEntry OBJECT-TYPE
    SYNTAX ApexUdpMapBlade3ApplyEntry
    MAX-ACCESS not-accessible
    STATUS current
    DESCRIPTION
        "UDP Map Apply Table Entry."
    INDEX { apexUdpMapBlade3ApplyOutputTsNum }
::= { apexUdpMapBlade3ApplyTable 1 }

ApexUdpMapBlade3ApplyEntry ::= SEQUENCE
    {
     apexUdpMapBlade3ApplyOutputTsNum   Integer32,
     apexUdpMapBlade3ApplyChange        ApplyDataToDeviceTYPE,
     apexUdpMapBlade3InvalidApplyText   DisplayString
    }

apexUdpMapBlade3ApplyOutputTsNum OBJECT-TYPE
    SYNTAX Integer32(1..256)
    MAX-ACCESS not-accessible
    STATUS current
    DESCRIPTION
        "The index of the Udp Map Apply Table."
::= { apexUdpMapBlade3ApplyEntry 1 }

apexUdpMapBlade3ApplyChange OBJECT-TYPE
    SYNTAX ApplyDataToDeviceTYPE
    MAX-ACCESS read-write
    STATUS current
    DESCRIPTION
        "The Apply for the row of data in the Udp Map Table.

         A row in this table corresponds to the same row index in the
         Udp Map table.

         This parameter MUST be set to 'apply' in order for any of the data
         in the Udp Map Table row to take effect in the APEX.  This
         parameter MUST be set LAST after all other data in the Udp Map
         Table row has been configured.

         @Config(config=no, reboot=no)
        "
::= { apexUdpMapBlade3ApplyEntry 2 }

apexUdpMapBlade3InvalidApplyText OBJECT-TYPE
    SYNTAX DisplayString (SIZE (0..80))
    MAX-ACCESS read-only
    STATUS current
    DESCRIPTION
        "When apexUdpMapBlade3ApplyChange is set to applyNotInProgressInvalidData
         this entry may contain a text description of what was wrong with the data.
         This entry contains the description for the most recent apply of a
         table entry that was invalid."
::= { apexUdpMapBlade3ApplyEntry 3 }


-- ------------------------------------------------------------------------------
--
-- apexUdpMapBlade3Table
--

apexUdpMapBlade3Table OBJECT-TYPE
    SYNTAX SEQUENCE OF ApexUdpMapBlade3Entry
    MAX-ACCESS not-accessible
    STATUS current
    DESCRIPTION
        "Table of data for Udp Mapping. There are
         256 rows per blade.  Each row corresponds to one QAM channel.

         Once written, the change to this table will only take immediate
         effect after apexUdpMapBlade3ApplyChange is set to 'apply'.
         However, in order for the change to persist through subsequent
         reboots or power cycles, the change must be saved via apexSaveConfig.

         @Config(config=yes, reboot=no)
         @Commit(param=apexUdpMapBlade3ApplyChange, value=2)
         @Save(apexSaveConfig, value=2)
         @File(udpmap.ini, type='ini')
        "
::= { apexUdpMapBlade3 2 }

apexUdpMapBlade3Entry OBJECT-TYPE
    SYNTAX ApexUdpMapBlade3Entry
    MAX-ACCESS not-accessible
    STATUS current
    DESCRIPTION
        "Udp Mapping Table Entry."
    INDEX { apexUdpMapBlade3OutputTsNum }
::= { apexUdpMapBlade3Table 1 }

ApexUdpMapBlade3Entry ::= SEQUENCE
    {
     apexUdpMapBlade3OutputTsNum        Integer32,
     apexUdpMapBlade3StartProgNum       Integer32,
     apexUdpMapBlade3NumberProgs        Integer32,
     apexUdpMapBlade3VirtualIpIndex     Integer32,
     apexUdpMapBlade3ConfOutputTsNum    Integer32,
     apexUdpMapBlade3ConfInputInterface Integer32
    }

apexUdpMapBlade3OutputTsNum OBJECT-TYPE
    SYNTAX Integer32(1..256)
    MAX-ACCESS not-accessible
    STATUS current
    DESCRIPTION
        "Index of Udp Mapping Table.
        "
::= { apexUdpMapBlade3Entry 1 }

apexUdpMapBlade3StartProgNum OBJECT-TYPE
    SYNTAX Integer32(1..255)
    MAX-ACCESS read-write
    STATUS current
    DESCRIPTION
        "Indicates the first program number in a sequential range of programs
         that are to be routed to the same output transport stream.
        "
::= { apexUdpMapBlade3Entry 2 }

apexUdpMapBlade3NumberProgs OBJECT-TYPE
    SYNTAX Integer32(0..200)
    MAX-ACCESS read-write
    STATUS current
    DESCRIPTION
        "Indicates the number of programs that are to be mapped to the output
         transport stream.  One UDP port is opened for each program mapped to
         the output transport stream.
        "
::= { apexUdpMapBlade3Entry 3 }

apexUdpMapBlade3VirtualIpIndex OBJECT-TYPE
    SYNTAX Integer32(0..32)
    MAX-ACCESS read-write
    STATUS current
    DESCRIPTION
        "The index of the Virtual IP Table associated with this output TS. 
         This value is only used when configured for the 10-6 Modified UDP 
         Mapping Algorithm.  
         
         Range:
            '0'              = Not Applicable
            Virtual IP Index = 1-32 (valid IP must already be configured)
            
         The Virtual IP can only be selected when a GigE Input Interface index
         is not already selected. UDP port mappings will be assigned to either the
         configured Virtual IP or Physical GigE interface, but not both.
         
         When using a GigE Input Interface for UDP Port Mappings, this setting must be 
         set to 0. When Reporting UDP Port Mappings via RTSP D6, then the IP address is
         automatically allocated, and neither a Virtual IP or GigE interface can be
         selected. Both must be set to 0 in this case.
        "
::= { apexUdpMapBlade3Entry 4 }

apexUdpMapBlade3ConfOutputTsNum OBJECT-TYPE
    SYNTAX Integer32(0..1023)
    MAX-ACCESS read-write
    STATUS current
    DESCRIPTION
        "The configured output TS number for this output TS.  This value 
         is only used when configured for the 10-6 Modified UDP Mapping
         Algorithm.  Based on the 10-6 UDP Mapping Algorithm, this value 
         is used to calculate the UDP Port opened on the configured virtual 
         IP.  The upper 10 bits of the UDP port are based on this number
         and the lower 6 bits are based on the configured output program number.
        "
::= { apexUdpMapBlade3Entry 5 }

apexUdpMapBlade3ConfInputInterface OBJECT-TYPE
    SYNTAX Integer32(0..12)
    MAX-ACCESS read-write
    STATUS current
    DESCRIPTION
        "The configured GigE interface port number for this output TS.  This value 
         is only used when configured for the 10-6 Modified UDP Mapping
         Algorithm. The GigE interface can only be selected when a Virtual IP index
         is not already selected. UDP port mappings will be assigned to either the
         configured Virtual IP or Physical GigE interface, but not both.
         
         When using a Virtual IP for UDP Port Mappings, this setting must be set to
         0. When Reporting UDP Port Mappings via RTSP D6, then the IP address is
         automatically allocated, and neither a Virtual IP or GigE interface can be
         selected. Both must be set to 0 in this case.
         
         Range:
            '0'             = Not Applicable
            Input Interface = 1-12 (only interfaces in primary mode can be selected)
           
        "
::= { apexUdpMapBlade3Entry 6 }


-- ------------------------------------------------------------------------------
--
-- apexUdpMapBlade3MulticastTable
--

apexUdpMapBlade3MulticastTable OBJECT-TYPE
    SYNTAX SEQUENCE OF ApexUdpMapBlade3MulticastEntry
    MAX-ACCESS not-accessible
    STATUS current
    DESCRIPTION
        "Table of data for UDP Map Multicast. Each entry in
         this table identifies a Gigabit Ethernet input stream that is
         used for multicast UDP Port Mapping.
         
         Once written, the change to this table will only take immediate
         effect after apexUdpMapBlade3MulticastApplyChange is set to 'apply'.
         However, in order for the change to persist through subsequent
         reboots or power cycles, the change must be saved via apexSaveConfig.

         @Config(config=yes, reboot=no)
         @Commit(param=apexUdpMapBlade3MulticastApplyChange, value=2)
         @Save(apexSaveConfig, value=2)
         @File(udpmap.ini, type='ini')
        "
::= { apexUdpMapBlade3 3 }

apexUdpMapBlade3MulticastEntry OBJECT-TYPE
    SYNTAX ApexUdpMapBlade3MulticastEntry
    MAX-ACCESS not-accessible
    STATUS current
    DESCRIPTION
        "UDP Map Multicast Table Entry."
    INDEX { apexUdpMapBlade3MulticastIndex }
::= { apexUdpMapBlade3MulticastTable 1 }

ApexUdpMapBlade3MulticastEntry ::= SEQUENCE
    {
     apexUdpMapBlade3MulticastIndex           Integer32,
     apexUdpMapBlade3MulticastEnable          EnableDisableTYPE,
     apexUdpMapBlade3MulticastVirtualIpIndex  Integer32,
     apexUdpMapBlade3MulticastUdp             Integer32,
     apexUdpMapBlade3MulticastMcastIp         IpAddress,
     apexUdpMapBlade3MulticastSourceIp        IpAddress
    }

apexUdpMapBlade3MulticastIndex OBJECT-TYPE
    SYNTAX Integer32(1..256)
    MAX-ACCESS not-accessible
    STATUS current
    DESCRIPTION
        "Index of UDP Map Multicast Stream Table."
::= { apexUdpMapBlade3MulticastEntry 1 }

apexUdpMapBlade3MulticastEnable OBJECT-TYPE
    SYNTAX EnableDisableTYPE
    MAX-ACCESS read-write
    STATUS current
    DESCRIPTION
        "Indicates whether this UDP Map Multicast entry is enabled or disabled.
        "
::= { apexUdpMapBlade3MulticastEntry 2 }

apexUdpMapBlade3MulticastVirtualIpIndex OBJECT-TYPE
    SYNTAX Integer32(0..32)
    MAX-ACCESS read-write
    STATUS current
    DESCRIPTION
        "Index of the Virtual IP Table that corresponds to this entry.

         Range:
            '0'              = Not Applicable
            Virtual IP Index = 1-32
        "
::= { apexUdpMapBlade3MulticastEntry 3 }

apexUdpMapBlade3MulticastUdp OBJECT-TYPE
    SYNTAX Integer32(0..65535)
    MAX-ACCESS read-write
    STATUS current
    DESCRIPTION
        "GBE Input UDP Port.

         Range: 0-65535
        "
::= { apexUdpMapBlade3MulticastEntry 4 }

apexUdpMapBlade3MulticastMcastIp OBJECT-TYPE
    SYNTAX IpAddress
    MAX-ACCESS read-write
    STATUS current
    DESCRIPTION
        "The Multicast receive IP address.
         An IP address of 0.0.0.0 indicates singlecast only.

         Multicast IP addresses 224.0.0.0 to 224.0.0.255 are reserved.
        "
::= { apexUdpMapBlade3MulticastEntry 5 }

apexUdpMapBlade3MulticastSourceIp OBJECT-TYPE
    SYNTAX IpAddress
    MAX-ACCESS read-write
    STATUS current
    DESCRIPTION
        "This is the IP address of the source device. This field is only
         used when a multicast IP address is also specified.
        "
::= { apexUdpMapBlade3MulticastEntry 6 }


-- ------------------------------------------------------------------------------
--
-- apexUdpMapBlade3MulticastApplyTable
--

apexUdpMapBlade3MulticastApplyTable OBJECT-TYPE
    SYNTAX SEQUENCE OF ApexUdpMapBlade3MulticastApplyEntry
    MAX-ACCESS not-accessible
    STATUS current
    DESCRIPTION
        "Table of Apply Change for the UDP Map Multicast Table.

         A row in this table corresponds to the same row index in the
         UDP Map Multicast Table (apexUdpMapBlade3MulticastTable).
        "
::= { apexUdpMapBlade3 4 }

apexUdpMapBlade3MulticastApplyEntry OBJECT-TYPE
    SYNTAX ApexUdpMapBlade3MulticastApplyEntry
    MAX-ACCESS not-accessible
    STATUS current
    DESCRIPTION
        "UDP Map Multicast Apply Table Entry."
    INDEX { apexUdpMapBlade3MulticastApplyIndex }
::= { apexUdpMapBlade3MulticastApplyTable 1 }

ApexUdpMapBlade3MulticastApplyEntry ::= SEQUENCE
    {
     apexUdpMapBlade3MulticastApplyIndex  Integer32,
     apexUdpMapBlade3MulticastApplyChange ApplyDataToDeviceTYPE
    }

apexUdpMapBlade3MulticastApplyIndex OBJECT-TYPE
    SYNTAX Integer32(1..256)
    MAX-ACCESS not-accessible
    STATUS current
    DESCRIPTION
        "The index of the UDP Map Multicast Table."
::= { apexUdpMapBlade3MulticastApplyEntry 1 }

apexUdpMapBlade3MulticastApplyChange OBJECT-TYPE
    SYNTAX ApplyDataToDeviceTYPE
    MAX-ACCESS read-write
    STATUS current
    DESCRIPTION
        "The Apply for the row of data in the UDP Map Multicast Table.

         A row in this table corresponds to the same row index in the
         UDP Map Multicast Table.

         This parameter MUST be set to 'apply' in order for any of the data
         in the UDP Map Multicast Table row to take effect in the APEX.  This
         parameter MUST be set LAST after all other data in the UDP Map Multicast 
         Table row has been configured.

         @Config(config=no, reboot=no)
        "
::= { apexUdpMapBlade3MulticastApplyEntry 2 }


-- ------------------------------------------------------------------------------
--
-- apexUdpMapBlade4
--
-- apexUdpMapBlade4ApplyTable
--

apexUdpMapBlade4ApplyTable OBJECT-TYPE
    SYNTAX SEQUENCE OF ApexUdpMapBlade4ApplyEntry
    MAX-ACCESS not-accessible
    STATUS current
    DESCRIPTION
        "Table of Apply Change for the data for UDP Map Table.

         A row in this table corresponds to the same row index in the
         UDP Map table.
        "
::= { apexUdpMapBlade4 1 }

apexUdpMapBlade4ApplyEntry OBJECT-TYPE
    SYNTAX ApexUdpMapBlade4ApplyEntry
    MAX-ACCESS not-accessible
    STATUS current
    DESCRIPTION
        "UDP Map Apply Table Entry."
    INDEX { apexUdpMapBlade4ApplyOutputTsNum }
::= { apexUdpMapBlade4ApplyTable 1 }

ApexUdpMapBlade4ApplyEntry ::= SEQUENCE
    {
     apexUdpMapBlade4ApplyOutputTsNum   Integer32,
     apexUdpMapBlade4ApplyChange        ApplyDataToDeviceTYPE,
     apexUdpMapBlade4InvalidApplyText   DisplayString
    }

apexUdpMapBlade4ApplyOutputTsNum OBJECT-TYPE
    SYNTAX Integer32(1..256)
    MAX-ACCESS not-accessible
    STATUS current
    DESCRIPTION
        "The index of the Udp Map Apply Table."
::= { apexUdpMapBlade4ApplyEntry 1 }

apexUdpMapBlade4ApplyChange OBJECT-TYPE
    SYNTAX ApplyDataToDeviceTYPE
    MAX-ACCESS read-write
    STATUS current
    DESCRIPTION
        "The Apply for the row of data in the Udp Map Table.

         A row in this table corresponds to the same row index in the
         Udp Map table.

         This parameter MUST be set to 'apply' in order for any of the data
         in the Udp Map Table row to take effect in the APEX.  This
         parameter MUST be set LAST after all other data in the Udp Map
         Table row has been configured.

         @Config(config=no, reboot=no)
        "
::= { apexUdpMapBlade4ApplyEntry 2 }

apexUdpMapBlade4InvalidApplyText OBJECT-TYPE
    SYNTAX DisplayString (SIZE (0..80))
    MAX-ACCESS read-only
    STATUS current
    DESCRIPTION
        "When apexUdpMapBlade4ApplyChange is set to applyNotInProgressInvalidData
         this entry may contain a text description of what was wrong with the data.
         This entry contains the description for the most recent apply of a
         table entry that was invalid."
::= { apexUdpMapBlade4ApplyEntry 3 }


-- ------------------------------------------------------------------------------
--
-- apexUdpMapBlade4Table
--

apexUdpMapBlade4Table OBJECT-TYPE
    SYNTAX SEQUENCE OF ApexUdpMapBlade4Entry
    MAX-ACCESS not-accessible
    STATUS current
    DESCRIPTION
        "Table of data for Udp Mapping. There are
         256 rows per blade.  Each row corresponds to one QAM channel.

         Once written, the change to this table will only take immediate
         effect after apexUdpMapBlade4ApplyChange is set to 'apply'.
         However, in order for the change to persist through subsequent
         reboots or power cycles, the change must be saved via apexSaveConfig.

         @Config(config=yes, reboot=no)
         @Commit(param=apexUdpMapBlade4ApplyChange, value=2)
         @Save(apexSaveConfig, value=2)
         @File(udpmap.ini, type='ini')
        "
::= { apexUdpMapBlade4 2 }

apexUdpMapBlade4Entry OBJECT-TYPE
    SYNTAX ApexUdpMapBlade4Entry
    MAX-ACCESS not-accessible
    STATUS current
    DESCRIPTION
        "Udp Mapping Table Entry."
    INDEX { apexUdpMapBlade4OutputTsNum }
::= { apexUdpMapBlade4Table 1 }

ApexUdpMapBlade4Entry ::= SEQUENCE
    {
     apexUdpMapBlade4OutputTsNum        Integer32,
     apexUdpMapBlade4StartProgNum       Integer32,
     apexUdpMapBlade4NumberProgs        Integer32,
     apexUdpMapBlade4VirtualIpIndex     Integer32,
     apexUdpMapBlade4ConfOutputTsNum    Integer32,
     apexUdpMapBlade4ConfInputInterface Integer32
    }

apexUdpMapBlade4OutputTsNum OBJECT-TYPE
    SYNTAX Integer32(1..256)
    MAX-ACCESS not-accessible
    STATUS current
    DESCRIPTION
        "Index of Udp Mapping Table.
        "
::= { apexUdpMapBlade4Entry 1 }

apexUdpMapBlade4StartProgNum OBJECT-TYPE
    SYNTAX Integer32(1..255)
    MAX-ACCESS read-write
    STATUS current
    DESCRIPTION
        "Indicates the first program number in a sequential range of programs
         that are to be routed to the same output transport stream.
        "
::= { apexUdpMapBlade4Entry 2 }

apexUdpMapBlade4NumberProgs OBJECT-TYPE
    SYNTAX Integer32(0..200)
    MAX-ACCESS read-write
    STATUS current
    DESCRIPTION
        "Indicates the number of programs that are to be mapped to the output
         transport stream.  One UDP port is opened for each program mapped to
         the output transport stream.
        "
::= { apexUdpMapBlade4Entry 3 }

apexUdpMapBlade4VirtualIpIndex OBJECT-TYPE
    SYNTAX Integer32(0..32)
    MAX-ACCESS read-write
    STATUS current
    DESCRIPTION
        "The index of the Virtual IP Table associated with this output TS. 
         This value is only used when configured for the 10-6 Modified UDP 
         Mapping Algorithm.  
         
         Range:
            '0'              = Not Applicable
            Virtual IP Index = 1-32 (valid IP must already be configured)
            
         The Virtual IP can only be selected when a GigE Input Interface index
         is not already selected. UDP port mappings will be assigned to either the
         configured Virtual IP or Physical GigE interface, but not both.
         
         When using a GigE Input Interface for UDP Port Mappings, this setting must be 
         set to 0. When Reporting UDP Port Mappings via RTSP D6, then the IP address is
         automatically allocated, and neither a Virtual IP or GigE interface can be
         selected. Both must be set to 0 in this case.
        "
::= { apexUdpMapBlade4Entry 4 }

apexUdpMapBlade4ConfOutputTsNum OBJECT-TYPE
    SYNTAX Integer32(0..1023)
    MAX-ACCESS read-write
    STATUS current
    DESCRIPTION
        "The configured output TS number for this output TS.  This value 
         is only used when configured for the 10-6 Modified UDP Mapping
         Algorithm.  Based on the 10-6 UDP Mapping Algorithm, this value 
         is used to calculate the UDP Port opened on the configured virtual 
         IP.  The upper 10 bits of the UDP port are based on this number
         and the lower 6 bits are based on the configured output program number.
        "
::= { apexUdpMapBlade4Entry 5 }

apexUdpMapBlade4ConfInputInterface OBJECT-TYPE
    SYNTAX Integer32(0..12)
    MAX-ACCESS read-write
    STATUS current
    DESCRIPTION
        "The configured GigE interface port number for this output TS.  This value 
         is only used when configured for the 10-6 Modified UDP Mapping
         Algorithm. The GigE interface can only be selected when a Virtual IP index
         is not already selected. UDP port mappings will be assigned to either the
         configured Virtual IP or Physical GigE interface, but not both.
         
         When using a Virtual IP for UDP Port Mappings, this setting must be set to
         0. When Reporting UDP Port Mappings via RTSP D6, then the IP address is
         automatically allocated, and neither a Virtual IP or GigE interface can be
         selected. Both must be set to 0 in this case.
         
         Range:
            '0'             = Not Applicable
            Input Interface = 1-12 (only interfaces in primary mode can be selected)
           
        "
::= { apexUdpMapBlade4Entry 6 }



-- ------------------------------------------------------------------------------
--
-- apexUdpMapBlade4MulticastTable
--

apexUdpMapBlade4MulticastTable OBJECT-TYPE
    SYNTAX SEQUENCE OF ApexUdpMapBlade4MulticastEntry
    MAX-ACCESS not-accessible
    STATUS current
    DESCRIPTION
        "Table of data for UDP Map Multicast. Each entry in
         this table identifies a Gigabit Ethernet input stream that is
         used for multicast UDP Port Mapping.
         
         Once written, the change to this table will only take immediate
         effect after apexUdpMapBlade4MulticastApplyChange is set to 'apply'.
         However, in order for the change to persist through subsequent
         reboots or power cycles, the change must be saved via apexSaveConfig.

         @Config(config=yes, reboot=no)
         @Commit(param=apexUdpMapBlade4MulticastApplyChange, value=2)
         @Save(apexSaveConfig, value=2)
         @File(udpmap.ini, type='ini')
        "
::= { apexUdpMapBlade4 3 }

apexUdpMapBlade4MulticastEntry OBJECT-TYPE
    SYNTAX ApexUdpMapBlade4MulticastEntry
    MAX-ACCESS not-accessible
    STATUS current
    DESCRIPTION
        "UDP Map Multicast Table Entry."
    INDEX { apexUdpMapBlade4MulticastIndex }
::= { apexUdpMapBlade4MulticastTable 1 }

ApexUdpMapBlade4MulticastEntry ::= SEQUENCE
    {
     apexUdpMapBlade4MulticastIndex           Integer32,
     apexUdpMapBlade4MulticastEnable          EnableDisableTYPE,
     apexUdpMapBlade4MulticastVirtualIpIndex  Integer32,
     apexUdpMapBlade4MulticastUdp             Integer32,
     apexUdpMapBlade4MulticastMcastIp         IpAddress,
     apexUdpMapBlade4MulticastSourceIp        IpAddress
    }

apexUdpMapBlade4MulticastIndex OBJECT-TYPE
    SYNTAX Integer32(1..256)
    MAX-ACCESS not-accessible
    STATUS current
    DESCRIPTION
        "Index of UDP Map Multicast Stream Table."
::= { apexUdpMapBlade4MulticastEntry 1 }

apexUdpMapBlade4MulticastEnable OBJECT-TYPE
    SYNTAX EnableDisableTYPE
    MAX-ACCESS read-write
    STATUS current
    DESCRIPTION
        "Indicates whether this UDP Map Multicast entry is enabled or disabled.
        "
::= { apexUdpMapBlade4MulticastEntry 2 }

apexUdpMapBlade4MulticastVirtualIpIndex OBJECT-TYPE
    SYNTAX Integer32(0..32)
    MAX-ACCESS read-write
    STATUS current
    DESCRIPTION
        "Index of the Virtual IP Table that corresponds to this entry.

         Range:
            '0'              = Not Applicable
            Virtual IP Index = 1-32
        "
::= { apexUdpMapBlade4MulticastEntry 3 }

apexUdpMapBlade4MulticastUdp OBJECT-TYPE
    SYNTAX Integer32(0..65535)
    MAX-ACCESS read-write
    STATUS current
    DESCRIPTION
        "GBE Input UDP Port.

         Range: 0-65535
        "
::= { apexUdpMapBlade4MulticastEntry 4 }

apexUdpMapBlade4MulticastMcastIp OBJECT-TYPE
    SYNTAX IpAddress
    MAX-ACCESS read-write
    STATUS current
    DESCRIPTION
        "The Multicast receive IP address.
         An IP address of 0.0.0.0 indicates singlecast only.

         Multicast IP addresses 224.0.0.0 to 224.0.0.255 are reserved.
        "
::= { apexUdpMapBlade4MulticastEntry 5 }

apexUdpMapBlade4MulticastSourceIp OBJECT-TYPE
    SYNTAX IpAddress
    MAX-ACCESS read-write
    STATUS current
    DESCRIPTION
        "This is the IP address of the source device. This field is only
         used when a multicast IP address is also specified.
        "
::= { apexUdpMapBlade4MulticastEntry 6 }


-- ------------------------------------------------------------------------------
--
-- apexUdpMapBlade4MulticastApplyTable
--

apexUdpMapBlade4MulticastApplyTable OBJECT-TYPE
    SYNTAX SEQUENCE OF ApexUdpMapBlade4MulticastApplyEntry
    MAX-ACCESS not-accessible
    STATUS current
    DESCRIPTION
        "Table of Apply Change for the UDP Map Multicast Table.

         A row in this table corresponds to the same row index in the
         UDP Map Multicast Table (apexUdpMapBlade4MulticastTable).
        "
::= { apexUdpMapBlade4 4 }

apexUdpMapBlade4MulticastApplyEntry OBJECT-TYPE
    SYNTAX ApexUdpMapBlade4MulticastApplyEntry
    MAX-ACCESS not-accessible
    STATUS current
    DESCRIPTION
        "UDP Map Multicast Apply Table Entry."
    INDEX { apexUdpMapBlade4MulticastApplyIndex }
::= { apexUdpMapBlade4MulticastApplyTable 1 }

ApexUdpMapBlade4MulticastApplyEntry ::= SEQUENCE
    {
     apexUdpMapBlade4MulticastApplyIndex  Integer32,
     apexUdpMapBlade4MulticastApplyChange ApplyDataToDeviceTYPE
    }

apexUdpMapBlade4MulticastApplyIndex OBJECT-TYPE
    SYNTAX Integer32(1..256)
    MAX-ACCESS not-accessible
    STATUS current
    DESCRIPTION
        "The index of the UDP Map Multicast Table."
::= { apexUdpMapBlade4MulticastApplyEntry 1 }

apexUdpMapBlade4MulticastApplyChange OBJECT-TYPE
    SYNTAX ApplyDataToDeviceTYPE
    MAX-ACCESS read-write
    STATUS current
    DESCRIPTION
        "The Apply for the row of data in the UDP Map Multicast Table.

         A row in this table corresponds to the same row index in the
         UDP Map Multicast Table.

         This parameter MUST be set to 'apply' in order for any of the data
         in the UDP Map Multicast Table row to take effect in the APEX.  This
         parameter MUST be set LAST after all other data in the UDP Map Multicast 
         Table row has been configured.

         @Config(config=no, reboot=no)
        "
::= { apexUdpMapBlade4MulticastApplyEntry 2 }


-- ------------------------------------------------------------------------------
--
-- apexUdpMapBlade5
--
-- apexUdpMapBlade5ApplyTable
--

apexUdpMapBlade5ApplyTable OBJECT-TYPE
    SYNTAX SEQUENCE OF ApexUdpMapBlade5ApplyEntry
    MAX-ACCESS not-accessible
    STATUS current
    DESCRIPTION
        "Table of Apply Change for the data for UDP Map Table.

         A row in this table corresponds to the same row index in the
         UDP Map table.
        "
::= { apexUdpMapBlade5 1 }

apexUdpMapBlade5ApplyEntry OBJECT-TYPE
    SYNTAX ApexUdpMapBlade5ApplyEntry
    MAX-ACCESS not-accessible
    STATUS current
    DESCRIPTION
        "UDP Map Apply Table Entry."
    INDEX { apexUdpMapBlade5ApplyOutputTsNum }
::= { apexUdpMapBlade5ApplyTable 1 }

ApexUdpMapBlade5ApplyEntry ::= SEQUENCE
    {
     apexUdpMapBlade5ApplyOutputTsNum   Integer32,
     apexUdpMapBlade5ApplyChange        ApplyDataToDeviceTYPE,
     apexUdpMapBlade5InvalidApplyText   DisplayString
    }

apexUdpMapBlade5ApplyOutputTsNum OBJECT-TYPE
    SYNTAX Integer32(1..256)
    MAX-ACCESS not-accessible
    STATUS current
    DESCRIPTION
        "The index of the Udp Map Apply Table."
::= { apexUdpMapBlade5ApplyEntry 1 }

apexUdpMapBlade5ApplyChange OBJECT-TYPE
    SYNTAX ApplyDataToDeviceTYPE
    MAX-ACCESS read-write
    STATUS current
    DESCRIPTION
        "The Apply for the row of data in the Udp Map Table.

         A row in this table corresponds to the same row index in the
         Udp Map table.

         This parameter MUST be set to 'apply' in order for any of the data
         in the Udp Map Table row to take effect in the APEX.  This
         parameter MUST be set LAST after all other data in the Udp Map
         Table row has been configured.

         @Config(config=no, reboot=no)
        "
::= { apexUdpMapBlade5ApplyEntry 2 }

apexUdpMapBlade5InvalidApplyText OBJECT-TYPE
    SYNTAX DisplayString (SIZE (0..80))
    MAX-ACCESS read-only
    STATUS current
    DESCRIPTION
        "When apexUdpMapBlade5ApplyChange is set to applyNotInProgressInvalidData
         this entry may contain a text description of what was wrong with the data.
         This entry contains the description for the most recent apply of a
         table entry that was invalid."
::= { apexUdpMapBlade5ApplyEntry 3 }


-- ------------------------------------------------------------------------------
--
-- apexUdpMapBlade5Table
--

apexUdpMapBlade5Table OBJECT-TYPE
    SYNTAX SEQUENCE OF ApexUdpMapBlade5Entry
    MAX-ACCESS not-accessible
    STATUS current
    DESCRIPTION
        "Table of data for Udp Mapping. There are
         256 rows per blade.  Each row corresponds to one QAM channel.

         Once written, the change to this table will only take immediate
         effect after apexUdpMapBlade5ApplyChange is set to 'apply'.
         However, in order for the change to persist through subsequent
         reboots or power cycles, the change must be saved via apexSaveConfig.

         @Config(config=yes, reboot=no)
         @Commit(param=apexUdpMapBlade5ApplyChange, value=2)
         @Save(apexSaveConfig, value=2)
         @File(udpmap.ini, type='ini')
        "
::= { apexUdpMapBlade5 2 }

apexUdpMapBlade5Entry OBJECT-TYPE
    SYNTAX ApexUdpMapBlade5Entry
    MAX-ACCESS not-accessible
    STATUS current
    DESCRIPTION
        "Udp Mapping Table Entry."
    INDEX { apexUdpMapBlade5OutputTsNum }
::= { apexUdpMapBlade5Table 1 }

ApexUdpMapBlade5Entry ::= SEQUENCE
    {
     apexUdpMapBlade5OutputTsNum        Integer32,
     apexUdpMapBlade5StartProgNum       Integer32,
     apexUdpMapBlade5NumberProgs        Integer32,
     apexUdpMapBlade5VirtualIpIndex     Integer32,
     apexUdpMapBlade5ConfOutputTsNum    Integer32,
     apexUdpMapBlade5ConfInputInterface Integer32
    }

apexUdpMapBlade5OutputTsNum OBJECT-TYPE
    SYNTAX Integer32(1..256)
    MAX-ACCESS not-accessible
    STATUS current
    DESCRIPTION
        "Index of Udp Mapping Table.
        "
::= { apexUdpMapBlade5Entry 1 }

apexUdpMapBlade5StartProgNum OBJECT-TYPE
    SYNTAX Integer32(1..255)
    MAX-ACCESS read-write
    STATUS current
    DESCRIPTION
        "Indicates the first program number in a sequential range of programs
         that are to be routed to the same output transport stream.
        "
::= { apexUdpMapBlade5Entry 2 }

apexUdpMapBlade5NumberProgs OBJECT-TYPE
    SYNTAX Integer32(0..200)
    MAX-ACCESS read-write
    STATUS current
    DESCRIPTION
        "Indicates the number of programs that are to be mapped to the output
         transport stream.  One UDP port is opened for each program mapped to
         the output transport stream.
        "
::= { apexUdpMapBlade5Entry 3 }

apexUdpMapBlade5VirtualIpIndex OBJECT-TYPE
    SYNTAX Integer32(0..32)
    MAX-ACCESS read-write
    STATUS current
    DESCRIPTION
        "The index of the Virtual IP Table associated with this output TS. 
         This value is only used when configured for the 10-6 Modified UDP 
         Mapping Algorithm.  
         
         Range:
            '0'              = Not Applicable
            Virtual IP Index = 1-32 (valid IP must already be configured)
            
         The Virtual IP can only be selected when a GigE Input Interface index
         is not already selected. UDP port mappings will be assigned to either the
         configured Virtual IP or Physical GigE interface, but not both.
         
         When using a GigE Input Interface for UDP Port Mappings, this setting must be 
         set to 0. When Reporting UDP Port Mappings via RTSP D6, then the IP address is
         automatically allocated, and neither a Virtual IP or GigE interface can be
         selected. Both must be set to 0 in this case.
        "
::= { apexUdpMapBlade5Entry 4 }

apexUdpMapBlade5ConfOutputTsNum OBJECT-TYPE
    SYNTAX Integer32(0..1023)
    MAX-ACCESS read-write
    STATUS current
    DESCRIPTION
        "The configured output TS number for this output TS.  This value 
         is only used when configured for the 10-6 Modified UDP Mapping
         Algorithm.  Based on the 10-6 UDP Mapping Algorithm, this value 
         is used to calculate the UDP Port opened on the configured virtual 
         IP.  The upper 10 bits of the UDP port are based on this number
         and the lower 6 bits are based on the configured output program number.
        "
::= { apexUdpMapBlade5Entry 5 }

apexUdpMapBlade5ConfInputInterface OBJECT-TYPE
    SYNTAX Integer32(0..12)
    MAX-ACCESS read-write
    STATUS current
    DESCRIPTION
        "The configured GigE interface port number for this output TS.  This value 
         is only used when configured for the 10-6 Modified UDP Mapping
         Algorithm. The GigE interface can only be selected when a Virtual IP index
         is not already selected. UDP port mappings will be assigned to either the
         configured Virtual IP or Physical GigE interface, but not both.
         
         When using a Virtual IP for UDP Port Mappings, this setting must be set to
         0. When Reporting UDP Port Mappings via RTSP D6, then the IP address is
         automatically allocated, and neither a Virtual IP or GigE interface can be
         selected. Both must be set to 0 in this case.
         
         Range:
            '0'             = Not Applicable
            Input Interface = 1-12 (only interfaces in primary mode can be selected)
           
        "
::= { apexUdpMapBlade5Entry 6 }


-- ------------------------------------------------------------------------------
--
-- apexUdpMapBlade5MulticastTable
--

apexUdpMapBlade5MulticastTable OBJECT-TYPE
    SYNTAX SEQUENCE OF ApexUdpMapBlade5MulticastEntry
    MAX-ACCESS not-accessible
    STATUS current
    DESCRIPTION
        "Table of data for UDP Map Multicast. Each entry in
         this table identifies a Gigabit Ethernet input stream that is
         used for multicast UDP Port Mapping.
         
         Once written, the change to this table will only take immediate
         effect after apexUdpMapBlade5MulticastApplyChange is set to 'apply'.
         However, in order for the change to persist through subsequent
         reboots or power cycles, the change must be saved via apexSaveConfig.

         @Config(config=yes, reboot=no)
         @Commit(param=apexUdpMapBlade5MulticastApplyChange, value=2)
         @Save(apexSaveConfig, value=2)
         @File(udpmap.ini, type='ini')
        "
::= { apexUdpMapBlade5 3 }

apexUdpMapBlade5MulticastEntry OBJECT-TYPE
    SYNTAX ApexUdpMapBlade5MulticastEntry
    MAX-ACCESS not-accessible
    STATUS current
    DESCRIPTION
        "UDP Map Multicast Table Entry."
    INDEX { apexUdpMapBlade5MulticastIndex }
::= { apexUdpMapBlade5MulticastTable 1 }

ApexUdpMapBlade5MulticastEntry ::= SEQUENCE
    {
     apexUdpMapBlade5MulticastIndex           Integer32,
     apexUdpMapBlade5MulticastEnable          EnableDisableTYPE,
     apexUdpMapBlade5MulticastVirtualIpIndex  Integer32,
     apexUdpMapBlade5MulticastUdp             Integer32,
     apexUdpMapBlade5MulticastMcastIp         IpAddress,
     apexUdpMapBlade5MulticastSourceIp        IpAddress
    }

apexUdpMapBlade5MulticastIndex OBJECT-TYPE
    SYNTAX Integer32(1..256)
    MAX-ACCESS not-accessible
    STATUS current
    DESCRIPTION
        "Index of UDP Map Multicast Stream Table."
::= { apexUdpMapBlade5MulticastEntry 1 }

apexUdpMapBlade5MulticastEnable OBJECT-TYPE
    SYNTAX EnableDisableTYPE
    MAX-ACCESS read-write
    STATUS current
    DESCRIPTION
        "Indicates whether this UDP Map Multicast entry is enabled or disabled.
        "
::= { apexUdpMapBlade5MulticastEntry 2 }

apexUdpMapBlade5MulticastVirtualIpIndex OBJECT-TYPE
    SYNTAX Integer32(0..32)
    MAX-ACCESS read-write
    STATUS current
    DESCRIPTION
        "Index of the Virtual IP Table that corresponds to this entry.

         Range:
            '0'              = Not Applicable
            Virtual IP Index = 1-32
        "
::= { apexUdpMapBlade5MulticastEntry 3 }

apexUdpMapBlade5MulticastUdp OBJECT-TYPE
    SYNTAX Integer32(0..65535)
    MAX-ACCESS read-write
    STATUS current
    DESCRIPTION
        "GBE Input UDP Port.

         Range: 0-65535
        "
::= { apexUdpMapBlade5MulticastEntry 4 }

apexUdpMapBlade5MulticastMcastIp OBJECT-TYPE
    SYNTAX IpAddress
    MAX-ACCESS read-write
    STATUS current
    DESCRIPTION
        "The Multicast receive IP address.
         An IP address of 0.0.0.0 indicates singlecast only.

         Multicast IP addresses 224.0.0.0 to 224.0.0.255 are reserved.
        "
::= { apexUdpMapBlade5MulticastEntry 5 }

apexUdpMapBlade5MulticastSourceIp OBJECT-TYPE
    SYNTAX IpAddress
    MAX-ACCESS read-write
    STATUS current
    DESCRIPTION
        "This is the IP address of the source device. This field is only
         used when a multicast IP address is also specified.
        "
::= { apexUdpMapBlade5MulticastEntry 6 }


-- ------------------------------------------------------------------------------
--
-- apexUdpMapBlade5MulticastApplyTable
--

apexUdpMapBlade5MulticastApplyTable OBJECT-TYPE
    SYNTAX SEQUENCE OF ApexUdpMapBlade5MulticastApplyEntry
    MAX-ACCESS not-accessible
    STATUS current
    DESCRIPTION
        "Table of Apply Change for the UDP Map Multicast Table.

         A row in this table corresponds to the same row index in the
         UDP Map Multicast Table (apexUdpMapBlade5MulticastTable).
        "
::= { apexUdpMapBlade5 4 }

apexUdpMapBlade5MulticastApplyEntry OBJECT-TYPE
    SYNTAX ApexUdpMapBlade5MulticastApplyEntry
    MAX-ACCESS not-accessible
    STATUS current
    DESCRIPTION
        "UDP Map Multicast Apply Table Entry."
    INDEX { apexUdpMapBlade5MulticastApplyIndex }
::= { apexUdpMapBlade5MulticastApplyTable 1 }

ApexUdpMapBlade5MulticastApplyEntry ::= SEQUENCE
    {
     apexUdpMapBlade5MulticastApplyIndex  Integer32,
     apexUdpMapBlade5MulticastApplyChange ApplyDataToDeviceTYPE
    }

apexUdpMapBlade5MulticastApplyIndex OBJECT-TYPE
    SYNTAX Integer32(1..256)
    MAX-ACCESS not-accessible
    STATUS current
    DESCRIPTION
        "The index of the UDP Map Multicast Table."
::= { apexUdpMapBlade5MulticastApplyEntry 1 }

apexUdpMapBlade5MulticastApplyChange OBJECT-TYPE
    SYNTAX ApplyDataToDeviceTYPE
    MAX-ACCESS read-write
    STATUS current
    DESCRIPTION
        "The Apply for the row of data in the UDP Map Multicast Table.

         A row in this table corresponds to the same row index in the
         UDP Map Multicast Table.

         This parameter MUST be set to 'apply' in order for any of the data
         in the UDP Map Multicast Table row to take effect in the APEX.  This
         parameter MUST be set LAST after all other data in the UDP Map Multicast 
         Table row has been configured.

         @Config(config=no, reboot=no)
        "
::= { apexUdpMapBlade5MulticastApplyEntry 2 }


-- ------------------------------------------------------------------------------
--
-- apexUdpMapBlade6
--
-- apexUdpMapBlade6ApplyTable
--

apexUdpMapBlade6ApplyTable OBJECT-TYPE
    SYNTAX SEQUENCE OF ApexUdpMapBlade6ApplyEntry
    MAX-ACCESS not-accessible
    STATUS current
    DESCRIPTION
        "Table of Apply Change for the data for UDP Map Table.

         A row in this table corresponds to the same row index in the
         UDP Map table.
        "
::= { apexUdpMapBlade6 1 }

apexUdpMapBlade6ApplyEntry OBJECT-TYPE
    SYNTAX ApexUdpMapBlade6ApplyEntry
    MAX-ACCESS not-accessible
    STATUS current
    DESCRIPTION
        "UDP Map Apply Table Entry."
    INDEX { apexUdpMapBlade6ApplyOutputTsNum }
::= { apexUdpMapBlade6ApplyTable 1 }

ApexUdpMapBlade6ApplyEntry ::= SEQUENCE
    {
     apexUdpMapBlade6ApplyOutputTsNum   Integer32,
     apexUdpMapBlade6ApplyChange        ApplyDataToDeviceTYPE,
     apexUdpMapBlade6InvalidApplyText   DisplayString
    }

apexUdpMapBlade6ApplyOutputTsNum OBJECT-TYPE
    SYNTAX Integer32(1..256)
    MAX-ACCESS not-accessible
    STATUS current
    DESCRIPTION
        "The index of the Udp Map Apply Table."
::= { apexUdpMapBlade6ApplyEntry 1 }

apexUdpMapBlade6ApplyChange OBJECT-TYPE
    SYNTAX ApplyDataToDeviceTYPE
    MAX-ACCESS read-write
    STATUS current
    DESCRIPTION
        "The Apply for the row of data in the Udp Map Table.

         A row in this table corresponds to the same row index in the
         Udp Map table.

         This parameter MUST be set to 'apply' in order for any of the data
         in the Udp Map Table row to take effect in the APEX.  This
         parameter MUST be set LAST after all other data in the Udp Map
         Table row has been configured.

         @Config(config=no, reboot=no)
        "
::= { apexUdpMapBlade6ApplyEntry 2 }

apexUdpMapBlade6InvalidApplyText OBJECT-TYPE
    SYNTAX DisplayString (SIZE (0..80))
    MAX-ACCESS read-only
    STATUS current
    DESCRIPTION
        "When apexUdpMapBlade6ApplyChange is set to applyNotInProgressInvalidData
         this entry may contain a text description of what was wrong with the data.
         This entry contains the description for the most recent apply of a
         table entry that was invalid."
::= { apexUdpMapBlade6ApplyEntry 3 }


-- ------------------------------------------------------------------------------
--
-- apexUdpMapBlade6Table
--

apexUdpMapBlade6Table OBJECT-TYPE
    SYNTAX SEQUENCE OF ApexUdpMapBlade6Entry
    MAX-ACCESS not-accessible
    STATUS current
    DESCRIPTION
        "Table of data for Udp Mapping. There are
         256 rows per blade.  Each row corresponds to one QAM channel.

         Once written, the change to this table will only take immediate
         effect after apexUdpMapBlade6ApplyChange is set to 'apply'.
         However, in order for the change to persist through subsequent
         reboots or power cycles, the change must be saved via apexSaveConfig.

         @Config(config=yes, reboot=no)
         @Commit(param=apexUdpMapBlade6ApplyChange, value=2)
         @Save(apexSaveConfig, value=2)
         @File(udpmap.ini, type='ini')
        "
::= { apexUdpMapBlade6 2 }

apexUdpMapBlade6Entry OBJECT-TYPE
    SYNTAX ApexUdpMapBlade6Entry
    MAX-ACCESS not-accessible
    STATUS current
    DESCRIPTION
        "Udp Mapping Table Entry."
    INDEX { apexUdpMapBlade6OutputTsNum }
::= { apexUdpMapBlade6Table 1 }

ApexUdpMapBlade6Entry ::= SEQUENCE
    {
     apexUdpMapBlade6OutputTsNum        Integer32,
     apexUdpMapBlade6StartProgNum       Integer32,
     apexUdpMapBlade6NumberProgs        Integer32,
     apexUdpMapBlade6VirtualIpIndex     Integer32,
     apexUdpMapBlade6ConfOutputTsNum    Integer32,
     apexUdpMapBlade6ConfInputInterface Integer32
    }

apexUdpMapBlade6OutputTsNum OBJECT-TYPE
    SYNTAX Integer32(1..256)
    MAX-ACCESS not-accessible
    STATUS current
    DESCRIPTION
        "Index of Udp Mapping Table.
        "
::= { apexUdpMapBlade6Entry 1 }

apexUdpMapBlade6StartProgNum OBJECT-TYPE
    SYNTAX Integer32(1..255)
    MAX-ACCESS read-write
    STATUS current
    DESCRIPTION
        "Indicates the first program number in a sequential range of programs
         that are to be routed to the same output transport stream.
        "
::= { apexUdpMapBlade6Entry 2 }

apexUdpMapBlade6NumberProgs OBJECT-TYPE
    SYNTAX Integer32(0..200)
    MAX-ACCESS read-write
    STATUS current
    DESCRIPTION
        "Indicates the number of programs that are to be mapped to the output
         transport stream.  One UDP port is opened for each program mapped to
         the output transport stream.
        "
::= { apexUdpMapBlade6Entry 3 }

apexUdpMapBlade6VirtualIpIndex OBJECT-TYPE
    SYNTAX Integer32(0..32)
    MAX-ACCESS read-write
    STATUS current
    DESCRIPTION
        "The index of the Virtual IP Table associated with this output TS. 
         This value is only used when configured for the 10-6 Modified UDP 
         Mapping Algorithm.  
         
         Range:
            '0'              = Not Applicable
            Virtual IP Index = 1-32 (valid IP must already be configured)
            
         The Virtual IP can only be selected when a GigE Input Interface index
         is not already selected. UDP port mappings will be assigned to either the
         configured Virtual IP or Physical GigE interface, but not both.
         
         When using a GigE Input Interface for UDP Port Mappings, this setting must be 
         set to 0. When Reporting UDP Port Mappings via RTSP D6, then the IP address is
         automatically allocated, and neither a Virtual IP or GigE interface can be
         selected. Both must be set to 0 in this case.
        "
::= { apexUdpMapBlade6Entry 4 }

apexUdpMapBlade6ConfOutputTsNum OBJECT-TYPE
    SYNTAX Integer32(0..1023)
    MAX-ACCESS read-write
    STATUS current
    DESCRIPTION
        "The configured output TS number for this output TS.  This value 
         is only used when configured for the 10-6 Modified UDP Mapping
         Algorithm.  Based on the 10-6 UDP Mapping Algorithm, this value 
         is used to calculate the UDP Port opened on the configured virtual 
         IP.  The upper 10 bits of the UDP port are based on this number
         and the lower 6 bits are based on the configured output program number.
        "
::= { apexUdpMapBlade6Entry 5 }

apexUdpMapBlade6ConfInputInterface OBJECT-TYPE
    SYNTAX Integer32(0..12)
    MAX-ACCESS read-write
    STATUS current
    DESCRIPTION
        "The configured GigE interface port number for this output TS.  This value 
         is only used when configured for the 10-6 Modified UDP Mapping
         Algorithm. The GigE interface can only be selected when a Virtual IP index
         is not already selected. UDP port mappings will be assigned to either the
         configured Virtual IP or Physical GigE interface, but not both.
         
         When using a Virtual IP for UDP Port Mappings, this setting must be set to
         0. When Reporting UDP Port Mappings via RTSP D6, then the IP address is
         automatically allocated, and neither a Virtual IP or GigE interface can be
         selected. Both must be set to 0 in this case.
         
         Range:
            '0'             = Not Applicable
            Input Interface = 1-12 (only interfaces in primary mode can be selected)
           
        "
::= { apexUdpMapBlade6Entry 6 }


-- ------------------------------------------------------------------------------
--
-- apexUdpMapBlade6MulticastTable
--

apexUdpMapBlade6MulticastTable OBJECT-TYPE
    SYNTAX SEQUENCE OF ApexUdpMapBlade6MulticastEntry
    MAX-ACCESS not-accessible
    STATUS current
    DESCRIPTION
        "Table of data for UDP Map Multicast. Each entry in
         this table identifies a Gigabit Ethernet input stream that is
         used for multicast UDP Port Mapping.
         
         Once written, the change to this table will only take immediate
         effect after apexUdpMapBlade6MulticastApplyChange is set to 'apply'.
         However, in order for the change to persist through subsequent
         reboots or power cycles, the change must be saved via apexSaveConfig.

         @Config(config=yes, reboot=no)
         @Commit(param=apexUdpMapBlade6MulticastApplyChange, value=2)
         @Save(apexSaveConfig, value=2)
         @File(udpmap.ini, type='ini')
        "
::= { apexUdpMapBlade6 3 }

apexUdpMapBlade6MulticastEntry OBJECT-TYPE
    SYNTAX ApexUdpMapBlade6MulticastEntry
    MAX-ACCESS not-accessible
    STATUS current
    DESCRIPTION
        "UDP Map Multicast Table Entry."
    INDEX { apexUdpMapBlade6MulticastIndex }
::= { apexUdpMapBlade6MulticastTable 1 }

ApexUdpMapBlade6MulticastEntry ::= SEQUENCE
    {
     apexUdpMapBlade6MulticastIndex           Integer32,
     apexUdpMapBlade6MulticastEnable          EnableDisableTYPE,
     apexUdpMapBlade6MulticastVirtualIpIndex  Integer32,
     apexUdpMapBlade6MulticastUdp             Integer32,
     apexUdpMapBlade6MulticastMcastIp         IpAddress,
     apexUdpMapBlade6MulticastSourceIp        IpAddress
    }

apexUdpMapBlade6MulticastIndex OBJECT-TYPE
    SYNTAX Integer32(1..256)
    MAX-ACCESS not-accessible
    STATUS current
    DESCRIPTION
        "Index of UDP Map Multicast Stream Table."
::= { apexUdpMapBlade6MulticastEntry 1 }

apexUdpMapBlade6MulticastEnable OBJECT-TYPE
    SYNTAX EnableDisableTYPE
    MAX-ACCESS read-write
    STATUS current
    DESCRIPTION
        "Indicates whether this UDP Map Multicast entry is enabled or disabled.
        "
::= { apexUdpMapBlade6MulticastEntry 2 }

apexUdpMapBlade6MulticastVirtualIpIndex OBJECT-TYPE
    SYNTAX Integer32(0..32)
    MAX-ACCESS read-write
    STATUS current
    DESCRIPTION
        "Index of the Virtual IP Table that corresponds to this entry.

         Range:
            '0'              = Not Applicable
            Virtual IP Index = 1-32
        "
::= { apexUdpMapBlade6MulticastEntry 3 }

apexUdpMapBlade6MulticastUdp OBJECT-TYPE
    SYNTAX Integer32(0..65535)
    MAX-ACCESS read-write
    STATUS current
    DESCRIPTION
        "GBE Input UDP Port.

         Range: 0-65535
        "
::= { apexUdpMapBlade6MulticastEntry 4 }

apexUdpMapBlade6MulticastMcastIp OBJECT-TYPE
    SYNTAX IpAddress
    MAX-ACCESS read-write
    STATUS current
    DESCRIPTION
        "The Multicast receive IP address.
         An IP address of 0.0.0.0 indicates singlecast only.

         Multicast IP addresses 224.0.0.0 to 224.0.0.255 are reserved.
        "
::= { apexUdpMapBlade6MulticastEntry 5 }

apexUdpMapBlade6MulticastSourceIp OBJECT-TYPE
    SYNTAX IpAddress
    MAX-ACCESS read-write
    STATUS current
    DESCRIPTION
        "This is the IP address of the source device. This field is only
         used when a multicast IP address is also specified.
        "
::= { apexUdpMapBlade6MulticastEntry 6 }


-- ------------------------------------------------------------------------------
--
-- apexUdpMapBlade6MulticastApplyTable
--

apexUdpMapBlade6MulticastApplyTable OBJECT-TYPE
    SYNTAX SEQUENCE OF ApexUdpMapBlade6MulticastApplyEntry
    MAX-ACCESS not-accessible
    STATUS current
    DESCRIPTION
        "Table of Apply Change for the UDP Map Multicast Table.

         A row in this table corresponds to the same row index in the
         UDP Map Multicast Table (apexUdpMapBlade6MulticastTable).
        "
::= { apexUdpMapBlade6 4 }

apexUdpMapBlade6MulticastApplyEntry OBJECT-TYPE
    SYNTAX ApexUdpMapBlade6MulticastApplyEntry
    MAX-ACCESS not-accessible
    STATUS current
    DESCRIPTION
        "UDP Map Multicast Apply Table Entry."
    INDEX { apexUdpMapBlade6MulticastApplyIndex }
::= { apexUdpMapBlade6MulticastApplyTable 1 }

ApexUdpMapBlade6MulticastApplyEntry ::= SEQUENCE
    {
     apexUdpMapBlade6MulticastApplyIndex  Integer32,
     apexUdpMapBlade6MulticastApplyChange ApplyDataToDeviceTYPE
    }

apexUdpMapBlade6MulticastApplyIndex OBJECT-TYPE
    SYNTAX Integer32(1..256)
    MAX-ACCESS not-accessible
    STATUS current
    DESCRIPTION
        "The index of the UDP Map Multicast Table."
::= { apexUdpMapBlade6MulticastApplyEntry 1 }

apexUdpMapBlade6MulticastApplyChange OBJECT-TYPE
    SYNTAX ApplyDataToDeviceTYPE
    MAX-ACCESS read-write
    STATUS current
    DESCRIPTION
        "The Apply for the row of data in the UDP Map Multicast Table.

         A row in this table corresponds to the same row index in the
         UDP Map Multicast Table.

         This parameter MUST be set to 'apply' in order for any of the data
         in the UDP Map Multicast Table row to take effect in the APEX.  This
         parameter MUST be set LAST after all other data in the UDP Map Multicast 
         Table row has been configured.

         @Config(config=no, reboot=no)
        "
::= { apexUdpMapBlade6MulticastApplyEntry 2 }


-- ------------------------------------------------------------------------------
--
-- apexUdpMapBlade7
--
-- apexUdpMapBlade7ApplyTable
--

apexUdpMapBlade7ApplyTable OBJECT-TYPE
    SYNTAX SEQUENCE OF ApexUdpMapBlade7ApplyEntry
    MAX-ACCESS not-accessible
    STATUS current
    DESCRIPTION
        "Table of Apply Change for the data for UDP Map Table.

         A row in this table corresponds to the same row index in the
         UDP Map table.
        "
::= { apexUdpMapBlade7 1 }

apexUdpMapBlade7ApplyEntry OBJECT-TYPE
    SYNTAX ApexUdpMapBlade7ApplyEntry
    MAX-ACCESS not-accessible
    STATUS current
    DESCRIPTION
        "UDP Map Apply Table Entry."
    INDEX { apexUdpMapBlade7ApplyOutputTsNum }
::= { apexUdpMapBlade7ApplyTable 1 }

ApexUdpMapBlade7ApplyEntry ::= SEQUENCE
    {
     apexUdpMapBlade7ApplyOutputTsNum   Integer32,
     apexUdpMapBlade7ApplyChange        ApplyDataToDeviceTYPE,
     apexUdpMapBlade7InvalidApplyText   DisplayString
    }

apexUdpMapBlade7ApplyOutputTsNum OBJECT-TYPE
    SYNTAX Integer32(1..256)
    MAX-ACCESS not-accessible
    STATUS current
    DESCRIPTION
        "The index of the Udp Map Apply Table."
::= { apexUdpMapBlade7ApplyEntry 1 }

apexUdpMapBlade7ApplyChange OBJECT-TYPE
    SYNTAX ApplyDataToDeviceTYPE
    MAX-ACCESS read-write
    STATUS current
    DESCRIPTION
        "The Apply for the row of data in the Udp Map Table.

         A row in this table corresponds to the same row index in the
         Udp Map table.

         This parameter MUST be set to 'apply' in order for any of the data
         in the Udp Map Table row to take effect in the APEX.  This
         parameter MUST be set LAST after all other data in the Udp Map
         Table row has been configured.

         @Config(config=no, reboot=no)
        "
::= { apexUdpMapBlade7ApplyEntry 2 }

apexUdpMapBlade7InvalidApplyText OBJECT-TYPE
    SYNTAX DisplayString (SIZE (0..80))
    MAX-ACCESS read-only
    STATUS current
    DESCRIPTION
        "When apexUdpMapBlade7ApplyChange is set to applyNotInProgressInvalidData
         this entry may contain a text description of what was wrong with the data.
         This entry contains the description for the most recent apply of a
         table entry that was invalid."
::= { apexUdpMapBlade7ApplyEntry 3 }


-- ------------------------------------------------------------------------------
--
-- apexUdpMapBlade7Table
--

apexUdpMapBlade7Table OBJECT-TYPE
    SYNTAX SEQUENCE OF ApexUdpMapBlade7Entry
    MAX-ACCESS not-accessible
    STATUS current
    DESCRIPTION
        "Table of data for Udp Mapping. There are
         256 rows per blade.  Each row corresponds to one QAM channel.

         Once written, the change to this table will only take immediate
         effect after apexUdpMapBlade7ApplyChange is set to 'apply'.
         However, in order for the change to persist through subsequent
         reboots or power cycles, the change must be saved via apexSaveConfig.

         @Config(config=yes, reboot=no)
         @Commit(param=apexUdpMapBlade7ApplyChange, value=2)
         @Save(apexSaveConfig, value=2)
         @File(udpmap.ini, type='ini')
        "
::= { apexUdpMapBlade7 2 }

apexUdpMapBlade7Entry OBJECT-TYPE
    SYNTAX ApexUdpMapBlade7Entry
    MAX-ACCESS not-accessible
    STATUS current
    DESCRIPTION
        "Udp Mapping Table Entry."
    INDEX { apexUdpMapBlade7OutputTsNum }
::= { apexUdpMapBlade7Table 1 }

ApexUdpMapBlade7Entry ::= SEQUENCE
    {
     apexUdpMapBlade7OutputTsNum        Integer32,
     apexUdpMapBlade7StartProgNum       Integer32,
     apexUdpMapBlade7NumberProgs        Integer32,
     apexUdpMapBlade7VirtualIpIndex     Integer32,
     apexUdpMapBlade7ConfOutputTsNum    Integer32,
     apexUdpMapBlade7ConfInputInterface Integer32
    }

apexUdpMapBlade7OutputTsNum OBJECT-TYPE
    SYNTAX Integer32(1..256)
    MAX-ACCESS not-accessible
    STATUS current
    DESCRIPTION
        "Index of Udp Mapping Table.
        "
::= { apexUdpMapBlade7Entry 1 }

apexUdpMapBlade7StartProgNum OBJECT-TYPE
    SYNTAX Integer32(1..255)
    MAX-ACCESS read-write
    STATUS current
    DESCRIPTION
        "Indicates the first program number in a sequential range of programs
         that are to be routed to the same output transport stream.
        "
::= { apexUdpMapBlade7Entry 2 }

apexUdpMapBlade7NumberProgs OBJECT-TYPE
    SYNTAX Integer32(0..200)
    MAX-ACCESS read-write
    STATUS current
    DESCRIPTION
        "Indicates the number of programs that are to be mapped to the output
         transport stream.  One UDP port is opened for each program mapped to
         the output transport stream.
        "
::= { apexUdpMapBlade7Entry 3 }

apexUdpMapBlade7VirtualIpIndex OBJECT-TYPE
    SYNTAX Integer32(0..32)
    MAX-ACCESS read-write
    STATUS current
    DESCRIPTION
        "The index of the Virtual IP Table associated with this output TS. 
         This value is only used when configured for the 10-6 Modified UDP 
         Mapping Algorithm.  
         
         Range:
            '0'              = Not Applicable
            Virtual IP Index = 1-32 (valid IP must already be configured)
            
         The Virtual IP can only be selected when a GigE Input Interface index
         is not already selected. UDP port mappings will be assigned to either the
         configured Virtual IP or Physical GigE interface, but not both.
         
         When using a GigE Input Interface for UDP Port Mappings, this setting must be 
         set to 0. When Reporting UDP Port Mappings via RTSP D6, then the IP address is
         automatically allocated, and neither a Virtual IP or GigE interface can be
         selected. Both must be set to 0 in this case.
        "
::= { apexUdpMapBlade7Entry 4 }

apexUdpMapBlade7ConfOutputTsNum OBJECT-TYPE
    SYNTAX Integer32(0..1023)
    MAX-ACCESS read-write
    STATUS current
    DESCRIPTION
        "The configured output TS number for this output TS.  This value 
         is only used when configured for the 10-6 Modified UDP Mapping
         Algorithm.  Based on the 10-6 UDP Mapping Algorithm, this value 
         is used to calculate the UDP Port opened on the configured virtual 
         IP.  The upper 10 bits of the UDP port are based on this number
         and the lower 6 bits are based on the configured output program number.
        "
::= { apexUdpMapBlade7Entry 5 }

apexUdpMapBlade7ConfInputInterface OBJECT-TYPE
    SYNTAX Integer32(0..12)
    MAX-ACCESS read-write
    STATUS current
    DESCRIPTION
        "The configured GigE interface port number for this output TS.  This value 
         is only used when configured for the 10-6 Modified UDP Mapping
         Algorithm. The GigE interface can only be selected when a Virtual IP index
         is not already selected. UDP port mappings will be assigned to either the
         configured Virtual IP or Physical GigE interface, but not both.
         
         When using a Virtual IP for UDP Port Mappings, this setting must be set to
         0. When Reporting UDP Port Mappings via RTSP D6, then the IP address is
         automatically allocated, and neither a Virtual IP or GigE interface can be
         selected. Both must be set to 0 in this case.
         
         Range:
            '0'             = Not Applicable
            Input Interface = 1-12 (only interfaces in primary mode can be selected)
           
        "
::= { apexUdpMapBlade7Entry 6 }


-- ------------------------------------------------------------------------------
--
-- apexUdpMapBlade7MulticastTable
--

apexUdpMapBlade7MulticastTable OBJECT-TYPE
    SYNTAX SEQUENCE OF ApexUdpMapBlade7MulticastEntry
    MAX-ACCESS not-accessible
    STATUS current
    DESCRIPTION
        "Table of data for UDP Map Multicast. Each entry in
         this table identifies a Gigabit Ethernet input stream that is
         used for multicast UDP Port Mapping.
         
         Once written, the change to this table will only take immediate
         effect after apexUdpMapBlade7MulticastApplyChange is set to 'apply'.
         However, in order for the change to persist through subsequent
         reboots or power cycles, the change must be saved via apexSaveConfig.

         @Config(config=yes, reboot=no)
         @Commit(param=apexUdpMapBlade7MulticastApplyChange, value=2)
         @Save(apexSaveConfig, value=2)
         @File(udpmap.ini, type='ini')
        "
::= { apexUdpMapBlade7 3 }

apexUdpMapBlade7MulticastEntry OBJECT-TYPE
    SYNTAX ApexUdpMapBlade7MulticastEntry
    MAX-ACCESS not-accessible
    STATUS current
    DESCRIPTION
        "UDP Map Multicast Table Entry."
    INDEX { apexUdpMapBlade7MulticastIndex }
::= { apexUdpMapBlade7MulticastTable 1 }

ApexUdpMapBlade7MulticastEntry ::= SEQUENCE
    {
     apexUdpMapBlade7MulticastIndex           Integer32,
     apexUdpMapBlade7MulticastEnable          EnableDisableTYPE,
     apexUdpMapBlade7MulticastVirtualIpIndex  Integer32,
     apexUdpMapBlade7MulticastUdp             Integer32,
     apexUdpMapBlade7MulticastMcastIp         IpAddress,
     apexUdpMapBlade7MulticastSourceIp        IpAddress
    }

apexUdpMapBlade7MulticastIndex OBJECT-TYPE
    SYNTAX Integer32(1..256)
    MAX-ACCESS not-accessible
    STATUS current
    DESCRIPTION
        "Index of UDP Map Multicast Stream Table."
::= { apexUdpMapBlade7MulticastEntry 1 }

apexUdpMapBlade7MulticastEnable OBJECT-TYPE
    SYNTAX EnableDisableTYPE
    MAX-ACCESS read-write
    STATUS current
    DESCRIPTION
        "Indicates whether this UDP Map Multicast entry is enabled or disabled.
        "
::= { apexUdpMapBlade7MulticastEntry 2 }

apexUdpMapBlade7MulticastVirtualIpIndex OBJECT-TYPE
    SYNTAX Integer32(0..32)
    MAX-ACCESS read-write
    STATUS current
    DESCRIPTION
        "Index of the Virtual IP Table that corresponds to this entry.

         Range:
            '0'              = Not Applicable
            Virtual IP Index = 1-32
        "
::= { apexUdpMapBlade7MulticastEntry 3 }

apexUdpMapBlade7MulticastUdp OBJECT-TYPE
    SYNTAX Integer32(0..65535)
    MAX-ACCESS read-write
    STATUS current
    DESCRIPTION
        "GBE Input UDP Port.

         Range: 0-65535
        "
::= { apexUdpMapBlade7MulticastEntry 4 }

apexUdpMapBlade7MulticastMcastIp OBJECT-TYPE
    SYNTAX IpAddress
    MAX-ACCESS read-write
    STATUS current
    DESCRIPTION
        "The Multicast receive IP address.
         An IP address of 0.0.0.0 indicates singlecast only.

         Multicast IP addresses 224.0.0.0 to 224.0.0.255 are reserved.
        "
::= { apexUdpMapBlade7MulticastEntry 5 }

apexUdpMapBlade7MulticastSourceIp OBJECT-TYPE
    SYNTAX IpAddress
    MAX-ACCESS read-write
    STATUS current
    DESCRIPTION
        "This is the IP address of the source device. This field is only
         used when a multicast IP address is also specified.
        "
::= { apexUdpMapBlade7MulticastEntry 6 }


-- ------------------------------------------------------------------------------
--
-- apexUdpMapBlade7MulticastApplyTable
--

apexUdpMapBlade7MulticastApplyTable OBJECT-TYPE
    SYNTAX SEQUENCE OF ApexUdpMapBlade7MulticastApplyEntry
    MAX-ACCESS not-accessible
    STATUS current
    DESCRIPTION
        "Table of Apply Change for the UDP Map Multicast Table.

         A row in this table corresponds to the same row index in the
         UDP Map Multicast Table (apexUdpMapBlade7MulticastTable).
        "
::= { apexUdpMapBlade7 4 }

apexUdpMapBlade7MulticastApplyEntry OBJECT-TYPE
    SYNTAX ApexUdpMapBlade7MulticastApplyEntry
    MAX-ACCESS not-accessible
    STATUS current
    DESCRIPTION
        "UDP Map Multicast Apply Table Entry."
    INDEX { apexUdpMapBlade7MulticastApplyIndex }
::= { apexUdpMapBlade7MulticastApplyTable 1 }

ApexUdpMapBlade7MulticastApplyEntry ::= SEQUENCE
    {
     apexUdpMapBlade7MulticastApplyIndex  Integer32,
     apexUdpMapBlade7MulticastApplyChange ApplyDataToDeviceTYPE
    }

apexUdpMapBlade7MulticastApplyIndex OBJECT-TYPE
    SYNTAX Integer32(1..256)
    MAX-ACCESS not-accessible
    STATUS current
    DESCRIPTION
        "The index of the UDP Map Multicast Table."
::= { apexUdpMapBlade7MulticastApplyEntry 1 }

apexUdpMapBlade7MulticastApplyChange OBJECT-TYPE
    SYNTAX ApplyDataToDeviceTYPE
    MAX-ACCESS read-write
    STATUS current
    DESCRIPTION
        "The Apply for the row of data in the UDP Map Multicast Table.

         A row in this table corresponds to the same row index in the
         UDP Map Multicast Table.

         This parameter MUST be set to 'apply' in order for any of the data
         in the UDP Map Multicast Table row to take effect in the APEX.  This
         parameter MUST be set LAST after all other data in the UDP Map Multicast 
         Table row has been configured.

         @Config(config=no, reboot=no)
        "
::= { apexUdpMapBlade7MulticastApplyEntry 2 }


-- ------------------------------------------------------------------------------
--
-- apexUdpMapBlade8
--
-- apexUdpMapBlade8ApplyTable
--

apexUdpMapBlade8ApplyTable OBJECT-TYPE
    SYNTAX SEQUENCE OF ApexUdpMapBlade8ApplyEntry
    MAX-ACCESS not-accessible
    STATUS current
    DESCRIPTION
        "Table of Apply Change for the data for UDP Map Table.

         A row in this table corresponds to the same row index in the
         UDP Map table.
        "
::= { apexUdpMapBlade8 1 }

apexUdpMapBlade8ApplyEntry OBJECT-TYPE
    SYNTAX ApexUdpMapBlade8ApplyEntry
    MAX-ACCESS not-accessible
    STATUS current
    DESCRIPTION
        "UDP Map Apply Table Entry."
    INDEX { apexUdpMapBlade8ApplyOutputTsNum }
::= { apexUdpMapBlade8ApplyTable 1 }

ApexUdpMapBlade8ApplyEntry ::= SEQUENCE
    {
     apexUdpMapBlade8ApplyOutputTsNum   Integer32,
     apexUdpMapBlade8ApplyChange        ApplyDataToDeviceTYPE,
     apexUdpMapBlade8InvalidApplyText   DisplayString
    }

apexUdpMapBlade8ApplyOutputTsNum OBJECT-TYPE
    SYNTAX Integer32(1..256)
    MAX-ACCESS not-accessible
    STATUS current
    DESCRIPTION
        "The index of the Udp Map Apply Table."
::= { apexUdpMapBlade8ApplyEntry 1 }

apexUdpMapBlade8ApplyChange OBJECT-TYPE
    SYNTAX ApplyDataToDeviceTYPE
    MAX-ACCESS read-write
    STATUS current
    DESCRIPTION
        "The Apply for the row of data in the Udp Map Table.

         A row in this table corresponds to the same row index in the
         Udp Map table.

         This parameter MUST be set to 'apply' in order for any of the data
         in the Udp Map Table row to take effect in the APEX.  This
         parameter MUST be set LAST after all other data in the Udp Map
         Table row has been configured.

         @Config(config=no, reboot=no)
        "
::= { apexUdpMapBlade8ApplyEntry 2 }

apexUdpMapBlade8InvalidApplyText OBJECT-TYPE
    SYNTAX DisplayString (SIZE (0..80))
    MAX-ACCESS read-only
    STATUS current
    DESCRIPTION
        "When apexUdpMapBlade8ApplyChange is set to applyNotInProgressInvalidData
         this entry may contain a text description of what was wrong with the data.
         This entry contains the description for the most recent apply of a
         table entry that was invalid."
::= { apexUdpMapBlade8ApplyEntry 3 }


-- ------------------------------------------------------------------------------
--
-- apexUdpMapBlade8Table
--

apexUdpMapBlade8Table OBJECT-TYPE
    SYNTAX SEQUENCE OF ApexUdpMapBlade8Entry
    MAX-ACCESS not-accessible
    STATUS current
    DESCRIPTION
        "Table of data for Udp Mapping. There are
         256 rows per blade.  Each row corresponds to one QAM channel.

         Once written, the change to this table will only take immediate
         effect after apexUdpMapBlade8ApplyChange is set to 'apply'.
         However, in order for the change to persist through subsequent
         reboots or power cycles, the change must be saved via apexSaveConfig.

         @Config(config=yes, reboot=no)
         @Commit(param=apexUdpMapBlade8ApplyChange, value=2)
         @Save(apexSaveConfig, value=2)
         @File(udpmap.ini, type='ini')
        "
::= { apexUdpMapBlade8 2 }

apexUdpMapBlade8Entry OBJECT-TYPE
    SYNTAX ApexUdpMapBlade8Entry
    MAX-ACCESS not-accessible
    STATUS current
    DESCRIPTION
        "Udp Mapping Table Entry."
    INDEX { apexUdpMapBlade8OutputTsNum }
::= { apexUdpMapBlade8Table 1 }

ApexUdpMapBlade8Entry ::= SEQUENCE
    {
     apexUdpMapBlade8OutputTsNum        Integer32,
     apexUdpMapBlade8StartProgNum       Integer32,
     apexUdpMapBlade8NumberProgs        Integer32,
     apexUdpMapBlade8VirtualIpIndex     Integer32,
     apexUdpMapBlade8ConfOutputTsNum    Integer32,
     apexUdpMapBlade8ConfInputInterface Integer32
    }

apexUdpMapBlade8OutputTsNum OBJECT-TYPE
    SYNTAX Integer32(1..256)
    MAX-ACCESS not-accessible
    STATUS current
    DESCRIPTION
        "Index of Udp Mapping Table.
        "
::= { apexUdpMapBlade8Entry 1 }

apexUdpMapBlade8StartProgNum OBJECT-TYPE
    SYNTAX Integer32(1..255)
    MAX-ACCESS read-write
    STATUS current
    DESCRIPTION
        "Indicates the first program number in a sequential range of programs
         that are to be routed to the same output transport stream.
        "
::= { apexUdpMapBlade8Entry 2 }

apexUdpMapBlade8NumberProgs OBJECT-TYPE
    SYNTAX Integer32(0..200)
    MAX-ACCESS read-write
    STATUS current
    DESCRIPTION
        "Indicates the number of programs that are to be mapped to the output
         transport stream.  One UDP port is opened for each program mapped to
         the output transport stream.
        "
::= { apexUdpMapBlade8Entry 3 }

apexUdpMapBlade8VirtualIpIndex OBJECT-TYPE
    SYNTAX Integer32(0..32)
    MAX-ACCESS read-write
    STATUS current
    DESCRIPTION
        "The index of the Virtual IP Table associated with this output TS. 
         This value is only used when configured for the 10-6 Modified UDP 
         Mapping Algorithm.  
         
         Range:
            '0'              = Not Applicable
            Virtual IP Index = 1-32 (valid IP must already be configured)
            
         The Virtual IP can only be selected when a GigE Input Interface index
         is not already selected. UDP port mappings will be assigned to either the
         configured Virtual IP or Physical GigE interface, but not both.
         
         When using a GigE Input Interface for UDP Port Mappings, this setting must be 
         set to 0. When Reporting UDP Port Mappings via RTSP D6, then the IP address is
         automatically allocated, and neither a Virtual IP or GigE interface can be
         selected. Both must be set to 0 in this case.
        "
::= { apexUdpMapBlade8Entry 4 }

apexUdpMapBlade8ConfOutputTsNum OBJECT-TYPE
    SYNTAX Integer32(0..1023)
    MAX-ACCESS read-write
    STATUS current
    DESCRIPTION
        "The configured output TS number for this output TS.  This value 
         is only used when configured for the 10-6 Modified UDP Mapping
         Algorithm.  Based on the 10-6 UDP Mapping Algorithm, this value 
         is used to calculate the UDP Port opened on the configured virtual 
         IP.  The upper 10 bits of the UDP port are based on this number
         and the lower 6 bits are based on the configured output program number.
        "
::= { apexUdpMapBlade8Entry 5 }

apexUdpMapBlade8ConfInputInterface OBJECT-TYPE
    SYNTAX Integer32(0..12)
    MAX-ACCESS read-write
    STATUS current
    DESCRIPTION
        "The configured GigE interface port number for this output TS.  This value 
         is only used when configured for the 10-6 Modified UDP Mapping
         Algorithm. The GigE interface can only be selected when a Virtual IP index
         is not already selected. UDP port mappings will be assigned to either the
         configured Virtual IP or Physical GigE interface, but not both.
         
         When using a Virtual IP for UDP Port Mappings, this setting must be set to
         0. When Reporting UDP Port Mappings via RTSP D6, then the IP address is
         automatically allocated, and neither a Virtual IP or GigE interface can be
         selected. Both must be set to 0 in this case.
         
         Range:
            '0'             = Not Applicable
            Input Interface = 1-12 (only interfaces in primary mode can be selected)
           
        "
::= { apexUdpMapBlade8Entry 6 }


-- ------------------------------------------------------------------------------
--
-- apexUdpMapBlade8MulticastTable
--

apexUdpMapBlade8MulticastTable OBJECT-TYPE
    SYNTAX SEQUENCE OF ApexUdpMapBlade8MulticastEntry
    MAX-ACCESS not-accessible
    STATUS current
    DESCRIPTION
        "Table of data for UDP Map Multicast. Each entry in
         this table identifies a Gigabit Ethernet input stream that is
         used for multicast UDP Port Mapping.
         
         Once written, the change to this table will only take immediate
         effect after apexUdpMapBlade8MulticastApplyChange is set to 'apply'.
         However, in order for the change to persist through subsequent
         reboots or power cycles, the change must be saved via apexSaveConfig.

         @Config(config=yes, reboot=no)
         @Commit(param=apexUdpMapBlade8MulticastApplyChange, value=2)
         @Save(apexSaveConfig, value=2)
         @File(udpmap.ini, type='ini')
        "
::= { apexUdpMapBlade8 3 }

apexUdpMapBlade8MulticastEntry OBJECT-TYPE
    SYNTAX ApexUdpMapBlade8MulticastEntry
    MAX-ACCESS not-accessible
    STATUS current
    DESCRIPTION
        "UDP Map Multicast Table Entry."
    INDEX { apexUdpMapBlade8MulticastIndex }
::= { apexUdpMapBlade8MulticastTable 1 }

ApexUdpMapBlade8MulticastEntry ::= SEQUENCE
    {
     apexUdpMapBlade8MulticastIndex           Integer32,
     apexUdpMapBlade8MulticastEnable          EnableDisableTYPE,
     apexUdpMapBlade8MulticastVirtualIpIndex  Integer32,
     apexUdpMapBlade8MulticastUdp             Integer32,
     apexUdpMapBlade8MulticastMcastIp         IpAddress,
     apexUdpMapBlade8MulticastSourceIp        IpAddress
    }

apexUdpMapBlade8MulticastIndex OBJECT-TYPE
    SYNTAX Integer32(1..256)
    MAX-ACCESS not-accessible
    STATUS current
    DESCRIPTION
        "Index of UDP Map Multicast Stream Table."
::= { apexUdpMapBlade8MulticastEntry 1 }

apexUdpMapBlade8MulticastEnable OBJECT-TYPE
    SYNTAX EnableDisableTYPE
    MAX-ACCESS read-write
    STATUS current
    DESCRIPTION
        "Indicates whether this UDP Map Multicast entry is enabled or disabled.
        "
::= { apexUdpMapBlade8MulticastEntry 2 }

apexUdpMapBlade8MulticastVirtualIpIndex OBJECT-TYPE
    SYNTAX Integer32(0..32)
    MAX-ACCESS read-write
    STATUS current
    DESCRIPTION
        "Index of the Virtual IP Table that corresponds to this entry.

         Range:
            '0'              = Not Applicable
            Virtual IP Index = 1-32
        "
::= { apexUdpMapBlade8MulticastEntry 3 }

apexUdpMapBlade8MulticastUdp OBJECT-TYPE
    SYNTAX Integer32(0..65535)
    MAX-ACCESS read-write
    STATUS current
    DESCRIPTION
        "GBE Input UDP Port.

         Range: 0-65535
        "
::= { apexUdpMapBlade8MulticastEntry 4 }

apexUdpMapBlade8MulticastMcastIp OBJECT-TYPE
    SYNTAX IpAddress
    MAX-ACCESS read-write
    STATUS current
    DESCRIPTION
        "The Multicast receive IP address.
         An IP address of 0.0.0.0 indicates singlecast only.

         Multicast IP addresses 224.0.0.0 to 224.0.0.255 are reserved.
        "
::= { apexUdpMapBlade8MulticastEntry 5 }

apexUdpMapBlade8MulticastSourceIp OBJECT-TYPE
    SYNTAX IpAddress
    MAX-ACCESS read-write
    STATUS current
    DESCRIPTION
        "This is the IP address of the source device. This field is only
         used when a multicast IP address is also specified.
        "
::= { apexUdpMapBlade8MulticastEntry 6 }


-- ------------------------------------------------------------------------------
--
-- apexUdpMapBlade8MulticastApplyTable
--

apexUdpMapBlade8MulticastApplyTable OBJECT-TYPE
    SYNTAX SEQUENCE OF ApexUdpMapBlade8MulticastApplyEntry
    MAX-ACCESS not-accessible
    STATUS current
    DESCRIPTION
        "Table of Apply Change for the UDP Map Multicast Table.

         A row in this table corresponds to the same row index in the
         UDP Map Multicast Table (apexUdpMapBlade8MulticastTable).
        "
::= { apexUdpMapBlade8 4 }

apexUdpMapBlade8MulticastApplyEntry OBJECT-TYPE
    SYNTAX ApexUdpMapBlade8MulticastApplyEntry
    MAX-ACCESS not-accessible
    STATUS current
    DESCRIPTION
        "UDP Map Multicast Apply Table Entry."
    INDEX { apexUdpMapBlade8MulticastApplyIndex }
::= { apexUdpMapBlade8MulticastApplyTable 1 }

ApexUdpMapBlade8MulticastApplyEntry ::= SEQUENCE
    {
     apexUdpMapBlade8MulticastApplyIndex  Integer32,
     apexUdpMapBlade8MulticastApplyChange ApplyDataToDeviceTYPE
    }

apexUdpMapBlade8MulticastApplyIndex OBJECT-TYPE
    SYNTAX Integer32(1..256)
    MAX-ACCESS not-accessible
    STATUS current
    DESCRIPTION
        "The index of the UDP Map Multicast Table."
::= { apexUdpMapBlade8MulticastApplyEntry 1 }

apexUdpMapBlade8MulticastApplyChange OBJECT-TYPE
    SYNTAX ApplyDataToDeviceTYPE
    MAX-ACCESS read-write
    STATUS current
    DESCRIPTION
        "The Apply for the row of data in the UDP Map Multicast Table.

         A row in this table corresponds to the same row index in the
         UDP Map Multicast Table.

         This parameter MUST be set to 'apply' in order for any of the data
         in the UDP Map Multicast Table row to take effect in the APEX.  This
         parameter MUST be set LAST after all other data in the UDP Map Multicast 
         Table row has been configured.

         @Config(config=no, reboot=no)
        "
::= { apexUdpMapBlade8MulticastApplyEntry 2 }


-- ------------------------------------------------------------------------------
--
-- apexUdpMapVirtualIp
--
-- apexUdpMapVirtualIpTable
--

apexUdpMapVirtualIpTable OBJECT-TYPE
    SYNTAX SEQUENCE OF ApexUdpMapVirtualIpEntry
    MAX-ACCESS not-accessible
    STATUS current
    DESCRIPTION
        "Table of configuration data for UDP Map Virtual IP.
         
         The index into the Virtual IP table is fixed for each output stream 
         as follows:
            Virtual IP 1 - 8:
               Slots: 1 - 2 (64 output streams)
         
         Each Virtual IP covers 64 output streams spread over 8 output streams per RF Port. 

         Virtual IP 1 is mapped to Slot 1 and 2, OTS 1 - 8 of ports 1 - 4. 
         This corresponds to logical output streams (1 - 8, 65 - 72, 129 - 136, 193 - 200).
         
         Virtual IP 2 is mapped to Slot 1 and 2, OTS 9 - 16 of ports 1 - 4. 
         This corresponds to logical output streams (9 - 16, 73 - 80, 137 - 144, 201 - 208).
         
         For details, refer to users manual.
         Summary is below:
            - Virtual IP 1: QAM Blades 1-2, RF 1 - 4, Channels 1-8
            - Virtual IP 2: QAM Blades 1-2, RF 1 - 4, Channels 9-16
            - Virtual IP 3: QAM Blades 1-2, RF 1 - 4, Channels 17-24
            - Virtual IP 4: QAM Blades 1-2, RF 1 - 4, Channels 25-32
            - Virtual IP 5: QAM Blades 1-2, RF 1 - 4, Channels 33-40
            - Virtual IP 6: QAM Blades 1-2, RF 1 - 4, Channels 41-48
            - Virtual IP 7: QAM Blades 1-2, RF 1 - 4, Channels 49-56 (not used in release 1)
            - Virtual IP 8: QAM Blades 1-2, RF 1 - 4, Channels 57-64 (not used in release 1)
            - Virtual IP 9: QAM Blades 3-4, RF 1 - 4, Channels 1-8
            - Virtual IP 10: QAM Blades 3-4, RF 1 - 4, Channels 9-16
            - Virtual IP 11: QAM Blades 3-4, RF 1 - 4, Channels 17-24
            - Virtual IP 12: QAM Blades 3-4, RF 1 - 4, Channels 25-32
            - Virtual IP 13: QAM Blades 3-4, RF 1 - 4, Channels 33-40
            - Virtual IP 14: QAM Blades 3-4, RF 1 - 4, Channels 41-48
            - Virtual IP 15: QAM Blades 3-4, RF 1 - 4, Channels 49-56 (not used in release 1)
            - Virtual IP 16: QAM Blades 3-4, RF 1 - 4, Channels 57-64 (not used in release 1)
            - Virtual IPs 17-32 continue with Blades 5-8
         
         Once written, the change to this table will only take immediate
         effect after apexUdpMapVirtualIpApplyChange is set to 'apply'.
         However, in order for the change to persist through subsequent
         reboots or power cycles, the change must be saved via apexSaveConfig.

         @Config(config=yes, reboot=no)
         @Commit(param=apexUdpMapVirtualIpApplyChange, value=2)
         @Save(apexSaveConfig, value=2)
         @File(udpmap.ini, type='ini')
        "
::= { apexUdpMapVirtualIp 1 }

apexUdpMapVirtualIpEntry OBJECT-TYPE
    SYNTAX ApexUdpMapVirtualIpEntry
    MAX-ACCESS not-accessible
    STATUS current
    DESCRIPTION
        "UDP Map Virtual IP Table Entry."
    INDEX { apexUdpMapVirtualIpIndex }
::= { apexUdpMapVirtualIpTable 1 }

ApexUdpMapVirtualIpEntry ::= SEQUENCE
    {
     apexUdpMapVirtualIpIndex           Integer32,
     apexUdpMapVirtualIpInputInterface  Integer32,
     apexUdpMapVirtualIpAddress         IpAddress
    }

apexUdpMapVirtualIpIndex OBJECT-TYPE
    SYNTAX Integer32(1..32)
    MAX-ACCESS not-accessible
    STATUS current
    DESCRIPTION
        "Index of UDP Map Virtual IP Table.
        
         Range:
            '0'              = Not Applicable
            Virtual IP Index = 1-32
        "
::= { apexUdpMapVirtualIpEntry 1 }

apexUdpMapVirtualIpInputInterface OBJECT-TYPE
    SYNTAX Integer32(0..12)
    MAX-ACCESS read-write
    STATUS current
    DESCRIPTION
        "Input interface assigned to this Virtual IP. An entry of 0
         means that this virtual IP row is not used. 

         Range:
            '0'             = Not Applicable
            Input Interface = 1-12
        "
::= { apexUdpMapVirtualIpEntry 2 }

apexUdpMapVirtualIpAddress OBJECT-TYPE
    SYNTAX IpAddress
    MAX-ACCESS read-write
    STATUS current
    DESCRIPTION
        "Virtual IP address (0.0.0.0 or valid Class A, B, or C address).
         This setting is only applicable when the interface setting is
         non-zero.
        "
::= { apexUdpMapVirtualIpEntry 3 }


-- ------------------------------------------------------------------------------
--
-- apexUdpMapStatus
--
-- apexUdpMapStatusGeneral
--

apexUdpMapVirtualIpInvalidApplyText OBJECT-TYPE
    SYNTAX DisplayString (SIZE (0..80))
    MAX-ACCESS read-only
    STATUS current
    DESCRIPTION
        "When apexUdpMapVirtualIpApplyChange is set to 
         applyNotInProgressInvalidData, this entry may contain a text description 
         of what was wrong with the data. This entry contains the description for 
         the most recent apply of a related entry that was invalid. 
        "
::= { apexUdpMapStatusGeneral 1 }

apexUdpMapAlgorithmApplyText OBJECT-TYPE
    SYNTAX DisplayString (SIZE (0..80))
    MAX-ACCESS read-only
    STATUS current
    DESCRIPTION
        "When UDP Mapping algorithm is configured, this entry may contain a text 
         description of what was wrong with the data. If algorithm change was 
         valid, this description is set to null string. This entry contains the 
         description for the most recent change of the UDP mapping algorithm.. 
        "
::= { apexUdpMapStatusGeneral 2 }


-- ------------------------------------------------------------------------------
--
-- apexUdpMapStatusTable
--
       
apexUdpMapStatusTable OBJECT-TYPE
    SYNTAX SEQUENCE OF ApexUdpMapStatusEntry
    MAX-ACCESS not-accessible
    STATUS current
    DESCRIPTION
        "Table of status data for UDP Map Status Table. 
         Indexed by Blade Number and Output Transport Stream number.
        "
::= { apexUdpMapStatus 2 }

apexUdpMapStatusEntry OBJECT-TYPE
    SYNTAX ApexUdpMapStatusEntry
    MAX-ACCESS not-accessible
    STATUS current
    DESCRIPTION
        "Udp Map Status Table Entry."
    INDEX { apexUdpMapStatusBladeNum, apexUdpMapStatusOutputTsNum }
::= { apexUdpMapStatusTable 1 }

ApexUdpMapStatusEntry ::= SEQUENCE
    {
     apexUdpMapStatusBladeNum               Integer32,
     apexUdpMapStatusOutputTsNum            Integer32,
     apexUdpMapStatusStartUdpPort           Integer32,
     apexUdpMapStatusAssignedOutputTsNum    Integer32,
     apexUdpMapStatusNumberPrograms         Integer32
    }

apexUdpMapStatusBladeNum OBJECT-TYPE
    SYNTAX Integer32(1..8)
    MAX-ACCESS not-accessible
    STATUS current
    DESCRIPTION
        "Blade Number."
::= { apexUdpMapStatusEntry 1 }

apexUdpMapStatusOutputTsNum OBJECT-TYPE
    SYNTAX Integer32 (1..256)
    MAX-ACCESS not-accessible
    STATUS current
    DESCRIPTION
        "Output Transport Stream Number."
::= { apexUdpMapStatusEntry 2 }

apexUdpMapStatusStartUdpPort OBJECT-TYPE
    SYNTAX Integer32 (0..65536)
    MAX-ACCESS read-only
    STATUS current
    DESCRIPTION
        "Starting UDP port number.  Value of zero is used for OTSs that are not 
         configured for UDP Mapping mode."
::= { apexUdpMapStatusEntry 3 }

apexUdpMapStatusAssignedOutputTsNum OBJECT-TYPE
    SYNTAX Integer32 (0..1024)
    MAX-ACCESS read-only
    STATUS current
    DESCRIPTION
        "Assigned Output Transport Stream Number based on UDP Mapping mode.
         This number is used to calculate the starting UDP Port number."
::= { apexUdpMapStatusEntry 4 }

apexUdpMapStatusNumberPrograms OBJECT-TYPE
    SYNTAX Integer32
    MAX-ACCESS read-only
    STATUS current
    DESCRIPTION
        "Number of UDP Port Mapping programs assigned to this output."
::= { apexUdpMapStatusEntry 5 }       


-- ------------------------------------------------------------------------------
--
-- apexUdpMapStatusMulticastTable
--

apexUdpMapStatusMulticastTable OBJECT-TYPE
    SYNTAX SEQUENCE OF ApexUdpMapStatusMulticastEntry
    MAX-ACCESS not-accessible
    STATUS current
    DESCRIPTION
        "Table of status data for UDP Map Multicast Table. 
         There is 1 row for each blade.
        "
::= { apexUdpMapStatus 3 }

apexUdpMapStatusMulticastEntry OBJECT-TYPE
    SYNTAX ApexUdpMapStatusMulticastEntry
    MAX-ACCESS not-accessible
    STATUS current
    DESCRIPTION
        "Udp Map Multicast Status Table Entry."
    INDEX { apexUdpMapMulticastBladeNum }
::= { apexUdpMapStatusMulticastTable 1 }

ApexUdpMapStatusMulticastEntry ::= SEQUENCE
    {
     apexUdpMapMulticastBladeNum            Integer32,
     apexUdpMapMulticastInvalidApplyText    DisplayString
    }

apexUdpMapMulticastBladeNum OBJECT-TYPE
    SYNTAX Integer32(1..8)
    MAX-ACCESS not-accessible
    STATUS current
    DESCRIPTION
        "Blade Number."
::= { apexUdpMapStatusMulticastEntry 1 }

apexUdpMapMulticastInvalidApplyText OBJECT-TYPE
    SYNTAX DisplayString (SIZE (0..80))
    MAX-ACCESS read-only
    STATUS current
    DESCRIPTION
        "When apexUdpMapBlade#MulticastApplyChange is set to applyNotInProgressInvalidData,
         this entry may contain a text description of what was wrong with the data.
         This entry contains the description for the most recent apply
         of a related entry that was invalid. 
        "
::= { apexUdpMapStatusMulticastEntry 2 }


-- ------------------------------------------------------------------------------
--
-- apexUdpMapVirtualIpInputTsAssignedTable     
--

apexUdpMapVirtualIpInputTsAssignedTable OBJECT-TYPE
    SYNTAX SEQUENCE OF ApexUdpMapVirtualIpInputTsAssignedEntry
    MAX-ACCESS not-accessible
    STATUS current
    DESCRIPTION
        "Table of Gigabit Ethernet Virtual IP Input TS Assigned data.
        "
::= { apexUdpMapStatus 4 }

apexUdpMapVirtualIpInputTsAssignedEntry OBJECT-TYPE
    SYNTAX ApexUdpMapVirtualIpInputTsAssignedEntry
    MAX-ACCESS not-accessible
    STATUS current
    DESCRIPTION
        "Gigabit Ethernet Interface Virtual IP Input TS Assigned Table Entry."
    INDEX { apexUdpMapVirtualIpInputTsIndex }
::= { apexUdpMapVirtualIpInputTsAssignedTable 1 }

ApexUdpMapVirtualIpInputTsAssignedEntry ::= SEQUENCE
    {
     apexUdpMapVirtualIpInputTsIndex         Integer32,
     apexUdpMapVirtualIpInputTsAssignedCount Counter32
    }

apexUdpMapVirtualIpInputTsIndex OBJECT-TYPE
    SYNTAX Integer32(1..32)
    MAX-ACCESS not-accessible
    STATUS current
    DESCRIPTION
        "Index of UDP Map Virtual IP Table.
        
         Range:
            '0'              = Not Applicable
            Virtual IP Index = 1-32
        "
::= { apexUdpMapVirtualIpInputTsAssignedEntry 1 }

apexUdpMapVirtualIpInputTsAssignedCount OBJECT-TYPE
    SYNTAX Counter32
    MAX-ACCESS read-only
    STATUS current
    DESCRIPTION
        "Number of input transport streams assigned to the Virtual IP. 
         This is a count of inputs assigned for the UDP Port Mapping inputs
         that are associated with Virtual IP inputs.  
        "
::= { apexUdpMapVirtualIpInputTsAssignedEntry 2 }


-- ------------------------------------------------------------------------------
--
-- apexRds
--
-- apexRdsConfig
--
-- apexRdsConfigGeneral
--

apexRdsIpAddr OBJECT-TYPE
    SYNTAX IpAddress
    MAX-ACCESS read-write
    STATUS current
    DESCRIPTION
        "Rights Data Server IP address.  Class A, B, or C IP address of the RDS.
         Changing this parameter will cause the APEX to perform an EMM rollover
         sequence.

         This parameter is not changed by apexRdsSetDefault.

         Once written, the change to this parameter will only take immediate
         effect after apexRdsConfigApplyChange is set to 'apply'.  In
         order for the change to persist through subsequent reboots or power
         cycles, the change must be saved via apexSaveConfig.

         @Config(config=yes, reboot=no)
         @Commit(param=apexRdsConfigApplyChange, value=2)
         @Save(apexSaveConfig, value=2)
         @File(config.ini, type='ini')
        "
    ::= { apexRdsConfigGeneral 1 }

apexRdsTcpPort OBJECT-TYPE
    SYNTAX Integer32(0..65535)
    MAX-ACCESS read-write
    STATUS current
    DESCRIPTION
        "Rights Data Server TCP port.
         Changing this parameter will cause the APEX to perform an EMM rollover
         sequence.

         Once written, the change to this parameter will only take immediate
         effect after apexRdsConfigApplyChange is set to 'apply'.  In
         order for the change to persist through subsequent reboots or power
         cycles, the change must be saved via apexSaveConfig.

         @Config(config=yes, reboot=no)
         @Commit(param=apexRdsConfigApplyChange, value=2)
         @Save(apexSaveConfig, value=2)
         @File(config.ini, type='ini')
        "
    ::= { apexRdsConfigGeneral 2 }

apexRdsProgramEpochDuration OBJECT-TYPE
    SYNTAX Integer32(60..1440)
    MAX-ACCESS read-write
    STATUS current
    DESCRIPTION
        "The Program Epoch Duration in minutes.  Changes are not
         applied until the end of the current epoch.

         Once written, the change to this parameter will only take immediate
         effect after apexRdsConfigApplyChange is set to 'apply'.  In
         order for the change to persist through subsequent reboots or power
         cycles, the change must be saved via apexSaveConfig.

         @Config(config=yes, reboot=no)
         @Commit(param=apexRdsConfigApplyChange, value=2)
         @Save(apexSaveConfig, value=2)
         @File(config.ini, type='ini')
        "
    ::= { apexRdsConfigGeneral 3 }

apexRdsCetPollInterval OBJECT-TYPE
    SYNTAX Integer32(15..1440)
    MAX-ACCESS read-write
    STATUS current
    DESCRIPTION
        "Interval that the APEX will use to poll for CSN/State information.
         After receiving the CSN/State information, the APEX will determine if it
         needs to retrieve new EMMs.

         Once written, the change to this parameter will only take immediate
         effect after apexRdsConfigApplyChange is set to 'apply'.  In
         order for the change to persist through subsequent reboots or power
         cycles, the change must be saved via apexSaveConfig.

         @Config(config=yes, reboot=no)
         @Commit(param=apexRdsConfigApplyChange, value=2)
         @Save(apexSaveConfig, value=2)
         @File(config.ini, type='ini')
        "
    ::= { apexRdsConfigGeneral 4 }

apexRdsCetRefresh OBJECT-TYPE
    SYNTAX INTEGER
        {
         refreshNotInProgress   (1),
         refresh                (2)
        }
    MAX-ACCESS read-write
    STATUS current
    DESCRIPTION
        "Setting to 'refresh' forces the APEX to retrieve new
         EMMs (APEX performs an EMM rollover sequence).

         Once written, the change to this parameter will take effect immediately.

         @Config(config=no, reboot=no)
        "
    ::= { apexRdsConfigGeneral 5 }

apexRdsRmdPollInterval OBJECT-TYPE
    SYNTAX Integer32(15..1440)
    MAX-ACCESS read-write
    STATUS current
    DESCRIPTION
        "Interval that the APEX will use to poll for RMD information.

         Once written, the change to this parameter will only take immediate
         effect after apexRdsConfigApplyChange is set to 'apply'.  In
         order for the change to persist through subsequent reboots or power
         cycles, the change must be saved via apexSaveConfig.

         @Config(config=yes, reboot=no)
         @Commit(param=apexRdsConfigApplyChange, value=2)
         @Save(apexSaveConfig, value=2)
         @File(config.ini, type='ini')
        "
    ::= { apexRdsConfigGeneral 6 }

apexRdsRmdRefresh OBJECT-TYPE
    SYNTAX INTEGER
        {
         refreshNotInProgress   (1),
         refresh                (2)
        }
    MAX-ACCESS read-write
    STATUS current
    DESCRIPTION
        "Setting to 'refresh' forces the APEX to retrieve new
         EMMs (APEX performs an EMM rollover sequence).

         Once written, the change to this parameter will take effect immediately.

         @Config(config=no, reboot=no)
        "
    ::= { apexRdsConfigGeneral 7 }

apexRdsPollRandomization OBJECT-TYPE
    SYNTAX Integer32(0..10)
    MAX-ACCESS read-write
    STATUS current
    DESCRIPTION
        "RDS Polling Randomization Time.  Maximum time in minutes to delay
         polling at startup in order to avoid having many APEXs polling the
         RDS simultaneously.  The actual delay time will be
         randomly calculated by the APEX and will be no greater than this value.
         A value of zero means no delay and the APEX will poll immediately at
         startup.

         Once written, the change to this parameter will only take immediate
         effect after apexRdsConfigApplyChange is set to 'apply'.  In
         order for the change to persist through subsequent reboots or power
         cycles, the change must be saved via apexSaveConfig.

         @Config(config=yes, reboot=no)
         @Commit(param=apexRdsConfigApplyChange, value=2)
         @Save(apexSaveConfig, value=2)
         @File(config.ini, type='ini')
        "
    ::= { apexRdsConfigGeneral 8 }

apexRdsSetDefault OBJECT-TYPE
    SYNTAX INTEGER
        {
         notSettingToDefault (1),
         setToDefault        (2)
        }
    MAX-ACCESS read-write
    STATUS current
    DESCRIPTION
        "This parameter sets apexRdsCetPollInterval, apexRdsPollRandomization,
         apexRdsTcpPort, apexRdsRmdPollInterval and apexRdsProgramEpochDuration
         to default values.

         Once written, the change to this parameter will take effect immediately.

         @Config(config=no, reboot=no)
        "
::= { apexRdsConfigGeneral 9 }

apexRdsErrorCountReset OBJECT-TYPE
    SYNTAX ResetStatisticsTYPE
    MAX-ACCESS read-write
    STATUS current
    DESCRIPTION
        "Resets RDS Communication error counts.

         Once written, the change to this parameter will take effect immediately.

         @Config(config=no, reboot=no)
        "
::= { apexRdsConfigGeneral 10 }

apexRdsConfigApplyChange OBJECT-TYPE
    SYNTAX ApplyDataToDeviceTYPE
    MAX-ACCESS read-write
    STATUS current
    DESCRIPTION
        "The Apply for RDS configuration items. This parameter
         MUST be set to 'apply' in order for any of the following to
         take effect:
            apexRdsIpAddr
            apexRdsTcpPort
            apexRdsPollRandomization
            apexRdsCetPollInterval
            apexRdsRmdPollInterval
            apexRdsProgramEpochDuration

         This parameter MUST be set LAST after all associated parameters
         has been configured.

         @Config(config=no, reboot=no)
        "
::= { apexRdsConfigGeneral 11 }


-- ------------------------------------------------------------------------------
--
-- apexRdsStatus
--
-- apexRdsStatusGeneral
--

apexRdsConnectionStatus OBJECT-TYPE
    SYNTAX INTEGER
        {
         notConnectedInHoldoff            (1),
         notConnectedNoRdsIpAddress       (2),
         csnAquisitionSuccessful          (3),
         emmAquisitionSuccessful          (4),
         serviceListAquisitionSuccessful  (5),
         rmdAquisitionSuccessful          (6),
         csnAquisitionFailed              (7),
         emmAquisitionFailed              (8),
         serviceListAquisitionFailed      (9),
         rmdAquisitionFailed              (10)
        }
    MAX-ACCESS read-only
    STATUS current
    DESCRIPTION
        "Rights Data Server connection status."
::= { apexRdsStatusGeneral 1 }

apexRdsCurrentCsn OBJECT-TYPE
    SYNTAX Integer32(0..255)
    MAX-ACCESS read-only
    STATUS current
    DESCRIPTION
        "This is the current CSN that the APEX is
         using for encrypting all programs."
::= { apexRdsStatusGeneral 2 }

apexRdsCetNextPollTime OBJECT-TYPE
    SYNTAX Integer32
    MAX-ACCESS read-only
    STATUS current
    DESCRIPTION
        "Time in seconds until the next CET polling period."
::= { apexRdsStatusGeneral 3 }

apexRdsRmdNextPollTime OBJECT-TYPE
    SYNTAX Integer32
    MAX-ACCESS read-only
    STATUS current
    DESCRIPTION
        "Time in seconds until the next RMD polling period."
::= { apexRdsStatusGeneral 4 }

apexRdsEmmStatusTableSize OBJECT-TYPE
    SYNTAX Integer32
    MAX-ACCESS read-only
    STATUS current
    DESCRIPTION
        "EMM Status Table Size.  This is the maximum number of rows in the EMM Status
         Table and is the limit on apexRdsEmmStatusIndex."
::= { apexRdsStatusGeneral 5 }

apexRdsProgramMessagesReceived OBJECT-TYPE
    SYNTAX Counter32
    MAX-ACCESS read-only
    STATUS current
    DESCRIPTION
        "Number of successful ServiceEncrypt messages received in the last 15 minutes."
::= { apexRdsStatusGeneral 6 }

apexRdsProgramMessagesFailed OBJECT-TYPE
    SYNTAX Counter32
    MAX-ACCESS read-only
    STATUS current
    DESCRIPTION
        "Number of failed ServiceEncrypt messages received in the last 15 minutes."
::= { apexRdsStatusGeneral 7 }

apexRdsCommErrorCount OBJECT-TYPE
    SYNTAX Counter32
    MAX-ACCESS read-only
    STATUS current
    DESCRIPTION
        "Count of total server communication errors.
         This parameter is set to 0 when the APEX boots up."
::= { apexRdsStatusGeneral 8 }

apexRdsCommStatus OBJECT-TYPE
    SYNTAX INTEGER
        {
         notApplicable (0),
         ok            (1),
         error         (2)
        }
    MAX-ACCESS read-only
    STATUS current
    DESCRIPTION
        "Status of communication with RDS."
::= { apexRdsStatusGeneral 9 }

apexRdsFlashWriteCount OBJECT-TYPE
    SYNTAX Counter32
    MAX-ACCESS read-only
    STATUS current
    DESCRIPTION
        "Running count of the number of flash memory erasures/writes."
::= { apexRdsStatusGeneral 10 }

apexRdsMcast16 OBJECT-TYPE
    SYNTAX Unsigned32
    MAX-ACCESS read-only
    STATUS current
    DESCRIPTION
        "Multicast-16 bit address used for build PRK messages. The
         multicast-16 bit address is from the EMMs received."
::= { apexRdsStatusGeneral 11 }


-- ------------------------------------------------------------------------------
--
-- apexRdsEmmStatusTable
--

apexRdsEmmStatusTable OBJECT-TYPE
    SYNTAX SEQUENCE OF ApexRdsEmmStatusEntry
    MAX-ACCESS not-accessible
    STATUS current
    DESCRIPTION
        " Table of the most recent RDS responses."
::= { apexRdsStatus 2 }

apexRdsEmmStatusEntry OBJECT-TYPE
    SYNTAX ApexRdsEmmStatusEntry
    MAX-ACCESS not-accessible
    STATUS current
    DESCRIPTION
        "RDS EMM Status Table Entry."
    INDEX { apexRdsEmmStatusIndex }
::= { apexRdsEmmStatusTable 1 }

ApexRdsEmmStatusEntry ::= SEQUENCE
    {
     apexRdsEmmStatusIndex        Integer32,
     apexRdsEmmStatusCsn          Integer32,
     apexRdsEmmStatusState        INTEGER,
     apexRdsEmmStatusGpsTime      Integer32,
     apexRdsEmmStatusServerError  Unsigned32,
     apexRdsEmmStatusUnitAddress  DisplayString
    }

apexRdsEmmStatusIndex OBJECT-TYPE
    SYNTAX Integer32
    MAX-ACCESS not-accessible
    STATUS current
    DESCRIPTION
        "Index of EMM Status Table.
         Size of table can be found in apexRdsEmmStatusTableSize."
::= { apexRdsEmmStatusEntry 1 }

apexRdsEmmStatusCsn OBJECT-TYPE
    SYNTAX Integer32(0..255)
    MAX-ACCESS read-only
    STATUS current
    DESCRIPTION
        "Category Sequence Number (CSN). "
::= { apexRdsEmmStatusEntry 2 }

apexRdsEmmStatusState OBJECT-TYPE
    SYNTAX INTEGER
        {
         transitionComplete (1),
         transitionStart    (2),
         startOfNewEpoch    (3)
        }
    MAX-ACCESS read-only
    STATUS current
    DESCRIPTION
        "Category Epoch Transition (CET) State."
::= { apexRdsEmmStatusEntry 3 }

apexRdsEmmStatusGpsTime OBJECT-TYPE
    SYNTAX Integer32
    MAX-ACCESS read-only
    STATUS current
    DESCRIPTION
        "This is the time in GPS seconds that this row was written."
::= { apexRdsEmmStatusEntry 4 }

apexRdsEmmStatusServerError OBJECT-TYPE
    SYNTAX Unsigned32
    MAX-ACCESS read-only
    STATUS current
    DESCRIPTION
        "This is the error code reported to the APEX by
         the RDS.  Zero indicates no error."
::= { apexRdsEmmStatusEntry 5 }

apexRdsEmmStatusUnitAddress OBJECT-TYPE
    SYNTAX DisplayString (SIZE (20))
    MAX-ACCESS read-only
    STATUS current
    DESCRIPTION
        "This is the ACP address of the ACP associated
         with the error reported in apexRdsEmmStatusServerError.
         If no address is contained in this entry, the error
         applies to all ACPs or to the entire APEX.

         The address is made up of decimal digits formatted as
         ###-#####-#####-###."
::= { apexRdsEmmStatusEntry 6 }


-- ------------------------------------------------------------------------------
--
-- apexRdsSourceLookupTable
--

apexRdsSourceLookupTable OBJECT-TYPE
    SYNTAX SEQUENCE OF ApexRdsSourceLookupEntry
    MAX-ACCESS not-accessible
    STATUS current
    DESCRIPTION
        "This table provides a list of Source IDs and Provider IDs along
         with an associated string.  This table of information is provided by the
         RDS to make it easier for a user to determine the Source
         ID and Provider ID for a particular service.
        "
::= { apexRdsStatus  3 }

apexRdsSourceLookupEntry OBJECT-TYPE
    SYNTAX ApexRdsSourceLookupEntry
    MAX-ACCESS not-accessible
    STATUS current
    DESCRIPTION
        "Source Lookup Table Entry."
    INDEX { apexRdsSourceLookupIndex }
::= { apexRdsSourceLookupTable 1 }

ApexRdsSourceLookupEntry ::= SEQUENCE
    {
     apexRdsSourceLookupIndex         Integer32,
     apexRdsSourceLookupDescription   DisplayString,
     apexRdsSourceLookupSourceId      Integer32,
     apexRdsSourceLookupProviderId    Integer32
    }

apexRdsSourceLookupIndex OBJECT-TYPE
    SYNTAX Integer32
    MAX-ACCESS not-accessible
    STATUS current
    DESCRIPTION
        "Source Lookup Table Index."
::= { apexRdsSourceLookupEntry 1 }

apexRdsSourceLookupDescription OBJECT-TYPE
    SYNTAX DisplayString
    MAX-ACCESS read-only
    STATUS current
    DESCRIPTION
        "Text Description of the service provided by the Rights Data Server."
::= { apexRdsSourceLookupEntry 2 }

apexRdsSourceLookupSourceId OBJECT-TYPE
    SYNTAX Integer32
    MAX-ACCESS read-only
    STATUS current
    DESCRIPTION
        "Source Id of the service."
::= { apexRdsSourceLookupEntry 3 }

apexRdsSourceLookupProviderId OBJECT-TYPE
    SYNTAX Integer32
    MAX-ACCESS read-only
    STATUS current
    DESCRIPTION
        "Provider Id of the service."
::= { apexRdsSourceLookupEntry 4 }


-- ------------------------------------------------------------------------------
--
-- apexEncryption
--
-- apexEncryptionConfig
--
-- apexEncryptionConfigGeneral

-- none


-- ------------------------------------------------------------------------------
--
--  apexEncryptionConfTable
--

apexEncryptionConfTable OBJECT-TYPE
    SYNTAX SEQUENCE OF ApexEncryptionConfEntry
    MAX-ACCESS not-accessible
    STATUS current
    DESCRIPTION
        "This table shows the Encryption Algorithm Per QAM Blade."
::= { apexEncryptionConfigGeneral 2 }

apexEncryptionConfEntry OBJECT-TYPE
    SYNTAX ApexEncryptionConfEntry
    MAX-ACCESS not-accessible
    STATUS current
    DESCRIPTION
        "Encryption Algorithm Configuration Table."
    INDEX { apexEncrytionConfBladeNum }
::= { apexEncryptionConfTable 1 }

ApexEncryptionConfEntry ::= SEQUENCE
    {
     apexEncrytionConfBladeNum      Integer32,
     apexEncryptionConfAlgorithm    INTEGER
    }

apexEncrytionConfBladeNum OBJECT-TYPE
    SYNTAX Integer32(1..8)
    MAX-ACCESS not-accessible
    STATUS current
    DESCRIPTION
        "Blade Number."
::= { apexEncryptionConfEntry 1 }

apexEncryptionConfAlgorithm OBJECT-TYPE
    SYNTAX INTEGER
        {
          des-dcii           (1),
          des-scte-52        (2),
          dvb-csa            (3)
        }
    MAX-ACCESS read-write
    STATUS current
    DESCRIPTION
        "Configured encryption algorithm for the QAM blade.  

         Once written, a save must be performed via the apexSaveConfig.

         @Config(config=yes, reboot=no)
         @Save(apexSaveConfig, value=2)
         @File(config.ini, type='ini')
        "
::= { apexEncryptionConfEntry 2 }


-- ------------------------------------------------------------------------------
--
-- apexCteConfig
--

apexCteEncryptionMode  OBJECT-TYPE
    SYNTAX INTEGER
        {
         full  (1),
         fwk   (2),
         fpk   (3),
         clear (4)
        }
    MAX-ACCESS read-write
    STATUS current
    DESCRIPTION
        "This parameter is used to set the Encryption Mode.  It applies
         to all services on all QAMs in CTE mode.

           - 'full'  - The APEX will use Full encryption. The APEX will only be able to
                       encrypt programs in Full encryption mode if the APEX is able to
                       communicate with an RDS.

           - 'fwk'   - The APEX will use Fixed Working Key (FWK) encryption.

           - 'fpk'   - The APEX will use Fixed Program Key (FPK) encryption. The APEX
                       will not attempt to get EMMs.

           - 'clear' - The APEX performs no encryption of output programs.

         If the APEX is unable to encrypt programs in the configured mode, then those
         programs will not be mapped.

         Once written, the change to this parameter will only take immediate
         effect after apexCteApplyChange is set to 'apply'.  In
         order for the change to persist through subsequent reboots or power
         cycles, the change must be saved via the apexSaveConfig parameter.

         @Config(config=yes, reboot=no)
         @Commit(param=apexCteApplyChange, value=2)
         @Save(apexSaveConfig, value=2)
         @File(config.ini, type='ini')
        "
::= { apexCteConfig 1 }

apexCteCciLevel OBJECT-TYPE
    SYNTAX INTEGER
        {
         notDefined   (1),
         copyFreely   (2),
         copyOnce     (3),
         copyNever    (4),
         noMoreCopies (5)
        }
    MAX-ACCESS read-write
    STATUS current
    DESCRIPTION
        "Copy Control Information (CCI) Level setting for PRK messages.
           - notDefined   - CCI is not defined, settop box applications can
                           configure CCI
           - copyFreely   - program can be copied
           - copyOnce     - program can be copied once
           - copyNever    - program can never be copied
           - noMoreCopies -

         Once written, the change to this parameter will only take immediate
         effect after apexCteApplyChange is set to 'apply'.  In
         order for the change to persist through subsequent reboots or power
         cycles, the change must be saved via the apexSaveConfig parameter.

         @Config(config=yes, reboot=no)
         @Commit(param=apexCteApplyChange, value=2)
         @Save(apexSaveConfig, value=2)
         @File(config.ini, type='ini')
        "
::= { apexCteConfig 2 }

apexCteApsLevel OBJECT-TYPE
    SYNTAX INTEGER
        {
         notDefined       (1),
         off              (2),
         splitBurstOff    (3),
         splitBurst2Line  (4),
         splitBurst4Line  (5)
        }
    MAX-ACCESS read-write
    STATUS current
    DESCRIPTION
        "Analog Protection System (APS)
         Level setting for PRK messages.  Defines what copy protection encoding
         will be applied to the analog composite output by the settop box.
           - notDefined      - analog protection is not defined, settop box
                               applications can configure APS
           - off             - no analog protection
           - splitBurstOff   - AGC on, split burst off
           - splitBurst2Line - AGC on, 2 line split burst on
           - splitBurst4Line - AGC on, 4 line split burst on

         The APEX will set Tier Type based on apexCteApsLevel.
         The APEX will set tier type to subscription with right to tape
         when apexCteApsLevel is 'off' or 'notDefined'.
         The APEX will set tier type to subscription without right to tape when
         apexCteApsLevel is 'splitBurstOff', 'splitBurst2Line', or 'splitBurst4Line'.

         Once written, the change to this parameter will only take immediate
         effect after apexCteApplyChange is set to 'apply'.  In
         order for the change to persist through subsequent reboots or power
         cycles, the change must be saved via the apexSaveConfig parameter.

         @Config(config=yes, reboot=no)
         @Commit(param=apexCteApplyChange, value=2)
         @Save(apexSaveConfig, value=2)
         @File(config.ini, type='ini')
        "
::= { apexCteConfig 3 }

apexCteCitEnable OBJECT-TYPE
    SYNTAX EnableDisableTYPE
    MAX-ACCESS read-write
    STATUS current
    DESCRIPTION
        "Constrained Image Trigger (CIT) setting.
         If set to 'enabled' the settop box is notified not to allow a high
         quality digital output unless the receiving device also adheres to
         CIT processing. If the apexCteApsLevel is set to 'notDefined', the
         setting of the CIT value has no affect (CIT and APS are only used
         when APS is set to a defined value).

         Once written, the change to this parameter will only take immediate
         effect after apexCteApplyChange is set to 'apply'.  In
         order for the change to persist through subsequent reboots or power
         cycles, the change must be saved via the apexSaveConfig parameter.

         @Config(config=yes, reboot=no)
         @Commit(param=apexCteApplyChange, value=2)
         @Save(apexSaveConfig, value=2)
         @File(config.ini, type='ini')
        "
::= { apexCteConfig 4 }

apexCteCommonTier OBJECT-TYPE
    SYNTAX Integer32(0..16777215)
    MAX-ACCESS read-write
    STATUS current
    DESCRIPTION
        "EncryptionCommon Tier.  Identifies the tier
         number for which access is granted.  Range is 0 to 16777215.
         65536 is reserved and cannot be used.

         The APEX will set Tier Type based on apexCteApsLevel setting.
         Refer to the apexCteApsLevel description for more details.

         Once written, the change to this parameter will only take immediate
         effect after apexCteApplyChange is set to 'apply'.  In
         order for the change to persist through subsequent reboots or power
         cycles, the change must be saved via the apexSaveConfig parameter.

         @Config(config=yes, reboot=no)
         @Commit(param=apexCteApplyChange, value=2)
         @Save(apexSaveConfig, value=2)
         @File(config.ini, type='ini')
        "
::= { apexCteConfig 5 }

apexCteApplyChange OBJECT-TYPE
    SYNTAX ApplyDataToDeviceTYPE
    MAX-ACCESS read-write
    STATUS current
    DESCRIPTION
        "The Apply for CTE configuration items. This parameter
         MUST be set to 'apply' in order for any of the following to
         take effect:
            apexCteEncryptionMode
            apexCteCciLevel
            apexCteApsLevel
            apexCteCitEnable
            apexCteCommonTier

         This parameter MUST be set LAST after all associated parameters
         has been configured.

         @Config(config=no, reboot=no)
        "
::= { apexCteConfig 6 }


-- ------------------------------------------------------------------------------
--
-- apexEncryptionStatus
--
-- apexEncryptionStatusGeneral
--

-- none


-- ------------------------------------------------------------------------------
--
-- apexHostModule
-- 
-- apexHostModuleConfig
--
-- apexHostModuleConfigGeneral
--

apexHostModuleConfTable OBJECT-TYPE
    SYNTAX SEQUENCE OF ApexHostModuleConfEntry
    MAX-ACCESS not-accessible
    STATUS current
    DESCRIPTION
        "Reset individual Host module table."
::= { apexHostModuleConfigGeneral 2 }

apexHostModuleConfEntry OBJECT-TYPE
    SYNTAX ApexHostModuleConfEntry
    MAX-ACCESS not-accessible
    STATUS current
    DESCRIPTION
        "Entry in apexHostModuleConfTable."
    INDEX { apexHostModuleConfResetBladeNum }
::= { apexHostModuleConfTable 1 }

ApexHostModuleConfEntry ::= SEQUENCE
    {
     apexHostModuleConfResetBladeNum  Integer32,
     apexHostModuleConfResetModule    ApplyDataToDeviceTYPE
    }

apexHostModuleConfResetBladeNum OBJECT-TYPE
    SYNTAX Integer32(1..2)
    MAX-ACCESS not-accessible
    STATUS current
    DESCRIPTION
        "Host Module number. 
         Host 1 is Top Host. Host 2 is bottom Host.
        "
::= { apexHostModuleConfEntry 1 }

apexHostModuleConfResetModule OBJECT-TYPE
    SYNTAX ApplyDataToDeviceTYPE
    MAX-ACCESS read-write
    STATUS current
    DESCRIPTION
        "The Apply for Host Module Reset table.

         This parameter causes the selected Host module to Reset. Setting
         to Apply for selected Host causes that host module to reset. If
         the selected Host is the Active Host module, a failure to the Standby
         will occur as a result of resetting the Active host. 

         @Config(config=no, reboot=no)
        "
::= { apexHostModuleConfEntry 2 }


-- ------------------------------------------------------------------------------
--
-- apexHostModuleStatus
--
-- apexHostModuleStatusGeneral
--

-- none


-- ------------------------------------------------------------------------------
--
-- apexHostModuleStatusTable
--

apexHostModuleStatusTable OBJECT-TYPE
    SYNTAX SEQUENCE OF ApexHostModuleStatusEntry
    MAX-ACCESS not-accessible
    STATUS current
    DESCRIPTION
        "Host Module Status table."
::= { apexHostModuleStatus 2 }

apexHostModuleStatusEntry OBJECT-TYPE
    SYNTAX ApexHostModuleStatusEntry
    MAX-ACCESS not-accessible
    STATUS current
    DESCRIPTION
        "Entry in apexHostModuleStatusTable."
    INDEX { apexHostModuleStatusBladeNum }
::= { apexHostModuleStatusTable 1 }

ApexHostModuleStatusEntry ::= SEQUENCE
    {
     apexHostModuleStatusBladeNum Integer32,
     apexHostModuleStatusFault    INTEGER
    }

apexHostModuleStatusBladeNum OBJECT-TYPE
    SYNTAX Integer32(1..2)
    MAX-ACCESS not-accessible
    STATUS current
    DESCRIPTION
        "Host Module number. 
         Host 1 is Top Host. Host 2 is bottom Host.
        "
::= { apexHostModuleStatusEntry 1 }

apexHostModuleStatusFault OBJECT-TYPE
    SYNTAX INTEGER
        {
         ok(1),
         indeterminate(2),
         warning(3),
         minor(4),
         major(5),
         critical(6)
        }
    MAX-ACCESS read-only
    STATUS current
    DESCRIPTION
        "Current alarm fault condition of the Host Module.
         
         Reflected in apexAlarmHostModuleFault.
         
         This condition is set for Host Module HW and SW faults during
         board initialization and bringup and for runtime errors
         such as Host temperature, Enet1, and Enet2.
         
         Setting of this condition can cause a Host Module redundancy failover.
        "
::= { apexHostModuleStatusEntry 2 }


-- ------------------------------------------------------------------------------
--
-- apexHostModuleRedundancy
--
-- apexHostRedundConfig
--
-- apexHostRedundConfigGeneral
--

apexHostRedundConfigApplyChange OBJECT-TYPE
    SYNTAX ApplyDataToDeviceTYPE
    MAX-ACCESS read-write
    STATUS current
    DESCRIPTION
        "The Apply for Host Module Redundancy Config General.

         This parameter MUST be set to 'apply' in order for any of the data
         in apexHostRedundConfigGeneral to take effect (except 
         apexHostRedundForceSwitchover).  This parameter
         MUST be set LAST after all other data in apexHostRedundConfigGeneral 
         has been configured.

         Once written, the change to this parameter will take immediate effect.

         @Config(config=no, reboot=no)
        "
::= { apexHostRedundConfigGeneral 1 }

apexHostRedundSuspendFailover OBJECT-TYPE
    SYNTAX EnableDisableTYPE
    MAX-ACCESS read-write
    STATUS current
    DESCRIPTION
        "Host Module Redundancy Suspend Mode configuration. If enabled, switchover
         are not allowed (except if forced by the operator).

         Default value is disabled.

         @Config(config=yes, reboot=no)
         @Commit(param=apexHostRedundConfigApplyChange, value=2)
         @Save(apexSaveConfig, value=2)
         @File(config.ini, type='ini')
        "
::= { apexHostRedundConfigGeneral 2 }

apexHostRedundForceSwitchover OBJECT-TYPE
    SYNTAX INTEGER
        {
         notApplicable         (0),
         failoverNotInProgress (1),
         failover              (2),
         failoverNotPossible   (3)
        }
    MAX-ACCESS read-write
    STATUS current
    DESCRIPTION
        "When set to failover(2), the APEX will try to switch over from the
         currently active host module to the standby host module.

         The APEX set the value to failoverNotPossible (3) if some situation 
         makes the failover not possible. More info about it is provided in
         apexHostRedundInvalidApplyText.

         Once written, the change to this table will take immediate

         @Config(config=no, reboot=no)
        "
::= { apexHostRedundConfigGeneral 3 }

apexHostRedundTriggerEnet2LinkLoss OBJECT-TYPE
    SYNTAX EnableDisableTYPE
    MAX-ACCESS read-write
    STATUS current
    DESCRIPTION
        "Configures if ENET2 link loss is cause for switchover.

         @Config(config=yes, reboot=no)
         @Commit(param=apexHostRedundConfigApplyChange, value=2)
         @Save(apexSaveConfig, value=2)
         @File(config.ini, type='ini')
        "
::= { apexHostRedundConfigGeneral 4 }

apexHostRedundTriggerTemperature OBJECT-TYPE
    SYNTAX EnableDisableTYPE
    MAX-ACCESS read-write
    STATUS current
    DESCRIPTION
        "Configures if temperature fault is cause for switchover.

         @Config(config=yes, reboot=no)
         @Commit(param=apexHostRedundConfigApplyChange, value=2)
         @Save(apexSaveConfig, value=2)
         @File(config.ini, type='ini')
        "
::= { apexHostRedundConfigGeneral 5 }

apexHostRedundTriggerEnet1LinkLoss OBJECT-TYPE
    SYNTAX EnableDisableTYPE
    MAX-ACCESS read-write
    STATUS current
    DESCRIPTION
        "Configures if ENET1 link loss is cause for switchover.

         @Config(config=yes, reboot=no)
         @Commit(param=apexHostRedundConfigApplyChange, value=2)
         @Save(apexSaveConfig, value=2)
         @File(config.ini, type='ini')
        "
::= { apexHostRedundConfigGeneral 6 }

apexHostRedundTriggerEnetTimer OBJECT-TYPE
    SYNTAX Integer32(0..3600)
    MAX-ACCESS read-write
    STATUS current
    DESCRIPTION
        "Time in seconds to wait before triggering ENET link loss.
         It applies both to ENET1 and ENET2 interfaces.

         @Config(config=yes, reboot=no)
         @Commit(param=apexHostRedundConfigApplyChange, value=2)
         @Save(apexSaveConfig, value=2)
         @File(config.ini, type='ini')
        "
::= { apexHostRedundConfigGeneral 7}


-- ------------------------------------------------------------------------------
--
-- apexHostRedundStatus
--
-- apexHostRedundStatusGeneral
--

apexHostRedundInvalidApplyText OBJECT-TYPE
    SYNTAX DisplayString (SIZE (0..80))
    MAX-ACCESS read-only
    STATUS current
    DESCRIPTION
        "When apexHostRedundConfigApplyChange is set to applyNotInProgressInvalidData,
         this entry may contain a text description of what was wrong with the data.
         This entry contains the description for the most recent apply
         of a related entry that was invalid. 
        "
::= { apexHostRedundStatusGeneral 1 }

apexHostRedundSystemStatus OBJECT-TYPE
    SYNTAX  INTEGER
        {       
         notApplicable   (0),
         available       (1),
         notAvailable    (2),
         suspended       (3)
        }
    MAX-ACCESS read-only
    STATUS current
    DESCRIPTION
        "Shows the status of the Host Module Redundancy at system level. 
        "
::= { apexHostRedundStatusGeneral 2 }

apexHostRedundStatusTable OBJECT-TYPE
    SYNTAX SEQUENCE OF ApexHostRedundStatusEntry
    MAX-ACCESS not-accessible
    STATUS current
    DESCRIPTION
        "This is a table of status parameters for the two Host Modules.
        "
::= { apexHostRedundStatus 2 }

apexHostRedundStatusEntry OBJECT-TYPE
    SYNTAX ApexHostRedundStatusEntry
    MAX-ACCESS not-accessible
    STATUS current
    DESCRIPTION
        "Host Module Status Table Entry."
    INDEX { apexHostRedundStatusHostNum }
::= { apexHostRedundStatusTable 1 }

ApexHostRedundStatusEntry ::= SEQUENCE
    {
     apexHostRedundStatusHostNum         Integer32,
     apexHostRedundStatusState           INTEGER,
     apexHostRedundStatusReleaseVersion  DisplayString
    }

apexHostRedundStatusHostNum OBJECT-TYPE
    SYNTAX Integer32(1..2)
    MAX-ACCESS not-accessible
    STATUS current
    DESCRIPTION
        "Host Module Host Number
        "
::= { apexHostRedundStatusEntry 1 }

apexHostRedundStatusState OBJECT-TYPE
    SYNTAX INTEGER
        {
         notApplicable      (0),
         active             (1),
         activeInFailure    (2),
         standby            (3),
         backupInFailure    (4),
         booting            (5),
         upgrading          (6)
        }
    MAX-ACCESS read-only
    STATUS current
    DESCRIPTION
        "Status of the Host Module.
        "
::= { apexHostRedundStatusEntry 2 }

apexHostRedundStatusReleaseVersion OBJECT-TYPE
    SYNTAX DisplayString (SIZE (0..31))
    MAX-ACCESS read-only
    STATUS current
    DESCRIPTION
        "Version of the release loaded in the Host Module.
        "
::= { apexHostRedundStatusEntry 3 }


-- ------------------------------------------------------------------------------
--
-- apexQamBlade
--
-- apexQamBladeConfig
--
-- apexQamBladeConfigGeneral
--

-- none


-- ------------------------------------------------------------------------------
--
-- apexQamBladeConfigShutdownTable
--

apexQamBladeConfigShutdownTable OBJECT-TYPE
    SYNTAX SEQUENCE OF ApexQamBladeConfigShutdownEntry
    MAX-ACCESS not-accessible
    STATUS current
    DESCRIPTION
        "Table of blades to shutdown or restart a QAM blade. 
                 
         A row in this table corresponds to a blade.
        "
::= { apexQamBladeConfig 2 }

apexQamBladeConfigShutdownEntry OBJECT-TYPE
    SYNTAX ApexQamBladeConfigShutdownEntry
    MAX-ACCESS not-accessible
    STATUS current
    DESCRIPTION
        "Blade Shutdown Configuration Table Entry."
    INDEX { apexQamBladeConfigBladeNum }
::= { apexQamBladeConfigShutdownTable 1 }

ApexQamBladeConfigShutdownEntry ::= SEQUENCE
    {
     apexQamBladeConfigBladeNum      Integer32,
     apexQamBladeConfigShutdown      INTEGER
    }

apexQamBladeConfigBladeNum OBJECT-TYPE
    SYNTAX Integer32(1..8)
    MAX-ACCESS not-accessible
    STATUS current
    DESCRIPTION
        "Blade number."
::= { apexQamBladeConfigShutdownEntry 1 }

apexQamBladeConfigShutdown OBJECT-TYPE
    SYNTAX INTEGER
        {
         notApplicable(0),
         shutdown(1),
         shutdownComplete(2),
         restart(3)
        }
    MAX-ACCESS read-write
    STATUS current
    DESCRIPTION
        "Setting a row in this table to 'shutdown' causes the QAM blade to be
         shutdown. This allows the APEX to disable the QAM blade so that it
         can then be removed.
         
         Prior to removal of a QAM blade, the user must set the blade
         to be shutdown by setting the blade row of this table to 'shutdown'.
         
         Once blade has been properly shut down, the row in the
         table will be set to 'shutdownComplete'.  This indicates that the 
         QAM blade can then be safely removed.

         A user can also restart a QAM blade that has previously
         been shutdown by setting the blade row to 'restart'. This is only
         applicable if the QAM blade was shutdown. Once a new QAM blade is
         installed, a restart has no affect. 

         A row in this table corresponds to a blade.

         @Config(config=no, reboot=no)
        "
::= { apexQamBladeConfigShutdownEntry 2 }


-- ------------------------------------------------------------------------------
--
-- apexQamBladeStatus
--
-- apexQamBladeStatusGeneral
--

-- none


-- ------------------------------------------------------------------------------
--
--  apexQamBladeStatusTable
--

apexQamBladeStatusTable OBJECT-TYPE
    SYNTAX SEQUENCE OF ApexQamBladeStatusEntry
    MAX-ACCESS not-accessible
    STATUS current
    DESCRIPTION
        "Table of QAM Blade status, indexed by Blade Number. 
        "
::= { apexQamBladeStatus 2 }

apexQamBladeStatusEntry OBJECT-TYPE
    SYNTAX ApexQamBladeStatusEntry
    MAX-ACCESS not-accessible
    STATUS current
    DESCRIPTION
        "QAM Blade Status Table Entry."
    INDEX { apexQamBladeStatusBladeNum }
::= { apexQamBladeStatusTable 1 }

ApexQamBladeStatusEntry ::= SEQUENCE
    {
     apexQamBladeStatusBladeNum         Integer32,
     apexQamBladeStatusFaultSummary     INTEGER,
     apexQamBladeStatusFaultCondition   INTEGER,
     apexQamBladeStatusRfAlarmSummary   INTEGER,
     apexQamBladeStatusNpuCommFault     INTEGER,
     apexQamBladeStatusInitError        ErrorTYPE,
     apexQamBladeStatusServiceFault     INTEGER,
     apexQamBladeStatusOtsOverflowFault INTEGER,
     apexQamBladeStatusOtsUtilFault     INTEGER,
     apexQamBladeStatusLink             INTEGER,
     apexQamBladeStatusPacketPassCount  Counter32,
     apexQamBladeStatusPacketDropCount  Counter32,
     apexQamBladeStatusServiceInactiveFault INTEGER
    }

apexQamBladeStatusBladeNum OBJECT-TYPE
    SYNTAX Integer32(1..8)
    MAX-ACCESS not-accessible
    STATUS current
    DESCRIPTION
        "Blade Number."
::= { apexQamBladeStatusEntry 1 }

apexQamBladeStatusFaultSummary OBJECT-TYPE
    SYNTAX INTEGER
        {
         ok(1),
         indeterminate(2),
         warning(3),
         minor(4),
         major(5),
         critical(6)
        }
    MAX-ACCESS read-only
    STATUS current
    DESCRIPTION
        "Summary of all faults for a QAM Blade. This shows the highest level
         fault for an entire QAM blade. This summary is based on:
           - apexQamBladeStatusFaultCondition
           - apexQamBladeStatusRfAlarmSummary
           - apexQamBladeStatusNpuCommFault
           - apexQamBladeStatusInitError
           - apexTempsQamBladeFaultCondition
           - apexQamBladeStatusServiceFault
           - apexQamBladeStatusOtsOverflowFault
           - apexQamBladeStatusOtsUtilFault
        "
::= { apexQamBladeStatusEntry 2 }

apexQamBladeStatusFaultCondition OBJECT-TYPE
    SYNTAX INTEGER
        {
         ok(1),
         indeterminate(2),
         warning(3),
         minor(4),
         major(5),
         critical(6)
        }
    MAX-ACCESS read-only
    STATUS current
    DESCRIPTION
        "Current alarm fault condition of the QAM Blade.
         
         Reflected in apexAlarmQamBladeFault.
         
         This condition is set for QAM blade faults due to RF module
         errors and initialization of HW (download of NPU images or
         FPGA images).  Takes into account errors reported in
         apexRfModuleStatusTable.
         
         Setting of this condition can cause a QAM blade redundancy failover.
        "
::= { apexQamBladeStatusEntry 3 }


apexQamBladeStatusRfAlarmSummary OBJECT-TYPE
    SYNTAX INTEGER
        {
         ok(1),
         indeterminate(2),
         warning(3),
         minor(4),
         major(5),
         critical(6)
        }
    MAX-ACCESS read-only
    STATUS current
    DESCRIPTION
        "Current highest fault condition of the RF Ports and QAM channels
         on the QAM Blade.
         
         Summary of apexAlarmQamRfPortFault and apexAlarmQamChannelFault for
         the QAM Blade.
        "
::= { apexQamBladeStatusEntry 4 }

apexQamBladeStatusNpuCommFault OBJECT-TYPE
    SYNTAX INTEGER
        {
         ok(1),
         indeterminate(2),
         warning(3),
         minor(4),
         major(5),
         critical(6)
        }
    MAX-ACCESS read-only
    STATUS current
    DESCRIPTION
        "Current fault condition of NPU to Host Communications. This indicates
         an error between the Host and NPU on the QAM blade. This occurs after
         the QAM blade has been successfully downloaded and the Host and NPU
         are no longer able to communicate with each other.
         
         Reflected in apexAlarmNpuToHostCommFault.
        "
::= { apexQamBladeStatusEntry 5 }

apexQamBladeStatusInitError OBJECT-TYPE
    SYNTAX ErrorTYPE
    MAX-ACCESS read-only
    STATUS current
    DESCRIPTION
        "Error initializing blade.
         
         Refer to apexHwEventTable for more information.
        "
::= { apexQamBladeStatusEntry 6 }

apexQamBladeStatusServiceFault OBJECT-TYPE
    SYNTAX INTEGER
        {
         ok(1),
         indeterminate(2),
         warning(3),
         minor(4),
         major(5),
         critical(6)
        }
    MAX-ACCESS read-only
    STATUS current
    DESCRIPTION
        "Service in error fault condition summary for all services associated
         with this QAM blade. OK means that there are no services
         in error on any outputs on this QAM blade.
        "
::= { apexQamBladeStatusEntry 7 }

apexQamBladeStatusOtsOverflowFault OBJECT-TYPE
    SYNTAX INTEGER
        {
         ok(1),
         indeterminate(2),
         warning(3),
         minor(4),
         major(5),
         critical(6)
        }
    MAX-ACCESS read-only
    STATUS current
    DESCRIPTION
        "Output overflow fault condition summary for all output streams associated
         with this QAM blade. OK means that there are no output streams
         in an overflow state on this QAM blade.
        "
::= { apexQamBladeStatusEntry 8 }

apexQamBladeStatusOtsUtilFault OBJECT-TYPE
    SYNTAX INTEGER
        {
         ok(1),
         indeterminate(2),
         warning(3),
         minor(4),
         major(5),
         critical(6)
        }
    MAX-ACCESS read-only
    STATUS current
    DESCRIPTION
        "Output utilization fault condition summary for all output streams associated
         with this QAM blade. OK means that there are no output streams
         in with a utilization fault on this QAM blade.
        "
::= { apexQamBladeStatusEntry 9 }

apexQamBladeStatusLink OBJECT-TYPE
    SYNTAX INTEGER
        {
         unknown(0),
         down(1),
         up(2)
        }
    MAX-ACCESS read-only
    STATUS current
    DESCRIPTION
        "Link Status of the switch port that the QAM blade is connected to."
::= { apexQamBladeStatusEntry 10 }

apexQamBladeStatusPacketPassCount OBJECT-TYPE
    SYNTAX Counter32
    MAX-ACCESS read-only
    STATUS current
    DESCRIPTION
        "Number of packets enqueued on the Marvell port's egress queue."
::= { apexQamBladeStatusEntry 11 }

apexQamBladeStatusPacketDropCount OBJECT-TYPE
    SYNTAX Counter32
    MAX-ACCESS read-only
    STATUS current
    DESCRIPTION
        "Number of packets dropped from the Marvell port's egress queue."
::= { apexQamBladeStatusEntry 12 }

apexQamBladeStatusServiceInactiveFault OBJECT-TYPE
    SYNTAX INTEGER
        {
         ok(1),
         indeterminate(2),
         warning(3),
         minor(4),
         major(5),
         critical(6)
        }
    MAX-ACCESS read-only
    STATUS current
    DESCRIPTION
        "Service inactive error fault condition summary for all services associated
         with this QAM blade. OK means that there are no services
         inactive error on any outputs on this QAM blade.
        "
::= { apexQamBladeStatusEntry 13 }


-- ------------------------------------------------------------------------------
--
-- apexQamBladeOverflowTable
--

apexQamBladeOverflowTable OBJECT-TYPE
    SYNTAX SEQUENCE OF ApexQamBladeOverflowEntry
    MAX-ACCESS not-accessible
    STATUS current
    DESCRIPTION
        "Table of QAM Blade Overflow Error status, indexed by Blade Number. 
                                                         
         When overflow errors in this table are raised and/or cleared, 
         events will be logged in apexOutputTsEventTable. 
        "
::= { apexQamBladeStatus 3 }

apexQamBladeOverflowEntry OBJECT-TYPE
    SYNTAX ApexQamBladeOverflowEntry
    MAX-ACCESS not-accessible
    STATUS current
    DESCRIPTION
        "QAM Blade Overflow Table Entry."
    INDEX { apexQamBladeOverflowBladeNum }
::= { apexQamBladeOverflowTable 1 }

ApexQamBladeOverflowEntry ::= SEQUENCE
    {
     apexQamBladeOverflowBladeNum        Integer32,
     apexQamBladeGbeSwitchOverflowError  OverflowErrorTYPE,
     apexQamBladeIngressOverflowError    OverflowErrorTYPE,
     apexQamBladeNpuOverflowError        OverflowErrorTYPE
    }

apexQamBladeOverflowBladeNum OBJECT-TYPE
    SYNTAX Integer32(1..8)
    MAX-ACCESS not-accessible
    STATUS current
    DESCRIPTION
        "Blade Number."
::= { apexQamBladeOverflowEntry 1 }

apexQamBladeGbeSwitchOverflowError OBJECT-TYPE
    SYNTAX OverflowErrorTYPE
    MAX-ACCESS read-only
    STATUS current
    DESCRIPTION
        "Indicates whether an overflow error has occurred in the 10G Switch.
         This field will clear if there is no overflows."
::= { apexQamBladeOverflowEntry 2 }

apexQamBladeIngressOverflowError OBJECT-TYPE
    SYNTAX OverflowErrorTYPE
    MAX-ACCESS read-only
    STATUS current
    DESCRIPTION
        "Indicates whether an overflow error has occurred in the Ingress FPGA.
         This field will clear if there is no overflows."
::= { apexQamBladeOverflowEntry 3 }

apexQamBladeNpuOverflowError OBJECT-TYPE
    SYNTAX OverflowErrorTYPE
    MAX-ACCESS read-only
    STATUS current
    DESCRIPTION
        "Indicates whether an overflow error has occurred in the NPU.
         This field will clear if there is no overflows."
::= { apexQamBladeOverflowEntry 4 }

                         
-- ------------------------------------------------------------------------------
--
-- apexQamBladeIngressTable
--

apexQamBladeIngressTable OBJECT-TYPE
    SYNTAX SEQUENCE OF ApexQamBladeIngressEntry
    MAX-ACCESS not-accessible
    STATUS current
    DESCRIPTION
        "Table of Ingress FPGA Statistics per QAM Blade."
::= { apexQamBladeStatus 4 }

apexQamBladeIngressEntry OBJECT-TYPE
    SYNTAX ApexQamBladeIngressEntry
    MAX-ACCESS not-accessible
    STATUS current
    DESCRIPTION
        "A row in the Ingress FPGA Statistics per QAM Blade Table."
    INDEX { apexQamBladeIngressBladeNum }
::= { apexQamBladeIngressTable 1 }

ApexQamBladeIngressEntry ::= SEQUENCE
    {
     apexQamBladeIngressBladeNum             Integer32,
     apexQamBladeIngressInputUdpPackets      Counter32,     
     apexQamBladeIngressDiscardedPackets     Counter32,
     apexQamBladeIngressOverflowedPackets    Counter32,
     apexQamBladeIngressInputCurStreamCount  Counter32,     
     apexQamBladeIngressInputTotStreamCount  Counter32,    
     apexQamBladeIngressOutputCurStreamCount Counter32,     
     apexQamBladeIngressOutputTotStreamCount Counter32              
    }

apexQamBladeIngressBladeNum OBJECT-TYPE
    SYNTAX Integer32 (1..8)
    MAX-ACCESS not-accessible
    STATUS current
    DESCRIPTION
        "Blade Number."
::= { apexQamBladeIngressEntry 1 }

apexQamBladeIngressInputUdpPackets OBJECT-TYPE
    SYNTAX Counter32 
    MAX-ACCESS read-only
    STATUS current
    DESCRIPTION
        "Number of incoming UDP packets."
::= { apexQamBladeIngressEntry 2 }

apexQamBladeIngressDiscardedPackets OBJECT-TYPE
    SYNTAX Counter32
    MAX-ACCESS read-only
    STATUS current
    DESCRIPTION
        "Number of UDP packets dropped due to no destination."
::= { apexQamBladeIngressEntry 3 }

apexQamBladeIngressOverflowedPackets OBJECT-TYPE
    SYNTAX Counter32
    MAX-ACCESS read-only
    STATUS current
    DESCRIPTION
        "Number of UDP packets dropped due to no FPGA buffer space."
::= { apexQamBladeIngressEntry 4 }

apexQamBladeIngressInputCurStreamCount OBJECT-TYPE
    SYNTAX Counter32
    MAX-ACCESS read-only
    STATUS current
    DESCRIPTION
        "Number of null and non-null packets coming in to the ingress FPGA during
         the last monitoring period
         (apexGbeRoutedPacketUpdateInterval)."
::= { apexQamBladeIngressEntry 5 }

apexQamBladeIngressInputTotStreamCount OBJECT-TYPE
    SYNTAX Counter32
    MAX-ACCESS read-only
    STATUS current
    DESCRIPTION
        "Total number of null and non-null packets coming in to the ingress FPGA."
::= { apexQamBladeIngressEntry 6 }

apexQamBladeIngressOutputCurStreamCount OBJECT-TYPE
    SYNTAX Counter32
    MAX-ACCESS read-only
    STATUS current
    DESCRIPTION
        "Number of null and non-null packets routed from the ingress FPGA during
         the last monitoring period
         (apexGbeRoutedPacketUpdateInterval)."
::= { apexQamBladeIngressEntry 7 }

apexQamBladeIngressOutputTotStreamCount OBJECT-TYPE
    SYNTAX Counter32
    MAX-ACCESS read-only
    STATUS current
    DESCRIPTION
        "Total number of null and non-null packets routed from the ingress FPGA."
::= { apexQamBladeIngressEntry 8 }


-- ------------------------------------------------------------------------------
--
-- apexQamBladeInputTsTable
--

apexQamBladeInputTsTable OBJECT-TYPE
    SYNTAX SEQUENCE OF ApexQamBladeInputTsEntry
    MAX-ACCESS not-accessible
    STATUS current
    DESCRIPTION
        "Table of Input Stream Counts per QAM Blade."
::= { apexQamBladeStatus 5 }

apexQamBladeInputTsEntry OBJECT-TYPE
    SYNTAX ApexQamBladeInputTsEntry
    MAX-ACCESS not-accessible
    STATUS current
    DESCRIPTION
        "A row in the Input Stream Counts per QAM Blade Table."
    INDEX { apexQamBladeInputTsBladeNum }
::= { apexQamBladeInputTsTable 1 }

ApexQamBladeInputTsEntry ::= SEQUENCE
    {
     apexQamBladeInputTsBladeNum    Integer32,
     apexQamBladeInputTsCount       Counter32
    }

apexQamBladeInputTsBladeNum OBJECT-TYPE
    SYNTAX Integer32 (1..8)
    MAX-ACCESS not-accessible
    STATUS current
    DESCRIPTION
        "Blade Number."
::= { apexQamBladeInputTsEntry 1 }

apexQamBladeInputTsCount OBJECT-TYPE
    SYNTAX Counter32
    MAX-ACCESS read-only
    STATUS current
    DESCRIPTION
        "Total number of input streams assigned to the QAM Blade. For input streams
         that have a primary and secondary, those streams count as 1 input stream.
        "
::= { apexQamBladeInputTsEntry 2 }


-- ------------------------------------------------------------------------------
--
-- apexQamBladeRfStatusTable
--

apexQamBladeRfStatusTable OBJECT-TYPE
    SYNTAX SEQUENCE OF ApexQamBladeRfStatusEntry
    MAX-ACCESS not-accessible
    STATUS current
    DESCRIPTION
        "Table of QAM Blade RF Status. Summary status of faults
         on a QAM blade and RF Port basis. This table is for 
         faults of type:
          - Service, Output Overflow, and Output Utilization
        "
::= { apexQamBladeStatus 6 }

apexQamBladeRfStatusEntry OBJECT-TYPE 
    SYNTAX ApexQamBladeRfStatusEntry
    MAX-ACCESS not-accessible
    STATUS current
    DESCRIPTION
        "A row in the QAM Blade RF Status Table."
    INDEX { apexQamBladeRfStatusBladeNum, apexQamBladeRfStatusPortNum }
::= { apexQamBladeRfStatusTable 1 }

ApexQamBladeRfStatusEntry ::= SEQUENCE
    {
     apexQamBladeRfStatusBladeNum          Integer32,
     apexQamBladeRfStatusPortNum           Integer32,
     apexQamBladeRfStatusFault             INTEGER, 
     apexQamBladeRfStatusServiceFault      INTEGER, 
     apexQamBladeRfStatusOtsOverflowFault  INTEGER,
     apexQamBladeRfStatusOtsUtilFault      INTEGER,
     apexQamBladeRfNumServicesInError      Integer32,
     apexQamBladeRfNumOtsOverflowErrors    Integer32,
     apexQamBladeRfNumOtsUtilErrors        Integer32
    }

apexQamBladeRfStatusBladeNum OBJECT-TYPE
    SYNTAX Integer32(1..8)
    MAX-ACCESS not-accessible
    STATUS current
    DESCRIPTION
        "QAM Blade Number.
        "
::= { apexQamBladeRfStatusEntry 1 }

apexQamBladeRfStatusPortNum OBJECT-TYPE
    SYNTAX Integer32(1..4)
    MAX-ACCESS not-accessible
    STATUS current
    DESCRIPTION
        "RF Port Number.
        "
::= { apexQamBladeRfStatusEntry 2 }

apexQamBladeRfStatusFault OBJECT-TYPE
    SYNTAX INTEGER
        {
         ok(1),
         indeterminate(2),
         warning(3),
         minor(4),
         major(5),
         critical(6)
        }
    MAX-ACCESS read-only
    STATUS current
    DESCRIPTION
        "Summary of all faults for an RF Port on a QAM Blade.
         This shows the highest level fault for an RF Port.
         This summary is based on:
           - apexQamBladeRfStatusServiceFault
           - apexQamBladeRfStatusOtsOverflowFault
           - apexQamBladeRfStatusOtsOverflowFault
           - apexRfErrorRfPortFaultCondition
           - apexRfErrorRfPortChannelFaultSummary
        "
::= { apexQamBladeRfStatusEntry 3 }

apexQamBladeRfStatusServiceFault OBJECT-TYPE
    SYNTAX INTEGER
        {
         ok(1),
         indeterminate(2),
         warning(3),
         minor(4),
         major(5),
         critical(6)
        }
    MAX-ACCESS read-only
    STATUS current
    DESCRIPTION
        "Service in error fault condition summary for all services associated
         with this QAM blade and RF Port. OK means that there are no services
         in error on any outputs on this QAM blade and RF Port.
        "
::= { apexQamBladeRfStatusEntry 4 }

apexQamBladeRfStatusOtsOverflowFault OBJECT-TYPE
    SYNTAX INTEGER
        {
         ok(1),
         indeterminate(2),
         warning(3),
         minor(4),
         major(5),
         critical(6)
        }
    MAX-ACCESS read-only
    STATUS current
    DESCRIPTION
        "Output overflow fault condition summary for all output streams associated
         with this QAM blade and RF Port. OK means that there are no output streams
         in an overflow state on this QAM blade and RF Port.
        "
::= { apexQamBladeRfStatusEntry 5 }

apexQamBladeRfStatusOtsUtilFault OBJECT-TYPE
    SYNTAX INTEGER
        {
         ok(1),
         indeterminate(2),
         warning(3),
         minor(4),
         major(5),
         critical(6)
        }
    MAX-ACCESS read-only
    STATUS current
    DESCRIPTION
        "Output utilization fault condition summary for all output streams associated
         with this QAM blade and RF Port. OK means that there are no output streams
         in with a utilization fault on this QAM blade and RF Port.
        "
::= { apexQamBladeRfStatusEntry 6 }

apexQamBladeRfNumServicesInError OBJECT-TYPE
    SYNTAX Integer32
    MAX-ACCESS read-only
    STATUS current
    DESCRIPTION
        "Number of services in error on this QAM blade and RF Port.
        "
::= { apexQamBladeRfStatusEntry 7 }

apexQamBladeRfNumOtsOverflowErrors OBJECT-TYPE
    SYNTAX Integer32
    MAX-ACCESS read-only
    STATUS current
    DESCRIPTION
        "Number of outputs in overflow on this QAM blade and RF Port.
        "
::= { apexQamBladeRfStatusEntry 8 }

apexQamBladeRfNumOtsUtilErrors OBJECT-TYPE
    SYNTAX Integer32
    MAX-ACCESS read-only
    STATUS current
    DESCRIPTION
        "Number of output TS utilization errors on this QAM blade and RF Port.
        "
::= { apexQamBladeRfStatusEntry 9 }


-- ------------------------------------------------------------------------------
--
-- apexQamBladeNpuStatusTable
--

apexQamBladeNpuStatusTable OBJECT-TYPE
    SYNTAX SEQUENCE OF ApexQamBladeNpuStatusEntry
    MAX-ACCESS not-accessible
    STATUS current
    DESCRIPTION
        "Table of NPU Status per QAM Blade."
::= { apexQamBladeStatus 7 }

apexQamBladeNpuStatusEntry OBJECT-TYPE
    SYNTAX ApexQamBladeNpuStatusEntry
    MAX-ACCESS not-accessible
    STATUS current
    DESCRIPTION
        "A row in the NPU status table."
    INDEX { apexQamBladeNpuStatusBladeNum }
::= { apexQamBladeNpuStatusTable 1 }

ApexQamBladeNpuStatusEntry ::= SEQUENCE
    {
     apexQamBladeNpuStatusBladeNum           Integer32,
     apexQamBladeNpuStatusInputPackets       Counter32,     
     apexQamBladeNpuStatusInputPacketRate    Counter32,
     apexQamBladeNpuStatusInputPacketErrors  Counter32,
     apexQamBladeNpuStatusInputPacketDrops1  Counter32,     
     apexQamBladeNpuStatusInputPacketDrops2  Counter32    
    }

apexQamBladeNpuStatusBladeNum OBJECT-TYPE
    SYNTAX Integer32 (1..8)
    MAX-ACCESS not-accessible
    STATUS current
    DESCRIPTION
        "Blade Number."
::= { apexQamBladeNpuStatusEntry 1 }

apexQamBladeNpuStatusInputPackets OBJECT-TYPE
    SYNTAX Counter32 
    MAX-ACCESS read-only
    STATUS current
    DESCRIPTION
        "Number of input packets received by NPU."
::= { apexQamBladeNpuStatusEntry 2 }

apexQamBladeNpuStatusInputPacketRate OBJECT-TYPE
    SYNTAX Counter32
    MAX-ACCESS read-only
    STATUS current
    DESCRIPTION
        "Data rate of input packets in kbps."
::= { apexQamBladeNpuStatusEntry 3 }

apexQamBladeNpuStatusInputPacketErrors OBJECT-TYPE
    SYNTAX Counter32
    MAX-ACCESS read-only
    STATUS current
    DESCRIPTION
        "Number of input packets received by NPU that have errors."
::= { apexQamBladeNpuStatusEntry 4 }

apexQamBladeNpuStatusInputPacketDrops1 OBJECT-TYPE
    SYNTAX Counter32
    MAX-ACCESS read-only
    STATUS current
    DESCRIPTION
        "Number of input packets dropped by NPU due to an overflow at stage 1 
         of the pipeline."
::= { apexQamBladeNpuStatusEntry 5 }

apexQamBladeNpuStatusInputPacketDrops2 OBJECT-TYPE
    SYNTAX Counter32
    MAX-ACCESS read-only
    STATUS current
    DESCRIPTION
        "Number of input packets dropped by NPU due to an overflow at stage 2 
         of the pipeline."
::= { apexQamBladeNpuStatusEntry 6 }


-- ------------------------------------------------------------------------------
--
-- apexQamBladeRedundancy
--
-- apexQamBladeRedundancyConfig
--

apexQamBladeRedundConfigApplyChange OBJECT-TYPE
    SYNTAX ApplyDataToDeviceTYPE
    MAX-ACCESS read-write
    STATUS current
    DESCRIPTION
        "The Apply for QAM Blade Redundancy Configuration parameters.
         This parameter MUST be set to 'apply' in order for the data
         to take effect.
         
         This parameter MUST be set LAST after all QAM Blade Redundancy
         parameters affected by this parameter have been configured.

         @Config(config=no, reboot=no)
        "
::= { apexQamBladeRedundancyConfigGeneral 1 }

apexQamBladeRedundConfigEnable OBJECT-TYPE
    SYNTAX EnableDisableTYPE
    MAX-ACCESS read-write
    STATUS current
    DESCRIPTION
        "Enables QAM Blade redundancy mode, allowing the APEX to failover to the
         backup QAM blade.  

         Cannot be 'enabled' if the backup blade (8) is not present.

         Cannot be 'enabled' if there are any mappings to any QAM Channel
         on the backup blade.

         Once written, the change to this parameter will only take immediate
         effect after apexQamBladeRedundConfigApplyChange is set to 'apply'.
         In order for the change to persist through subsequent reboots or power
         cycles, the change must be saved via the apexSaveConfig parameter.

         @Config(config=yes, reboot=no)
         @Commit(param=apexQamBladeRedundConfigApplyChange, value=2)
         @Save(apexSaveConfig, value=2)
         @File(qamcfg.ini, type='ini')
        "
::= { apexQamBladeRedundancyConfigGeneral 2 }

apexQamBladeRedundConfigAutoSwitchBack OBJECT-TYPE
    SYNTAX EnableDisableTYPE
    MAX-ACCESS read-write
    STATUS current
    DESCRIPTION
        "This is the enable/disable of automatic switch back to the previous
         QAM Blade from backup for QAM blade redundancy.  When 'enabled',
         switch back to the previous QAM Blade will automatically occur when
         the QAM Blade comes back online.  When 'disabled', the user must force
         back to the previous QAM Blade using apexQamBladeRedundConfigForceSwitch.
         
         Does not apply when on backup due to apexQamBladeRedundConfigForceSwitch.

         Once written, the change to this parameter will only take immediate
         effect after apexQamBladeRedundConfigApplyChange is set to 'apply'.
         In order for the change to persist through subsequent reboots or power
         cycles, the change must be saved via the apexSaveConfig parameter.

         @Config(config=yes, reboot=no)
         @Commit(param=apexQamBladeRedundConfigApplyChange, value=2)
         @Save(apexSaveConfig, value=2)
         @File(qamcfg.ini, type='ini')"
::= { apexQamBladeRedundancyConfigGeneral 3 }

apexQamBladeRedundConfigSuspendFailover OBJECT-TYPE
    SYNTAX EnableDisableTYPE
    MAX-ACCESS read-write
    STATUS current
    DESCRIPTION
        "Enables and disables suspending of QAM Blade failover. Prevents failovers
         to or from backup.  Force failover (apexQamBladeRedundConfigForceSwitch)
         overrides this setting.

         Once written, the change to this parameter will only take immediate
         effect after apexQamBladeRedundConfigApplyChange is set to 'apply'.
         In order for the change to persist through subsequent reboots or power
         cycles, the change must be saved via the apexSaveConfig parameter.

         @Config(config=yes, reboot=no)
         @Commit(param=apexQamBladeRedundConfigApplyChange, value=2)
         @Save(apexSaveConfig, value=2)
         @File(qamcfg.ini, type='ini')
        "
::= { apexQamBladeRedundancyConfigGeneral 4 }

apexQamBladeRedundConfigForceSwitch OBJECT-TYPE
    SYNTAX INTEGER
        {
         switchNotInProgress (0),
         forceFrom1          (1),
         forceFrom2          (2),
         forceFrom3          (3),
         forceFrom4          (4),
         forceFrom5          (5),
         forceFrom6          (6),
         forceFrom7          (7),
         forceFromBackup     (8)
        }
    MAX-ACCESS read-write
    STATUS current
    DESCRIPTION
        "Force a switch of a QAM Blade to or from the backup.
         Selects which QAM Blade to switch from.  Overrides Suspend Failover
         (apexQamBladeRedundConfigSuspendFailover).

         Parameter is ignored when:
          - apexQamBladeRedundConfigEnable is 'disabled'.
          - backup is active and other than 'forceFromBackup' is selected.
          - backup is not active and 'forceFromBackup' is selected.

         'forceFromBackup' will force back to the failed primary indicated
         in apexQamBladeRedundStatusFailedBlade.

         APEX sets back to 'switchNotInProgress' when complete.

         Once written, the change to this parameter will take immediate effect.

         @Config(config=no, reboot=no)
        "
::= { apexQamBladeRedundancyConfigGeneral 5 }

apexQamBladeRedundConfigDefaultRfConfBlade OBJECT-TYPE
    SYNTAX Integer32(1..7)
    MAX-ACCESS read-write
    STATUS current
    DESCRIPTION
        "The primary QAM blade from which the backup blade will obtain its
         default configuration.  The RF configuration from the selected primary
         blade will be applied to the backup as a default configuration when
         there is no blade failed over.  
         
         This feature facilitates faster failover from the selected primary
         blade, and any other primary blades that are configured identically
         to the selected primary blade, by pre-configuring the backup blade
         and eliminating the need to reconfigure the backup configuration when
         a failover occurs.
         
         Parameter is ignored when apexQamBladeRedundConfigEnable is 'disabled'.
         
         Once written, the change to this parameter will take immediate effect.
         In order for the change to persist through subsequent reboots or power
         cycles, the change must be saved via the apexSaveConfig parameter.
         
         @Config(config=yes, reboot=no)
         @Save(apexSaveConfig, value=2)
         @File(qamcfg.ini, type='ini')
        "
::= { apexQamBladeRedundancyConfigGeneral 6 }


-- ------------------------------------------------------------------------------
--
-- apexQamBladeRedundancyStatus
--
-- apexQamBladeRedundancyStatusGeneral
--

apexQamBladeRedundStatusInvalidApplyText OBJECT-TYPE
    SYNTAX DisplayString (SIZE (0..80))
    MAX-ACCESS read-only
    STATUS current
    DESCRIPTION
        "When apexQamBladeRedundConfigApplyChange is set to
         'applyNotInProgressInvalidData' this entry may contain
         a text description of what was wrong with the data. This
         entry contains the description for the most recent apply
         of a related entry that was invalid.
        "
::= { apexQamBladeRedundancyStatusGeneral 1 }

apexQamBladeRedundStatusMismatch OBJECT-TYPE
    SYNTAX INTEGER
        {
         notApplicable (0),
         noMismatch    (1),
         backup        (2)
        }
    MAX-ACCESS read-only
    STATUS current
    DESCRIPTION
        "Indicates whether there is a potential for channels being lost
         when failing to the backup due to a mixture of QAM Blade RF port
         channel capacities.  The number of channels enabled is not considered.
         
         'notApplicable' - QAM RF Redundancy is disabled or backup blade is not
                           available.
         'noMismatch'    - Indicates no channels would be lost because there is
                           no mismatch.
         'backup'        - Indicates a loss of channels could occur on failover
                           to the backup because an RF port the backup has less
                           channel capacity than the matching RF port on one or
                           more of the available primary blades.         
        "
::= { apexQamBladeRedundancyStatusGeneral 2 }

apexQamBladeRedundStatusBackupBlade OBJECT-TYPE
    SYNTAX INTEGER
        {
         disabled    (0),
         standby     (1),
         active      (2),
         failed      (3),
         unavailable (4)
        }
    MAX-ACCESS read-only
    STATUS current
    DESCRIPTION
        "QAM Blade Redundancy state of configured backup blade.
         'disabled'    - QAM Blade Redundancy is disabled.
         'standby'     - QAM Blade Redundancy is enabled but backup is inactive.
                         No failure has occurred.
         'active'      - Failover has occurred and backup is active.
                         Refer to apexQamBladeRedundStatusFailedBlade for blade being
                         backed up.
         'failed'      - Backup blade has a failure.  APEX cannot provide blade
                         redundancy.
         'unavailable' - Backup blade is missing, shutdown, removed, etc.
                         (apexSysStatQamBladeAvailable is not 'available')
                         APEX cannot provide blade redundancy.
        "
::= { apexQamBladeRedundancyStatusGeneral 3 }

apexQamBladeRedundStatusFailedBlade OBJECT-TYPE
    SYNTAX Integer32
    MAX-ACCESS read-only
    STATUS current
    DESCRIPTION
        "Indicates which blade (1 to 7) has failed over to the backup.
         
         Zero indicates backup is not active.
        "
::= { apexQamBladeRedundancyStatusGeneral 4 }

apexQamBladeRedundStatusFailoverForced OBJECT-TYPE
    SYNTAX INTEGER
        {
         notForced (0),
         forced    (1)
        }
    MAX-ACCESS read-only
    STATUS current
    DESCRIPTION
        "Indicates failover to backup was forced via
         .
        "
::= { apexQamBladeRedundancyStatusGeneral 5 }

apexQamBladeRedundStatusForceSwitchText OBJECT-TYPE
    SYNTAX DisplayString (SIZE (0..80))
    MAX-ACCESS read-only
    STATUS current
    DESCRIPTION
        "When apexQamBladeRedundConfigForceSwitch is set to
         'switchNotInProgress' this entry will contain
         a text description if the force could not be
         performed.  The entry will be empty if the force
         was successful.
        "
::= { apexQamBladeRedundancyStatusGeneral 6 }


-- ------------------------------------------------------------------------------
--
-- apexRfModule
--
-- apexRfModuleConfig
--
-- apexRfModuleConfigGeneral
--

-- none


-- ------------------------------------------------------------------------------
--
-- apexRfModuleStatus
--
-- apexRfModuleStatusGeneral
--

-- none


-- ------------------------------------------------------------------------------
--
-- apexRfModuleStatusTable
--

apexRfModuleStatusTable OBJECT-TYPE
    SYNTAX SEQUENCE OF ApexRfModuleStatusEntry
    MAX-ACCESS not-accessible
    STATUS current
    DESCRIPTION
        "Table of RF Module Status."
::= { apexRfModuleStatus 2 }

apexRfModuleStatusEntry OBJECT-TYPE
    SYNTAX ApexRfModuleStatusEntry
    MAX-ACCESS not-accessible
    STATUS current
    DESCRIPTION
        "RF Module Status Table Entry."
    INDEX { apexRfModuleStatusBladeNum }
::= { apexRfModuleStatusTable 1 }

ApexRfModuleStatusEntry ::= SEQUENCE
    {
     apexRfModuleStatusBladeNum            Integer32,
     apexRfModuleStatusFaultCondition      INTEGER,
     apexRfModuleStatusInitError           ErrorTYPE,
     apexRfModuleStatusMasterClockLock     ErrorTYPE,
     apexRfModuleStatusRefernceClockLock   ErrorTYPE,
     apexRfModuleStatusInputPortError      ErrorTYPE,
     apexRfModuleStatus5VoltSupplyError    LowHighErrorTYPE,
     apexRfModuleStatus8VoltSupplyError    LowHighErrorTYPE,
     apexRfModuleStatusInternalPowerError  ErrorTYPE,
     apexRfModuleStatus5VoltSupplyLevel    Integer32,
     apexRfModuleStatus8VoltSupplyLevel    Integer32,
     apexRfModuleStatusCommunicationError  ErrorTYPE,
     apexRfModuleStatusCodeFileDownload    INTEGER
    }

apexRfModuleStatusBladeNum OBJECT-TYPE
    SYNTAX Integer32(1..8)
    MAX-ACCESS not-accessible
    STATUS current
    DESCRIPTION
        "QAM Blade Number."
::= { apexRfModuleStatusEntry 1 }
                      
apexRfModuleStatusFaultCondition OBJECT-TYPE
    SYNTAX INTEGER
        {
         ok(1),
         indeterminate(2),
         warning(3),
         minor(4),
         major(5),
         critical(6)
        }
    MAX-ACCESS read-only
    STATUS current
    DESCRIPTION
        "Current alarm condition for this RF Module.
         
         Reflected in apexAlarmQamBladeFault.
         
         Setting of this condition can cause a QAM blade redundancy failover.
        "
::= { apexRfModuleStatusEntry 2 }

apexRfModuleStatusInitError OBJECT-TYPE
    SYNTAX ErrorTYPE
    MAX-ACCESS read-only
    STATUS current
    DESCRIPTION
        "Error initializing module.
         
         Refer to apexHwEventTable for more information.
        "
::= { apexRfModuleStatusEntry 3 }

apexRfModuleStatusMasterClockLock OBJECT-TYPE
    SYNTAX ErrorTYPE
    MAX-ACCESS read-only
    STATUS current
    DESCRIPTION
        "Master clock lock status.
        "
::= { apexRfModuleStatusEntry 4 }

apexRfModuleStatusRefernceClockLock OBJECT-TYPE
    SYNTAX ErrorTYPE
    MAX-ACCESS read-only
    STATUS current
    DESCRIPTION
        "Reference clock lock status.
        "
::= { apexRfModuleStatusEntry 5 }

apexRfModuleStatusInputPortError OBJECT-TYPE
    SYNTAX ErrorTYPE
    MAX-ACCESS read-only
    STATUS current
    DESCRIPTION
        "Module Input Port status.
         'error' indicates there is an error on one or more input ports.
         
         Refer to apexHwEventTable for more information.
        "
::= { apexRfModuleStatusEntry 6 }

apexRfModuleStatus5VoltSupplyError OBJECT-TYPE
    SYNTAX LowHighErrorTYPE
    MAX-ACCESS read-only
    STATUS current
    DESCRIPTION
        "5.2 volt input supply status.
        "
::= { apexRfModuleStatusEntry 7 }

apexRfModuleStatus8VoltSupplyError OBJECT-TYPE
    SYNTAX LowHighErrorTYPE
    MAX-ACCESS read-only
    STATUS current
    DESCRIPTION
        "8.0 volt input supply status.
        "
::= { apexRfModuleStatusEntry 8 }

apexRfModuleStatusInternalPowerError OBJECT-TYPE
    SYNTAX ErrorTYPE
    MAX-ACCESS read-only
    STATUS current
    DESCRIPTION
        "Internal power status.
         'error' indicates one or more internal power voltages that are
         derived from one the input power supplies is in error.
        "
::= { apexRfModuleStatusEntry 9 }

apexRfModuleStatus5VoltSupplyLevel OBJECT-TYPE
    SYNTAX Integer32
    MAX-ACCESS read-only
    STATUS current
    DESCRIPTION
        "5.2 volt input supply level in units of 0.01 volts.
        "
::= { apexRfModuleStatusEntry 10 }

apexRfModuleStatus8VoltSupplyLevel OBJECT-TYPE
    SYNTAX Integer32
    MAX-ACCESS read-only
    STATUS current
    DESCRIPTION
        "8.0 volt input supply level in units of 0.01 volts.
        "
::= { apexRfModuleStatusEntry 11 }

apexRfModuleStatusCommunicationError OBJECT-TYPE
    SYNTAX ErrorTYPE
    MAX-ACCESS read-only
    STATUS current
    DESCRIPTION
        "Host to RF Module run-time communication status.
         'error' indicates a persistent communication problem occurring
         after module initialization. 
        "
::= { apexRfModuleStatusEntry 12 }

apexRfModuleStatusCodeFileDownload OBJECT-TYPE
    SYNTAX INTEGER
        {
         codeFileDownloadNotInProgress (0),
         codeFileDownloading           (1)
        }
    MAX-ACCESS read-only
    STATUS current
    DESCRIPTION
        "RF Module code file download status. 
        "
::= { apexRfModuleStatusEntry 13 }


-- ------------------------------------------------------------------------------
--
-- apexRouting
--
-- apexRoutingConfig
--
-- apexRoutingConfigGeneral
--

-- none


-- ------------------------------------------------------------------------------
--
-- apexRoutingStatus
--
-- apexRoutingStatusGeneral
--

apexMaxOutputTsServiceMappings OBJECT-TYPE
    SYNTAX Integer32
    MAX-ACCESS read-only
    STATUS current
    DESCRIPTION
        "Maximum number of services that can be mapped to any output
         stream.
        "
::= { apexRoutingStatusGeneral 1 }

apexTotalServicesMapped OBJECT-TYPE
    SYNTAX Integer32
    MAX-ACCESS read-only
    STATUS current
    DESCRIPTION
        "Total number of services mapped to all outputs on the APEX.
        "
::= { apexRoutingStatusGeneral 2 }

apexTotalPassThruTsMapped OBJECT-TYPE
    SYNTAX Integer32
    MAX-ACCESS read-only
    STATUS current
    DESCRIPTION
        "Total number of Pass Through streams mapped on the APEX. This
         is the number of outputs that have streams passed through them.
        "
::= { apexRoutingStatusGeneral 3 }

apexTotalPidsMapped OBJECT-TYPE
    SYNTAX Integer32
    MAX-ACCESS read-only
    STATUS current
    DESCRIPTION
        "Total number of ancillary PID mappings on the APEX. This is the
         number of non-service related PIDs that have been ancillary 
         mapped to all output streams on the APEX.
        "
::= { apexRoutingStatusGeneral 4 }

apexTotalManualRouteServices OBJECT-TYPE
    SYNTAX Integer32
    MAX-ACCESS read-only
    STATUS current
    DESCRIPTION
        "Total number of Manually Routed services mapped on the APEX.
        "
::= { apexRoutingStatusGeneral 5 }

apexTotalSessionsServices OBJECT-TYPE
    SYNTAX Integer32
    MAX-ACCESS read-only
    STATUS current
    DESCRIPTION
        "Total number of Session Control (SDV) services mapped on the APEX.
        "
::= { apexRoutingStatusGeneral 6 }

apexTotalUdpPortServices OBJECT-TYPE
    SYNTAX Integer32
    MAX-ACCESS read-only
    STATUS current
    DESCRIPTION
        "Total number of UDP Port mapped services mapped on the APEX.
        "
::= { apexRoutingStatusGeneral 7 }

apexTotalNumServicesInError OBJECT-TYPE
    SYNTAX Integer32
    MAX-ACCESS read-only
    STATUS current
    DESCRIPTION
        "Total number of services in error mapped on the APEX.
        "
::= { apexRoutingStatusGeneral 8 }

apexTotalDepiControlConnections  OBJECT-TYPE
    SYNTAX Integer32
    MAX-ACCESS read-only
    STATUS current
    DESCRIPTION
        "Total number of active control connections.
        "
::= { apexRoutingStatusGeneral 9 }

apexTotalDepiCntlMsgsDiscarded OBJECT-TYPE
    SYNTAX Integer32
    MAX-ACCESS read-only
    STATUS current
    DESCRIPTION
        "Total number of L2TPv3 control messages ignored because 
         they are not related to any existing control connection  .
        "
::= { apexRoutingStatusGeneral 10 }

apexTotalDepiDataMsgsDiscarded OBJECT-TYPE
    SYNTAX Integer32
    MAX-ACCESS read-only
    STATUS current
    DESCRIPTION
        "Total number of L2TPv3 data messages ignored because 
         they are not related to any existing session .
        "
::= { apexRoutingStatusGeneral 11 }

apexTotalNumDepiSessions OBJECT-TYPE
    SYNTAX Integer32
    MAX-ACCESS read-only
    STATUS current
    DESCRIPTION
        "Total number of DEPI sessions enabled in APEX.
        "
::= { apexRoutingStatusGeneral 12 }

apexTotalNumPriDepiSessions OBJECT-TYPE
    SYNTAX Integer32
    MAX-ACCESS read-only
    STATUS current
    DESCRIPTION
        "Total number of primary DEPI sessions enabled in APEX.
        "
::= { apexRoutingStatusGeneral 13 }


-- ------------------------------------------------------------------------------
--
-- apexRoutingStatusBladeTable
--

apexRoutingStatusBladeTable OBJECT-TYPE
    SYNTAX SEQUENCE OF ApexRoutingStatusBladeEntry
    MAX-ACCESS not-accessible
    STATUS current
    DESCRIPTION
        "Table of Routing status.
         Indexed by Blade Number."
::= { apexRoutingStatus 2 }

apexRoutingStatusBladeEntry OBJECT-TYPE
    SYNTAX ApexRoutingStatusBladeEntry
    MAX-ACCESS not-accessible
    STATUS current
    DESCRIPTION
        "A row in the Routing Status table."
    INDEX { apexRoutingStatusBladeNum }
::= { apexRoutingStatusBladeTable 1 }

ApexRoutingStatusBladeEntry ::= SEQUENCE
    {
     apexRoutingStatusBladeNum             Integer32,
     apexQamBladeServicesMapped            Integer32,
     apexQamBladePassThrusMapped           Integer32,
     apexQamBladePidsMapped                Integer32,
     apexQamBladeManualRouteServices       Integer32,
     apexQamBladeSessionsServices          Integer32,
     apexQamBladeUdpPortServices           Integer32,
     apexQamBladeNumServicesInError        Integer32,
     apexQamBladeActiveServicesMapped      Integer32,
     apexQamBladeActivePassThrusMapped     Integer32,
     apexQamBladeActivePidsMapped          Integer32,
     apexQamBladeInactiveServicesMapped    Integer32,
     apexQamBladeMultiplexedServicesMapped Integer32,
     apexQamBladeDepiSessionsMapped        Integer32,
     apexQamBladePriDepiSessionsMapped     Integer32,
     apexQamBladeSimScgsProvisioned        Integer32,
     apexQamBladeReplicatedServicesMapped  Integer32,
     apexQamBladeReplicatedPidsMapped      Integer32
    }

apexRoutingStatusBladeNum OBJECT-TYPE
    SYNTAX Integer32 (1..8)
    MAX-ACCESS not-accessible
    STATUS current
    DESCRIPTION
        "Blade Number."
::= { apexRoutingStatusBladeEntry 1 }

apexQamBladeServicesMapped OBJECT-TYPE
    SYNTAX Integer32
    MAX-ACCESS read-only
    STATUS current
    DESCRIPTION
        "Total number of services mapped to the QAM blade.
        "
::= { apexRoutingStatusBladeEntry 2 }

apexQamBladePassThrusMapped OBJECT-TYPE
    SYNTAX Integer32
    MAX-ACCESS read-only
    STATUS current
    DESCRIPTION
        "Total number of pass through streams mapped to the QAM blade. This
         is the number of outputs on the QAM blade with streams passed through.
        "
::= { apexRoutingStatusBladeEntry 3 }

apexQamBladePidsMapped OBJECT-TYPE
    SYNTAX Integer32
    MAX-ACCESS read-only
    STATUS current
    DESCRIPTION
        "Total number of Ancillary PIDs mapped to the QAM blade.
        "
::= { apexRoutingStatusBladeEntry 4 }

apexQamBladeManualRouteServices OBJECT-TYPE
    SYNTAX Integer32
    MAX-ACCESS read-only
    STATUS current
    DESCRIPTION
        "Total number of Manually Routed services mapped to the QAM blade.
        "
::= { apexRoutingStatusBladeEntry 5 }

apexQamBladeSessionsServices OBJECT-TYPE
    SYNTAX Integer32
    MAX-ACCESS read-only
    STATUS current
    DESCRIPTION
        "Total number of Session Control (SDV) services mapped to the QAM blade.
        "
::= { apexRoutingStatusBladeEntry 6 }

apexQamBladeUdpPortServices OBJECT-TYPE
    SYNTAX Integer32
    MAX-ACCESS read-only
    STATUS current
    DESCRIPTION
        "Total number of UDP Port services mapped to the QAM blade.
        "
::= { apexRoutingStatusBladeEntry 7 }

apexQamBladeNumServicesInError OBJECT-TYPE
    SYNTAX Integer32
    MAX-ACCESS read-only
    STATUS current
    DESCRIPTION
        "Total number of services in error mapped to the QAM blade.
        "
::= { apexRoutingStatusBladeEntry 8 }

apexQamBladeActiveServicesMapped OBJECT-TYPE
    SYNTAX Integer32
    MAX-ACCESS read-only
    STATUS current
    DESCRIPTION
        "Total number of active services mapped to the QAM blade. Active services
         are services that are started (output stream must also be active). Active
         services may be successfully mapped or may be in a service error state.  
        "
::= { apexRoutingStatusBladeEntry 9 }

apexQamBladeActivePassThrusMapped OBJECT-TYPE
    SYNTAX Integer32
    MAX-ACCESS read-only
    STATUS current
    DESCRIPTION
        "Total number of active pass through streams mapped to the QAM blade. This
         is the number of outputs on the QAM blade with streams passed through.
        "
::= { apexRoutingStatusBladeEntry 10 }

apexQamBladeActivePidsMapped OBJECT-TYPE
    SYNTAX Integer32
    MAX-ACCESS read-only
    STATUS current
    DESCRIPTION
        "Total number of active Ancillary PIDs mapped to the QAM blade.
        "
::= { apexRoutingStatusBladeEntry 11 }

apexQamBladeInactiveServicesMapped OBJECT-TYPE
    SYNTAX Integer32
    MAX-ACCESS read-only
    STATUS current
    DESCRIPTION
        "Total number of inactive services mapped to the QAM blade. Inactive services
         are services that are stopped. They are routed services waiting for the output
         stream to become active.  
        "
::= { apexRoutingStatusBladeEntry 12 }

apexQamBladeMultiplexedServicesMapped OBJECT-TYPE
    SYNTAX Integer32
    MAX-ACCESS read-only
    STATUS current
    DESCRIPTION
        "Total number of successfully multiplex services to the QAM blade. This
         includes all active services that are currently mapped without any errors.  
        "
::= { apexRoutingStatusBladeEntry 13 }

apexQamBladeDepiSessionsMapped OBJECT-TYPE
    SYNTAX Integer32
    MAX-ACCESS read-only
    STATUS current
    DESCRIPTION
        "Total number of mapped DEPI sessions in the blade.  
        "
::= { apexRoutingStatusBladeEntry 14 }


apexQamBladePriDepiSessionsMapped OBJECT-TYPE
    SYNTAX Integer32
    MAX-ACCESS read-only
    STATUS current
    DESCRIPTION
        "Total number of mapped primary DEPI sessions in the blade.  
        "
::= { apexRoutingStatusBladeEntry 15 }

apexQamBladeSimScgsProvisioned OBJECT-TYPE
    SYNTAX Integer32
    MAX-ACCESS read-only
    STATUS current
    DESCRIPTION
        "Total number of Simulcrypt SCGs provisioned in the blade.
        "
::= { apexRoutingStatusBladeEntry 16 }

apexQamBladeReplicatedServicesMapped OBJECT-TYPE
    SYNTAX Integer32
    MAX-ACCESS read-only
    STATUS current
    DESCRIPTION
        "Total number of replicated services mapped to the QAM blade.
         A replicated service is a service that has its output stream
         configured in Replicated operating mode. This is a count of 
         the services replicated from another output stream. 
        "
::= { apexRoutingStatusBladeEntry 17 }

apexQamBladeReplicatedPidsMapped OBJECT-TYPE
    SYNTAX Integer32
    MAX-ACCESS read-only
    STATUS current
    DESCRIPTION
        "Total number of Ancillary PIDs mapped to the QAM blade.
         A replicated PID is a PID that has its output stream
         configured in Replicated operating mode. This is a count of 
         the Ancillary PIDs replicated from another output stream. 
        "
::= { apexRoutingStatusBladeEntry 18 }


-- ------------------------------------------------------------------------------
--
-- apexRoutingStatusOtsTable
--

apexRoutingStatusOtsTable OBJECT-TYPE
    SYNTAX SEQUENCE OF ApexRoutingStatusOtsEntry
    MAX-ACCESS not-accessible
    STATUS current
    DESCRIPTION
        "Table of Routing Status.
         Indexed by Blade Number and Output Transport Stream number."
::= { apexRoutingStatus 3 }

apexRoutingStatusOtsEntry OBJECT-TYPE
    SYNTAX ApexRoutingStatusOtsEntry
    MAX-ACCESS not-accessible
    STATUS current
    DESCRIPTION
        "A row in the Output Transport Stream Status table."
    INDEX { apexRoutingStatusOtsBladeNum, apexRoutingStatusOtsNum }
::= { apexRoutingStatusOtsTable 1 }

ApexRoutingStatusOtsEntry ::= SEQUENCE
    {
     apexRoutingStatusOtsBladeNum      Integer32,
     apexRoutingStatusOtsNum           Integer32,
     apexOutputTsServicesMapped        Integer32,
     apexOutputTsPassThrusMapped       Integer32,
     apexOutputTsPidsMapped            Integer32,
     apexOutputTsServicesInError       Integer32,
     apexOutputTsDepiSessionMappings   Integer32
    }

apexRoutingStatusOtsBladeNum OBJECT-TYPE
    SYNTAX Integer32 (1..8)
    MAX-ACCESS not-accessible
    STATUS current
    DESCRIPTION
        "Blade Number."
::= { apexRoutingStatusOtsEntry 1 }

apexRoutingStatusOtsNum OBJECT-TYPE
    SYNTAX Integer32 (1..256)
    MAX-ACCESS not-accessible
    STATUS current
    DESCRIPTION
        "Output Transport Stream Number."
::= { apexRoutingStatusOtsEntry 2 }

apexOutputTsServicesMapped OBJECT-TYPE
    SYNTAX Integer32
    MAX-ACCESS read-only
    STATUS current
    DESCRIPTION
        "Total number of services mapped to the output stream.
        "
::= { apexRoutingStatusOtsEntry 3 }

apexOutputTsPassThrusMapped OBJECT-TYPE
    SYNTAX Integer32
    MAX-ACCESS read-only
    STATUS current
    DESCRIPTION
        "Total number of Pass Throughs mapped to the output stream.
         There can only be 1 stream passed through to an output stream.
        "
::= { apexRoutingStatusOtsEntry 4 }

apexOutputTsPidsMapped OBJECT-TYPE
    SYNTAX Integer32
    MAX-ACCESS read-only
    STATUS current
    DESCRIPTION
        "Total number of Ancillary PIDs mapped to the output stream.
        "
::= { apexRoutingStatusOtsEntry 5 }


apexOutputTsServicesInError OBJECT-TYPE
    SYNTAX Integer32
    MAX-ACCESS read-only
    STATUS current
    DESCRIPTION
        "Total number of services in error mapped to the output stream.
        "
::= { apexRoutingStatusOtsEntry 6 }

apexOutputTsDepiSessionMappings OBJECT-TYPE
    SYNTAX Integer32
    MAX-ACCESS read-only
    STATUS current
    DESCRIPTION
        "Total number of DEPI sessions mapped to the output stream. (0 or 1)
        "
::= { apexRoutingStatusOtsEntry 7 }


-- ------------------------------------------------------------------------------
--
-- apexRoutingStatusOtsSimTable
--

apexRoutingStatusOtsSimTable OBJECT-TYPE
    SYNTAX SEQUENCE OF ApexRoutingStatusOtsSimEntry
    MAX-ACCESS not-accessible
    STATUS current
    DESCRIPTION
        "Table of Simulcrypt Routing Status.
         Indexed by Blade Number and Output Transport Stream number."
::= { apexRoutingStatus 4 }

apexRoutingStatusOtsSimEntry OBJECT-TYPE
    SYNTAX ApexRoutingStatusOtsSimEntry
    MAX-ACCESS not-accessible
    STATUS current
    DESCRIPTION
        "A row in the Output Transport Stream Simulcrypt Status table."
    INDEX { apexRoutingStatusOtsSimBladeNum, apexRoutingStatusOtsSimOtsNum }
::= { apexRoutingStatusOtsSimTable 1 }

ApexRoutingStatusOtsSimEntry ::= SEQUENCE
    {
     apexRoutingStatusOtsSimBladeNum         Integer32,
     apexRoutingStatusOtsSimOtsNum           Integer32,
     apexRoutingStatusOtsSimScgsProvisioned  Integer32
    }

apexRoutingStatusOtsSimBladeNum OBJECT-TYPE
    SYNTAX Integer32 (1..8)
    MAX-ACCESS not-accessible
    STATUS current
    DESCRIPTION
        "Blade Number."
::= { apexRoutingStatusOtsSimEntry 1 }

apexRoutingStatusOtsSimOtsNum OBJECT-TYPE
    SYNTAX Integer32 (1..256)
    MAX-ACCESS not-accessible
    STATUS current
    DESCRIPTION
        "Output Transport Stream Number."
::= { apexRoutingStatusOtsSimEntry 2 }

apexRoutingStatusOtsSimScgsProvisioned OBJECT-TYPE
    SYNTAX Integer32
    MAX-ACCESS read-only
    STATUS current
    DESCRIPTION
        "Total number of Simulcrypt SCGs provisioned in the OTS.
        "
::= { apexRoutingStatusOtsSimEntry 3 }


-- ------------------------------------------------------------------------------
--
-- apexLiveUpgrade
--
-- apexLiveUpgradeConfig
--
-- apexLiveUpgradeConfigGeneral
--

apexLiveUpgradeRequest OBJECT-TYPE
    SYNTAX INTEGER
        {
         notApplicable             (0),
         liveUpgradeNotInProgress  (1),
         liveUpgradeRequest        (2),
         liveUpgradeRequestForce   (3),
         liveUpgradeWarning        (4),
         liveUpgradeInProgress     (5),
         liveUpgradeError          (6),
         liveUpgradeCompleted      (7)
        }
    MAX-ACCESS read-write
    STATUS current
    DESCRIPTION
        "This object handles live upgrade interactions between EM and APEX3000.

         'liveUpgradeNotInProgress' default value.
 
         'liveUpgradeRequest' set by the EM to start a live upgrade.
         
         'liveUpgradeRequestForce' set by the EM to start a live upgrade without
                                   warning notifications.

         'liveUpgradeWarning' set by the APEX3000 after liveUpgradeRequest if 
                              some situation in the APEX3000 may impact the 
                              live upgrade procedure. Additional information is
                              provided in apexLiveUpgradeStatusText.

         'liveUpgradeInProgress' set by the APEX3000 when the Live Upgrade is in
                                 progress.

         'liveUpgradeError' set by the APEX3000 if some error makes the live 
                            upgrade not possible. Additional information is
                            provided in apexLiveUpgradeStatusText.

         'liveUpgradeCompleted' set by the APEX3000 when the live upgrade is 
                                completed.

         @Config(config=no, reboot=no)
        "
::= { apexLiveUpgradeConfigGeneral 1 }

apexLiveUpgradeOperation OBJECT-TYPE
    SYNTAX INTEGER
        {
         fileTransferRequestNotInProgress (0),
         fileTransferRequest              (1),
         fileIsReady                      (2),
         errorWhenUploadingfile           (3)
        }
    MAX-ACCESS read-write
    STATUS current
    DESCRIPTION
        "This object is used by the APEX to request a file transfer during the upgrade procedure.

         'fileTransferRequestNotInProgress' default value.
 
         'fileTransferRequest' set by the APEX to request a file transfer. The filename should
         be previously set in the apexLiveUpgradeRequestedFile object.

         'fileIsReady' set by the EM once the file is uploaded correctly on the APEX.

         'errorWhenUploadingfile' set by the EM when some error occurs during the upload operation.

         @Config(config=no, reboot=no)
        "
::= { apexLiveUpgradeConfigGeneral 2 }

apexLiveUpgradeRequestedFile OBJECT-TYPE
    SYNTAX DisplayString (SIZE (0..127))
    MAX-ACCESS read-write
    STATUS current
    DESCRIPTION
        "This object is used by the APEX to indicate the requested file during live upgrade procedure.
         It's formatted using the following syntax:

         'local_file_name, destination_path'.

         Where local_file_name refers to the local path (user side), and destination path is the remote
         directory where the EM should upload the file.
        
         for example:

         'apex3000_smp_app.cod, /upgrade/kernel.img'.

         Indicates to the EM that it should upload the file 'apex3000_smp_app.cod' to the destination
         '/upgrade/kernel.img'.

         @Config(config=no, reboot=no)
        "
::= { apexLiveUpgradeConfigGeneral 3 }

apexLiveUpgradeMode OBJECT-TYPE
    SYNTAX INTEGER
        {
         notApplicable             (0),
         bootp                     (1),
         elementManager            (2)
        }
    MAX-ACCESS read-write
    STATUS current
    DESCRIPTION
        "This parameter is used to set from where the images are going to be downloaded.

         'bootp' a BOOTP/TFTP server is used. 

         'elementManager' new build is provided using the Element Manager. 

         @Config(config=yes, reboot=no)
         @Save(apexSaveConfig, value=2)
         @File(config.ini, type='ini')
        "
::= { apexLiveUpgradeConfigGeneral 4 }


-- ------------------------------------------------------------------------------
--
-- apexLiveUpgradeStatus
--
-- apexLiveUpgradeStatusGeneral
--

apexLiveUpgradeStatusText OBJECT-TYPE
    SYNTAX DisplayString (SIZE (0..127))
    MAX-ACCESS read-only
    STATUS current
    DESCRIPTION
        "Additional information about the live upgrade progress set by the APEX3000.
        "
::= { apexLiveUpgradeStatusGeneral 1 }


-- ------------------------------------------------------------------------------
--
-- apexBladeFanStatusTable
--

apexBladeFanStatusTable OBJECT-TYPE
    SYNTAX SEQUENCE OF ApexFanModuleStatusEntry
    MAX-ACCESS not-accessible
    STATUS current
    DESCRIPTION
        "This is a table of status parameters for the Fan(s) 
         on the Blade (QAM or Fan Filler Module)."
::= { apexBladeFanStatus 2 }

apexBladeFanStatusEntry OBJECT-TYPE
    SYNTAX ApexFanModuleStatusEntry
    MAX-ACCESS not-accessible
    STATUS current
    DESCRIPTION
        "Blade Fan Status Table Entry."
    INDEX { apexBladeFanStatusBladeNum }
::= { apexBladeFanStatusTable 1 }

ApexFanModuleStatusEntry ::= SEQUENCE
    {
     apexBladeFanStatusBladeNum        Integer32,
     apexBladeFanStatusFanSpeedControl Integer32,
     apexBladeFanStatusFan1Speed       Integer32,
     apexBladeFanStatusFan2Speed       Integer32,
     apexFanSpeed1FaultCondition       INTEGER,
     apexFanSpeed2FaultCondition       INTEGER
    }

apexBladeFanStatusBladeNum OBJECT-TYPE
    SYNTAX Integer32(1..8)
    MAX-ACCESS not-accessible
    STATUS current
    DESCRIPTION
        "Blade Number."
::= { apexBladeFanStatusEntry 1 }

apexBladeFanStatusFanSpeedControl OBJECT-TYPE
    SYNTAX Integer32
    MAX-ACCESS read-only
    STATUS current
    DESCRIPTION
        "This parameter indicates the Fan Speed Control in RPM."
::= { apexBladeFanStatusEntry 2 }

apexBladeFanStatusFan1Speed OBJECT-TYPE
    SYNTAX Integer32
    MAX-ACCESS read-only
    STATUS current
    DESCRIPTION
        "This parameter indicates the Fan 1 Speed in RPM."
::= { apexBladeFanStatusEntry 3 }

apexBladeFanStatusFan2Speed OBJECT-TYPE
    SYNTAX Integer32
    MAX-ACCESS read-only
    STATUS current
    DESCRIPTION
        "This parameter indicates the Fan 2 Speed in RPM."
::= { apexBladeFanStatusEntry 4 }

apexFanSpeed1FaultCondition OBJECT-TYPE
    SYNTAX INTEGER
        {
         ok(1),
         indeterminate(2),
         warning(3),
         minor(4),
         major(5),
         critical(6)
        }
    MAX-ACCESS read-only
    STATUS current
    DESCRIPTION
        "Fan 1 speed alarm condition for this blade module.
        
         Reflected in apexAlarmFanFault.
        "
::= { apexBladeFanStatusEntry 5 }

apexFanSpeed2FaultCondition OBJECT-TYPE
    SYNTAX INTEGER
        {
         ok(1),
         indeterminate(2),
         warning(3),
         minor(4),
         major(5),
         critical(6)
        }
    MAX-ACCESS read-only
    STATUS current
    DESCRIPTION
        "Fan 2 speed alarm condition for this blade module.
        
         Reflected in apexAlarmFanFault.
        "
::= { apexBladeFanStatusEntry 6 }


-- ------------------------------------------------------------------------------
--
-- apexDepi
--
-- apexDepiConfig
--
-- apexDepiConfigGeneral
--

apexDepiDiscardedNoSessionReset OBJECT-TYPE
    SYNTAX ResetStatisticsTYPE
    MAX-ACCESS read-write
    STATUS current
    DESCRIPTION
        "Reset L2TP discarded no-session packets counter.
        
         @Config(config=no, reboot=no)
        "
::= { apexDepiConfigGeneral 1 }


-- ------------------------------------------------------------------------------
--
-- apexDepiSessionRemoveSession              
--

apexDepiSessionRemoveSessionId OBJECT-TYPE
    SYNTAX Integer32
    MAX-ACCESS read-write
    STATUS current
    DESCRIPTION
        "Local session id to remove.
        
        @Commit(param=apexDepiSessionRemoveSessionApply, value=2)
        @Config(config=no, reboot=no)
        "
        
::= { apexDepiSessionRemoveSession  1 }

apexDepiSessionRemoveSessionApply OBJECT-TYPE
  SYNTAX ApplyDataToDeviceTYPE
    MAX-ACCESS read-write
    STATUS current
    DESCRIPTION
        "The Apply for the removal of entries from the DEPI session status table
         Once written, the change to this parameter will take immediate effect.
         
         @Config(config=no, reboot=no)
        "
::= { apexDepiSessionRemoveSession  2 }


-- ------------------------------------------------------------------------------
--
-- apexDepiRfLock              
--

apexDepiRfLockChannelFrequency  OBJECT-TYPE
    SYNTAX EnableDisableTYPE
    MAX-ACCESS read-write
    STATUS current
    DESCRIPTION
        "Blocks/allows the modification of channel frequency via Depi control plane messages.
        
         @Commit(param=apexDepiRfLockApplyChange, value=2)
         @Config(config=yes, reboot=no)
         @Save(apexSaveConfig, value=2)
         @File(depicfg.ini, type='ini')
        "
::= { apexDepiRfLock 1 }

apexDepiRfLockChannelModulation  OBJECT-TYPE
    SYNTAX EnableDisableTYPE
    MAX-ACCESS read-write
    STATUS current
    DESCRIPTION
        "Blocks/allows the modification of channel modulation via Depi control plane messages.
        
         @Commit(param=apexDepiRfLockApplyChange, value=2)
         @Config(config=yes, reboot=no)
         @Save(apexSaveConfig, value=2)
         @File(depicfg.ini, type='ini')
        "
::= { apexDepiRfLock 2 }

apexDepiRfLockChannelInterleaver  OBJECT-TYPE
    SYNTAX EnableDisableTYPE
    MAX-ACCESS read-write
    STATUS current
    DESCRIPTION
        "Blocks/allows the modification of Interleaver Depth via Depi control plane messages.
        
         @Commit(param=apexDepiRfLockApplyChange, value=2)
         @Config(config=yes, reboot=no)
         @Save(apexSaveConfig, value=2)
         @File(depicfg.ini, type='ini')
        "
::= { apexDepiRfLock 3 }

apexDepiRfLockChannelMute  OBJECT-TYPE
    SYNTAX EnableDisableTYPE
    MAX-ACCESS read-write
    STATUS current
    DESCRIPTION
        "Blocks/allows the modification of channel mute via Depi control plane messages.
        
         @Commit(param=apexDepiRfLockApplyChange, value=2)
         @Config(config=yes, reboot=no)
         @Save(apexSaveConfig, value=2)
         @File(depicfg.ini, type='ini')
        "
::= { apexDepiRfLock 4 }

apexDepiRfLockApplyChange  OBJECT-TYPE
    SYNTAX ApplyDataToDeviceTYPE
    MAX-ACCESS read-write 
    STATUS current
    DESCRIPTION
        "Applies the rf lock changes.
        
        @Config(config=no, reboot=no)
        "
::= { apexDepiRfLock 5 }

apexDepiRfLockInvalidApplyText OBJECT-TYPE
    SYNTAX DisplayString (SIZE (0..80))
    MAX-ACCESS read-only
    STATUS current
    DESCRIPTION
        "When apexDepiRfLockApplyChange is set to
         'applyNotInProgressInvalidData' this entry may contain
         a text description of what was wrong with the data. This
         entry contains the description for the most recent apply
         of a related entry that was invalid.
        "
::= { apexDepiRfLock 6 }


-- ------------------------------------------------------------------------------
--
-- apexDepiStatus
--
-- apexDepiStatusGeneral
--

apexDtiPort1LinkActive  OBJECT-TYPE
    SYNTAX ActiveTYPE
    MAX-ACCESS read-only
    STATUS current
    DESCRIPTION
        "This indicates if the DTI Ethernet link is active."
::= { apexDepiStatusGeneral 1 }

apexDtiPort2LinkActive  OBJECT-TYPE
    SYNTAX ActiveTYPE
    MAX-ACCESS read-only
    STATUS current
    DESCRIPTION
        "This indicates if the second DTI Ethernet link is active."
::= { apexDepiStatusGeneral 2 }

apexDtiClientStatusMode OBJECT-TYPE
    SYNTAX INTEGER
        {
         warmup(1),
         free-run(2),
         fast(3),
         normal(4),
         bridging(5),
         holdover(6)
        }
    MAX-ACCESS read-only
    STATUS current
    DESCRIPTION
        "The DTI Client MUST support and report these operational modes."
::= { apexDepiStatusGeneral 3 }

apexDtiClientPhaseError OBJECT-TYPE
    SYNTAX Integer32
    MAX-ACCESS read-only
    STATUS current
    DESCRIPTION
        "24-bit Phase Error in units of 149.8 MHz sample clock cycles.
         The lower eight bits of the 24-bit field MUST be padded with
         zeros and MUST NOT be used by the DTI server. The value MUST be a
         signed 2's complement number. If the DTI client supports more bits of
         resolution, the DTI client MUST round the reported value to the nearest
         integer sample clock cycle.
        "
::= { apexDepiStatusGeneral 4 }

apexDtiCurrentTimestamp OBJECT-TYPE
    SYNTAX Unsigned32
    MAX-ACCESS read-only
    STATUS current
    DESCRIPTION
        "DOCSIS 32-bit timestamp (DTS). "
::= { apexDepiStatusGeneral 5 }

apexDtiPort1CableAdvanceValue OBJECT-TYPE
    SYNTAX Integer32
    MAX-ACCESS read-only
    STATUS current
    DESCRIPTION
        "24-bit Cable Advance value is derived by dividing the cable delay by 2."
::= { apexDepiStatusGeneral 6 }

apexDtiPort2CableAdvanceValue OBJECT-TYPE
    SYNTAX Integer32
    MAX-ACCESS read-only
    STATUS current
    DESCRIPTION
        "24-bit Cable Advance value is derived by dividing the cable delay by 2."
::= { apexDepiStatusGeneral 7 }


-- ------------------------------------------------------------------------------
--
-- apexDepiSessionConfig 
--
-- apexDepiSessionConfigBlade1
--
-- apexDepiSessionConfigBlade1ApplyTable
--

apexDepiSessionConfigBlade1ApplyTable OBJECT-TYPE
    SYNTAX SEQUENCE OF ApexDepiSessionConfigBlade1ApplyEntry
    MAX-ACCESS not-accessible
    STATUS current
    DESCRIPTION
        "Table of Apply Change for the data for apexDepiSessionConfigBlade1Table.
        
        "
::= { apexDepiSessionConfigBlade1 1 }

apexDepiSessionConfigBlade1ApplyEntry OBJECT-TYPE
    SYNTAX ApexDepiSessionConfigBlade1ApplyEntry
    MAX-ACCESS not-accessible
    STATUS current
    DESCRIPTION
        "DEPI Session Config Blade 1 Apply Table Entry."
    INDEX { apexDepiSessionConfigBlade1ApplyOutputTsNum }
::= { apexDepiSessionConfigBlade1ApplyTable 1 }

ApexDepiSessionConfigBlade1ApplyEntry ::= SEQUENCE
    {
     apexDepiSessionConfigBlade1ApplyOutputTsNum    Integer32,
     apexDepiSessionConfigBlade1ApplyChange         ApplyDataToDeviceTYPE
    }

apexDepiSessionConfigBlade1ApplyOutputTsNum OBJECT-TYPE
    SYNTAX Integer32(1..256)
    MAX-ACCESS not-accessible
    STATUS current
    DESCRIPTION
        "The index of the Depi Session Config Apply Table."
::= { apexDepiSessionConfigBlade1ApplyEntry 1 }

apexDepiSessionConfigBlade1ApplyChange OBJECT-TYPE
    SYNTAX ApplyDataToDeviceTYPE
    MAX-ACCESS read-write
    STATUS current
    DESCRIPTION
        "The Apply for any entries in the apexDepiSessionConfigBlade1Table.

         This parameter MUST be set to 'apply' in order for any of the data
         in the apexDepiSessionConfigBlade1Table to take effect.  This
         parameter MUST be set LAST after all other data in the table entry has
         been configured.

         Once written, the change to this parameter will take immediate effect.

         @Config(config=no, reboot=no)
        "
::= { apexDepiSessionConfigBlade1ApplyEntry 2 }


-- ------------------------------------------------------------------------------
--
-- apexDepiSessionConfigBlade1Table
--

apexDepiSessionConfigBlade1Table OBJECT-TYPE
    SYNTAX SEQUENCE OF ApexDepiSessionConfigBlade1Entry
    MAX-ACCESS not-accessible
    STATUS current
    DESCRIPTION
        "Table of data for DEPI Session Mapping. There are
         48 rows in this table mapping QAM output TS to DEPI Session.

         Once written, the change to this table will only take immediate
         effect after apexDepiSessionConfigBlade1ApplyChange is set to 'apply'.
         However, in order for the change to persist through subsequent
         reboots or power cycles, the change must be saved via apexSaveConfig.

         @Config(config=yes, reboot=no)
         @Commit(param=apexDepiSessionConfigBlade1ApplyChange, value=2)
         @Save(apexSaveConfig, value=2)
         @File(depicfg.ini, type='ini')
        "
::= { apexDepiSessionConfigBlade1 2 }

apexDepiSessionConfigBlade1Entry OBJECT-TYPE
    SYNTAX ApexDepiSessionConfigBlade1Entry
    MAX-ACCESS not-accessible
    STATUS current
    DESCRIPTION
        "DEPI Session  Config Table Entry."
    INDEX { apexDepiSessionConfigBlade1OutputTsNum }
::= { apexDepiSessionConfigBlade1Table 1 }

ApexDepiSessionConfigBlade1Entry ::= SEQUENCE
    {
     apexDepiSessionConfigBlade1OutputTsNum     Integer32,
     apexDepiSessionConfigBlade1Enable          EnableDisableTYPE,
     apexDepiSessionConfigBlade1DocsisTsid      Unsigned32,
     apexDepiSessionConfigBlade1InterfaceNumber Integer32,
     apexDepiSessionConfigBlade1SourceIp        IpAddress
    }

apexDepiSessionConfigBlade1OutputTsNum OBJECT-TYPE
    SYNTAX Integer32(1..256)
    MAX-ACCESS not-accessible
    STATUS current
    DESCRIPTION
        "The QAM output transport stream number which to associate the DEPI Session.
        "
::= { apexDepiSessionConfigBlade1Entry 1 }

apexDepiSessionConfigBlade1Enable OBJECT-TYPE
    SYNTAX EnableDisableTYPE
    MAX-ACCESS read-write
    STATUS current
    DESCRIPTION
        "The enable setting for DEPI Session.

         Once written, the change to this parameter will take immediate
         effect.  In order for the change to persist through subsequent
         reboots or power cycles, the change must be saved via the
         apexSaveConfig parameter.
        "
::= { apexDepiSessionConfigBlade1Entry 2 }

apexDepiSessionConfigBlade1DocsisTsid OBJECT-TYPE
    SYNTAX Unsigned32(0..4294967295)
    MAX-ACCESS read-write
    STATUS current
    DESCRIPTION
        "The system wide unique M-CMTS TSID mapped to the QAM. This TSID is specified by the
         remote ID from the ICRQ message.
        "
::= { apexDepiSessionConfigBlade1Entry 3 }

apexDepiSessionConfigBlade1InterfaceNumber OBJECT-TYPE
    SYNTAX Integer32(1..12)
    MAX-ACCESS read-write
    STATUS current
    DESCRIPTION
        "Represents the Gigabit Ethernet interface number.
        "
::= { apexDepiSessionConfigBlade1Entry 4 }

apexDepiSessionConfigBlade1SourceIp OBJECT-TYPE
    SYNTAX IpAddress
    MAX-ACCESS read-write
    STATUS current
    DESCRIPTION
        "Represents the Source Ip Address for the session.
        "
::= { apexDepiSessionConfigBlade1Entry 5 }


-- ------------------------------------------------------------------------------
--
-- apexDepiSessionConfigBlade2
--
-- apexDepiSessionConfigBlade2ApplyTable
--

apexDepiSessionConfigBlade2ApplyTable OBJECT-TYPE
    SYNTAX SEQUENCE OF ApexDepiSessionConfigBlade2ApplyEntry
    MAX-ACCESS not-accessible
    STATUS current
    DESCRIPTION
        "Table of Apply Change for the data for apexDepiSessionConfigBlade2Table.
        "
::= { apexDepiSessionConfigBlade2 1 }

apexDepiSessionConfigBlade2ApplyEntry OBJECT-TYPE
    SYNTAX ApexDepiSessionConfigBlade2ApplyEntry
    MAX-ACCESS not-accessible
    STATUS current
    DESCRIPTION
        "DEPI Session Config Blade 2 Apply Table Entry."
    INDEX { apexDepiSessionConfigBlade2ApplyOutputTsNum }
::= { apexDepiSessionConfigBlade2ApplyTable 1 }

ApexDepiSessionConfigBlade2ApplyEntry ::= SEQUENCE
    {
     apexDepiSessionConfigBlade2ApplyOutputTsNum    Integer32,
     apexDepiSessionConfigBlade2ApplyChange         ApplyDataToDeviceTYPE
    }

apexDepiSessionConfigBlade2ApplyOutputTsNum OBJECT-TYPE
    SYNTAX Integer32(1..256)
    MAX-ACCESS not-accessible
    STATUS current
    DESCRIPTION
        "The index of the Depi Session Config Apply Table."
::= { apexDepiSessionConfigBlade2ApplyEntry 1 }

apexDepiSessionConfigBlade2ApplyChange OBJECT-TYPE
    SYNTAX ApplyDataToDeviceTYPE
    MAX-ACCESS read-write
    STATUS current
    DESCRIPTION
        "The Apply for any entries in the apexDepiSessionConfigBlade2Table.

         This parameter MUST be set to 'apply' in order for any of the data
         in the apexDepiSessionConfigBlade2Table to take effect.  This
         parameter MUST be set LAST after all other data in the table entry has
         been configured.

         Once written, the change to this parameter will take immediate effect.

         @Config(config=no, reboot=no)
        "
::= { apexDepiSessionConfigBlade2ApplyEntry 2 }


-- ------------------------------------------------------------------------------
--
-- apexDepiSessionConfigBlade2Table
--

apexDepiSessionConfigBlade2Table OBJECT-TYPE
    SYNTAX SEQUENCE OF ApexDepiSessionConfigBlade2Entry
    MAX-ACCESS not-accessible
    STATUS current
    DESCRIPTION
        "Table of data for DEPI Session Mapping. There are
         48 rows in this table mapping QAM output TS to DEPI Session.

         Once written, the change to this table will only take immediate
         effect after apexDepiSessionConfigBlade2ApplyChange is set to 'apply'.
         However, in order for the change to persist through subsequent
         reboots or power cycles, the change must be saved via apexSaveConfig.

         @Config(config=yes, reboot=no)
         @Commit(param=apexDepiSessionConfigBlade2ApplyChange, value=2)
         @Save(apexSaveConfig, value=2)
         @File(depicfg.ini, type='ini')
        "
::= { apexDepiSessionConfigBlade2 2 }

apexDepiSessionConfigBlade2Entry OBJECT-TYPE
    SYNTAX ApexDepiSessionConfigBlade2Entry
    MAX-ACCESS not-accessible
    STATUS current
    DESCRIPTION
        "DEPI Session  Config Table Entry."
    INDEX { apexDepiSessionConfigBlade2OutputTsNum }
::= { apexDepiSessionConfigBlade2Table 1 }

ApexDepiSessionConfigBlade2Entry ::= SEQUENCE
    {
     apexDepiSessionConfigBlade2OutputTsNum     Integer32,
     apexDepiSessionConfigBlade2Enable          EnableDisableTYPE,
     apexDepiSessionConfigBlade2DocsisTsid      Unsigned32,
     apexDepiSessionConfigBlade2InterfaceNumber Integer32,
     apexDepiSessionConfigBlade2SourceIp        IpAddress
    }

apexDepiSessionConfigBlade2OutputTsNum OBJECT-TYPE
    SYNTAX Integer32(1..256)
    MAX-ACCESS not-accessible
    STATUS current
    DESCRIPTION
        "The QAM output transport stream number which to associate the DEPI Session.
        "
::= { apexDepiSessionConfigBlade2Entry 1 }

apexDepiSessionConfigBlade2Enable OBJECT-TYPE
    SYNTAX EnableDisableTYPE
    MAX-ACCESS read-write
    STATUS current
    DESCRIPTION
        "The enable setting for DEPI Session.

         Once written, the change to this parameter will take immediate
         effect.  In order for the change to persist through subsequent
         reboots or power cycles, the change must be saved via the
         apexSaveConfig parameter.
        "
::= { apexDepiSessionConfigBlade2Entry 2 }

apexDepiSessionConfigBlade2DocsisTsid OBJECT-TYPE
    SYNTAX Unsigned32(0..4294967295)
    MAX-ACCESS read-write
    STATUS current
    DESCRIPTION
        "The system wide unique M-CMTS TSID mapped to the QAM. This TSID is specified by the
         remote ID from the ICRQ message.
        "
::= { apexDepiSessionConfigBlade2Entry 3 }

apexDepiSessionConfigBlade2InterfaceNumber OBJECT-TYPE
    SYNTAX Integer32(1..12)
    MAX-ACCESS read-write
    STATUS current
    DESCRIPTION
        "Represents the Gigabit Ethernet interface number.
        "
::= { apexDepiSessionConfigBlade2Entry 4 }

apexDepiSessionConfigBlade2SourceIp OBJECT-TYPE
    SYNTAX IpAddress
    MAX-ACCESS read-write
    STATUS current
    DESCRIPTION
        "Represents the Source Ip Address for the session.
        "
::= { apexDepiSessionConfigBlade2Entry 5 }


-- ------------------------------------------------------------------------------
--
-- apexDepiSessionConfigBlade3
--
-- apexDepiSessionConfigBlade3ApplyTable
--

apexDepiSessionConfigBlade3ApplyTable OBJECT-TYPE
    SYNTAX SEQUENCE OF ApexDepiSessionConfigBlade3ApplyEntry
    MAX-ACCESS not-accessible
    STATUS current
    DESCRIPTION
        "Table of Apply Change for the data for apexDepiSessionConfigBlade3Table.
        "
::= { apexDepiSessionConfigBlade3 1 }

apexDepiSessionConfigBlade3ApplyEntry OBJECT-TYPE
    SYNTAX ApexDepiSessionConfigBlade3ApplyEntry
    MAX-ACCESS not-accessible
    STATUS current
    DESCRIPTION
        "DEPI Session Config Blade 3 Apply Table Entry."
    INDEX { apexDepiSessionConfigBlade3ApplyOutputTsNum }
::= { apexDepiSessionConfigBlade3ApplyTable 1 }

ApexDepiSessionConfigBlade3ApplyEntry ::= SEQUENCE
    {
     apexDepiSessionConfigBlade3ApplyOutputTsNum    Integer32,
     apexDepiSessionConfigBlade3ApplyChange         ApplyDataToDeviceTYPE
    }

apexDepiSessionConfigBlade3ApplyOutputTsNum OBJECT-TYPE
    SYNTAX Integer32(1..256)
    MAX-ACCESS not-accessible
    STATUS current
    DESCRIPTION
        "The index of the Depi Session Config Apply Table."
::= { apexDepiSessionConfigBlade3ApplyEntry 1 }

apexDepiSessionConfigBlade3ApplyChange OBJECT-TYPE
    SYNTAX ApplyDataToDeviceTYPE
    MAX-ACCESS read-write
    STATUS current
    DESCRIPTION
        "The Apply for any entries in the apexDepiSessionConfigBlade3Table.

         This parameter MUST be set to 'apply' in order for any of the data
         in the apexDepiSessionConfigBlade3Table to take effect.  This
         parameter MUST be set LAST after all other data in the table entry has
         been configured.

         Once written, the change to this parameter will take immediate effect.

         @Config(config=no, reboot=no)
        "
::= { apexDepiSessionConfigBlade3ApplyEntry 2 }


-- ------------------------------------------------------------------------------
--
-- apexDepiSessionConfigBlade3Table
--

apexDepiSessionConfigBlade3Table OBJECT-TYPE
    SYNTAX SEQUENCE OF ApexDepiSessionConfigBlade3Entry
    MAX-ACCESS not-accessible
    STATUS current
    DESCRIPTION
        "Table of data for DEPI Session Mapping. There are
         48 rows in this table mapping QAM output TS to DEPI Session.

         Once written, the change to this table will only take immediate
         effect after apexDepiSessionConfigBlade3ApplyChange is set to 'apply'.
         However, in order for the change to persist through subsequent
         reboots or power cycles, the change must be saved via apexSaveConfig.

         @Config(config=yes, reboot=no)
         @Commit(param=apexDepiSessionConfigBlade3ApplyChange, value=2)
         @Save(apexSaveConfig, value=2)
         @File(depicfg.ini, type='ini')
        "
::= { apexDepiSessionConfigBlade3 2 }

apexDepiSessionConfigBlade3Entry OBJECT-TYPE
    SYNTAX ApexDepiSessionConfigBlade3Entry
    MAX-ACCESS not-accessible
    STATUS current
    DESCRIPTION
        "DEPI Session  Config Table Entry."
    INDEX { apexDepiSessionConfigBlade3OutputTsNum }
::= { apexDepiSessionConfigBlade3Table 1 }

ApexDepiSessionConfigBlade3Entry ::= SEQUENCE
    {
     apexDepiSessionConfigBlade3OutputTsNum     Integer32,
     apexDepiSessionConfigBlade3Enable          EnableDisableTYPE,
     apexDepiSessionConfigBlade3DocsisTsid      Unsigned32,
     apexDepiSessionConfigBlade3InterfaceNumber Integer32,
     apexDepiSessionConfigBlade3SourceIp        IpAddress
    }

apexDepiSessionConfigBlade3OutputTsNum OBJECT-TYPE
    SYNTAX Integer32(1..256)
    MAX-ACCESS not-accessible
    STATUS current
    DESCRIPTION
        "The QAM output transport stream number which to associate the DEPI Session.
        "
::= { apexDepiSessionConfigBlade3Entry 1 }

apexDepiSessionConfigBlade3Enable OBJECT-TYPE
    SYNTAX EnableDisableTYPE
    MAX-ACCESS read-write
    STATUS current
    DESCRIPTION
        "The enable setting for DEPI Session.

         Once written, the change to this parameter will take immediate
         effect.  In order for the change to persist through subsequent
         reboots or power cycles, the change must be saved via the
         apexSaveConfig parameter.
        "
::= { apexDepiSessionConfigBlade3Entry 2 }

apexDepiSessionConfigBlade3DocsisTsid OBJECT-TYPE
    SYNTAX Unsigned32(0..4294967295)
    MAX-ACCESS read-write
    STATUS current
    DESCRIPTION
        "The system wide unique M-CMTS TSID mapped to the QAM. This TSID is specified by the
         remote ID from the ICRQ message.
        "
::= { apexDepiSessionConfigBlade3Entry 3 }

apexDepiSessionConfigBlade3InterfaceNumber OBJECT-TYPE
    SYNTAX Integer32(1..12)
    MAX-ACCESS read-write
    STATUS current
    DESCRIPTION
        "Represents the Gigabit Ethernet interface number.
        "
::= { apexDepiSessionConfigBlade3Entry 4 }

apexDepiSessionConfigBlade3SourceIp OBJECT-TYPE
    SYNTAX IpAddress
    MAX-ACCESS read-write
    STATUS current
    DESCRIPTION
        "Represents the Source Ip Address for the session.
        "
::= { apexDepiSessionConfigBlade3Entry 5 }


-- ------------------------------------------------------------------------------
--
-- apexDepiSessionConfigBlade4
--
-- apexDepiSessionConfigBlade4ApplyTable
--

apexDepiSessionConfigBlade4ApplyTable OBJECT-TYPE
    SYNTAX SEQUENCE OF ApexDepiSessionConfigBlade4ApplyEntry
    MAX-ACCESS not-accessible
    STATUS current
    DESCRIPTION
        "Table of Apply Change for the data for apexDepiSessionConfigBlade4Table.
        "
::= { apexDepiSessionConfigBlade4 1 }

apexDepiSessionConfigBlade4ApplyEntry OBJECT-TYPE
    SYNTAX ApexDepiSessionConfigBlade4ApplyEntry
    MAX-ACCESS not-accessible
    STATUS current
    DESCRIPTION
        "DEPI Session Config Blade 4 Apply Table Entry."
    INDEX { apexDepiSessionConfigBlade4ApplyOutputTsNum }
::= { apexDepiSessionConfigBlade4ApplyTable 1 }

ApexDepiSessionConfigBlade4ApplyEntry ::= SEQUENCE
    {
     apexDepiSessionConfigBlade4ApplyOutputTsNum    Integer32,
     apexDepiSessionConfigBlade4ApplyChange         ApplyDataToDeviceTYPE
    }

apexDepiSessionConfigBlade4ApplyOutputTsNum OBJECT-TYPE
    SYNTAX Integer32(1..256)
    MAX-ACCESS not-accessible
    STATUS current
    DESCRIPTION
        "The index of the Depi Session Config Apply Table."
::= { apexDepiSessionConfigBlade4ApplyEntry 1 }

apexDepiSessionConfigBlade4ApplyChange OBJECT-TYPE
    SYNTAX ApplyDataToDeviceTYPE
    MAX-ACCESS read-write
    STATUS current
    DESCRIPTION
        "The Apply for any entries in the apexDepiSessionConfigBlade4Table.

         This parameter MUST be set to 'apply' in order for any of the data
         in the apexDepiSessionConfigBlade4Table to take effect.  This
         parameter MUST be set LAST after all other data in the table entry has
         been configured.

         Once written, the change to this parameter will take immediate effect.

         @Config(config=no, reboot=no)
        "
::= { apexDepiSessionConfigBlade4ApplyEntry 2 }


-- ------------------------------------------------------------------------------
--
-- apexDepiSessionConfigBlade4Table
--

apexDepiSessionConfigBlade4Table OBJECT-TYPE
    SYNTAX SEQUENCE OF ApexDepiSessionConfigBlade4Entry
    MAX-ACCESS not-accessible
    STATUS current
    DESCRIPTION
        "Table of data for DEPI Session Mapping. There are
         48 rows in this table mapping QAM output TS to DEPI Session.

         Once written, the change to this table will only take immediate
         effect after apexDepiSessionConfigBlade4ApplyChange is set to 'apply'.
         However, in order for the change to persist through subsequent
         reboots or power cycles, the change must be saved via apexSaveConfig.

         @Config(config=yes, reboot=no)
         @Commit(param=apexDepiSessionConfigBlade4ApplyChange, value=2)
         @Save(apexSaveConfig, value=2)
         @File(depicfg.ini, type='ini')
        "
::= { apexDepiSessionConfigBlade4 2 }

apexDepiSessionConfigBlade4Entry OBJECT-TYPE
    SYNTAX ApexDepiSessionConfigBlade4Entry
    MAX-ACCESS not-accessible
    STATUS current
    DESCRIPTION
        "DEPI Session  Config Table Entry."
    INDEX { apexDepiSessionConfigBlade4OutputTsNum }
::= { apexDepiSessionConfigBlade4Table 1 }

ApexDepiSessionConfigBlade4Entry ::= SEQUENCE
    {
     apexDepiSessionConfigBlade4OutputTsNum     Integer32,
     apexDepiSessionConfigBlade4Enable          EnableDisableTYPE,
     apexDepiSessionConfigBlade4DocsisTsid      Unsigned32,
     apexDepiSessionConfigBlade4InterfaceNumber Integer32,
     apexDepiSessionConfigBlade4SourceIp        IpAddress
    }

apexDepiSessionConfigBlade4OutputTsNum OBJECT-TYPE
    SYNTAX Integer32(1..256)
    MAX-ACCESS not-accessible
    STATUS current
    DESCRIPTION
        "The QAM output transport stream number which to associate the DEPI Session.
        "
::= { apexDepiSessionConfigBlade4Entry 1 }

apexDepiSessionConfigBlade4Enable OBJECT-TYPE
    SYNTAX EnableDisableTYPE
    MAX-ACCESS read-write
    STATUS current
    DESCRIPTION
        "The enable setting for DEPI Session.

         Once written, the change to this parameter will take immediate
         effect.  In order for the change to persist through subsequent
         reboots or power cycles, the change must be saved via the
         apexSaveConfig parameter.
        "
::= { apexDepiSessionConfigBlade4Entry 2 }

apexDepiSessionConfigBlade4DocsisTsid OBJECT-TYPE
    SYNTAX Unsigned32(0..4294967295)
    MAX-ACCESS read-write
    STATUS current
    DESCRIPTION
        "The system wide unique M-CMTS TSID mapped to the QAM. This TSID is specified by the
         remote ID from the ICRQ message.
        "
::= { apexDepiSessionConfigBlade4Entry 3 }

apexDepiSessionConfigBlade4InterfaceNumber OBJECT-TYPE
    SYNTAX Integer32(1..12)
    MAX-ACCESS read-write
    STATUS current
    DESCRIPTION
        "Represents the Gigabit Ethernet interface number.
        "
::= { apexDepiSessionConfigBlade4Entry 4 }

apexDepiSessionConfigBlade4SourceIp OBJECT-TYPE
    SYNTAX IpAddress
    MAX-ACCESS read-write
    STATUS current
    DESCRIPTION
        "Represents the Source Ip Address for the session.
        "
::= { apexDepiSessionConfigBlade4Entry 5 }


-- ------------------------------------------------------------------------------
--
-- apexDepiSessionConfigBlade5
--
-- apexDepiSessionConfigBlade5ApplyTable
--

apexDepiSessionConfigBlade5ApplyTable OBJECT-TYPE
    SYNTAX SEQUENCE OF ApexDepiSessionConfigBlade5ApplyEntry
    MAX-ACCESS not-accessible
    STATUS current
    DESCRIPTION
        "Table of Apply Change for the data for apexDepiSessionConfigBlade5Table.
        "
::= { apexDepiSessionConfigBlade5 1 }

apexDepiSessionConfigBlade5ApplyEntry OBJECT-TYPE
    SYNTAX ApexDepiSessionConfigBlade5ApplyEntry
    MAX-ACCESS not-accessible
    STATUS current
    DESCRIPTION
        "DEPI Session Config Blade 5 Apply Table Entry."
    INDEX { apexDepiSessionConfigBlade5ApplyOutputTsNum }
::= { apexDepiSessionConfigBlade5ApplyTable 1 }

ApexDepiSessionConfigBlade5ApplyEntry ::= SEQUENCE
    {
     apexDepiSessionConfigBlade5ApplyOutputTsNum    Integer32,
     apexDepiSessionConfigBlade5ApplyChange         ApplyDataToDeviceTYPE
    }

apexDepiSessionConfigBlade5ApplyOutputTsNum OBJECT-TYPE
    SYNTAX Integer32(1..256)
    MAX-ACCESS not-accessible
    STATUS current
    DESCRIPTION
        "The index of the Depi Session Config Apply Table."
::= { apexDepiSessionConfigBlade5ApplyEntry 1 }

apexDepiSessionConfigBlade5ApplyChange OBJECT-TYPE
    SYNTAX ApplyDataToDeviceTYPE
    MAX-ACCESS read-write
    STATUS current
    DESCRIPTION
        "The Apply for any entries in the apexDepiSessionConfigBlade5Table.

         This parameter MUST be set to 'apply' in order for any of the data
         in the apexDepiSessionConfigBlade5Table to take effect.  This
         parameter MUST be set LAST after all other data in the table entry has
         been configured.

         Once written, the change to this parameter will take immediate effect.

         @Config(config=no, reboot=no)
        "
::= { apexDepiSessionConfigBlade5ApplyEntry 2 }


-- ------------------------------------------------------------------------------
--
-- apexDepiSessionConfigBlade5Table
--

apexDepiSessionConfigBlade5Table OBJECT-TYPE
    SYNTAX SEQUENCE OF ApexDepiSessionConfigBlade5Entry
    MAX-ACCESS not-accessible
    STATUS current
    DESCRIPTION
        "Table of data for DEPI Session Mapping. There are
         48 rows in this table mapping QAM output TS to DEPI Session.

         Once written, the change to this table will only take immediate
         effect after apexDepiSessionConfigBlade5ApplyChange is set to 'apply'.
         However, in order for the change to persist through subsequent
         reboots or power cycles, the change must be saved via apexSaveConfig.

         @Config(config=yes, reboot=no)
         @Commit(param=apexDepiSessionConfigBlade5ApplyChange, value=2)
         @Save(apexSaveConfig, value=2)
         @File(depicfg.ini, type='ini')
        "
::= { apexDepiSessionConfigBlade5 2 }

apexDepiSessionConfigBlade5Entry OBJECT-TYPE
    SYNTAX ApexDepiSessionConfigBlade5Entry
    MAX-ACCESS not-accessible
    STATUS current
    DESCRIPTION
        "DEPI Session  Config Table Entry."
    INDEX { apexDepiSessionConfigBlade5OutputTsNum }
::= { apexDepiSessionConfigBlade5Table 1 }

ApexDepiSessionConfigBlade5Entry ::= SEQUENCE
    {
     apexDepiSessionConfigBlade5OutputTsNum     Integer32,
     apexDepiSessionConfigBlade5Enable          EnableDisableTYPE,
     apexDepiSessionConfigBlade5DocsisTsid      Unsigned32,
     apexDepiSessionConfigBlade5InterfaceNumber Integer32,
     apexDepiSessionConfigBlade5SourceIp        IpAddress
    }

apexDepiSessionConfigBlade5OutputTsNum OBJECT-TYPE
    SYNTAX Integer32(1..256)
    MAX-ACCESS not-accessible
    STATUS current
    DESCRIPTION
        "The QAM output transport stream number which to associate the DEPI Session.
        "
::= { apexDepiSessionConfigBlade5Entry 1 }

apexDepiSessionConfigBlade5Enable OBJECT-TYPE
    SYNTAX EnableDisableTYPE
    MAX-ACCESS read-write
    STATUS current
    DESCRIPTION
        "The enable setting for DEPI Session.

         Once written, the change to this parameter will take immediate
         effect.  In order for the change to persist through subsequent
         reboots or power cycles, the change must be saved via the
         apexSaveConfig parameter.
        "
::= { apexDepiSessionConfigBlade5Entry 2 }

apexDepiSessionConfigBlade5DocsisTsid OBJECT-TYPE
    SYNTAX Unsigned32(0..4294967295)
    MAX-ACCESS read-write
    STATUS current
    DESCRIPTION
        "The system wide unique M-CMTS TSID mapped to the QAM. This TSID is specified by the
         remote ID from the ICRQ message.
        "
::= { apexDepiSessionConfigBlade5Entry 3 }

apexDepiSessionConfigBlade5InterfaceNumber OBJECT-TYPE
    SYNTAX Integer32(1..12)
    MAX-ACCESS read-write
    STATUS current
    DESCRIPTION
        "Represents the Gigabit Ethernet interface number.
        "
::= { apexDepiSessionConfigBlade5Entry 4 }

apexDepiSessionConfigBlade5SourceIp OBJECT-TYPE
    SYNTAX IpAddress
    MAX-ACCESS read-write
    STATUS current
    DESCRIPTION
        "Represents the Source Ip Address for the session.
        "
::= { apexDepiSessionConfigBlade5Entry 5 }


-- ------------------------------------------------------------------------------
--
-- apexDepiSessionConfigBlade6
--
-- apexDepiSessionConfigBlade6ApplyTable
--

apexDepiSessionConfigBlade6ApplyTable OBJECT-TYPE
    SYNTAX SEQUENCE OF ApexDepiSessionConfigBlade6ApplyEntry
    MAX-ACCESS not-accessible
    STATUS current
    DESCRIPTION
        "Table of Apply Change for the data for apexDepiSessionConfigBlade6Table.
        "
::= { apexDepiSessionConfigBlade6 1 }

apexDepiSessionConfigBlade6ApplyEntry OBJECT-TYPE
    SYNTAX ApexDepiSessionConfigBlade6ApplyEntry
    MAX-ACCESS not-accessible
    STATUS current
    DESCRIPTION
        "DEPI Session Config Blade 6 Apply Table Entry."
    INDEX { apexDepiSessionConfigBlade6ApplyOutputTsNum }
::= { apexDepiSessionConfigBlade6ApplyTable 1 }

ApexDepiSessionConfigBlade6ApplyEntry ::= SEQUENCE
    {
     apexDepiSessionConfigBlade6ApplyOutputTsNum    Integer32,
     apexDepiSessionConfigBlade6ApplyChange         ApplyDataToDeviceTYPE
    }

apexDepiSessionConfigBlade6ApplyOutputTsNum OBJECT-TYPE
    SYNTAX Integer32(1..256)
    MAX-ACCESS not-accessible
    STATUS current
    DESCRIPTION
        "The index of the Depi Session Config Apply Table."
::= { apexDepiSessionConfigBlade6ApplyEntry 1 }

apexDepiSessionConfigBlade6ApplyChange OBJECT-TYPE
    SYNTAX ApplyDataToDeviceTYPE
    MAX-ACCESS read-write
    STATUS current
    DESCRIPTION
        "The Apply for any entries in the apexDepiSessionConfigBlade6Table.

         This parameter MUST be set to 'apply' in order for any of the data
         in the apexDepiSessionConfigBlade6Table to take effect.  This
         parameter MUST be set LAST after all other data in the table entry has
         been configured.

         Once written, the change to this parameter will take immediate effect.

         @Config(config=no, reboot=no)
        "
::= { apexDepiSessionConfigBlade6ApplyEntry 2 }


-- ------------------------------------------------------------------------------
--
-- apexDepiSessionConfigBlade6Table
--

apexDepiSessionConfigBlade6Table OBJECT-TYPE
    SYNTAX SEQUENCE OF ApexDepiSessionConfigBlade6Entry
    MAX-ACCESS not-accessible
    STATUS current
    DESCRIPTION
        "Table of data for DEPI Session Mapping. There are
         48 rows in this table mapping QAM output TS to DEPI Session.

         Once written, the change to this table will only take immediate
         effect after apexDepiSessionConfigBlade6ApplyChange is set to 'apply'.
         However, in order for the change to persist through subsequent
         reboots or power cycles, the change must be saved via apexSaveConfig.

         @Config(config=yes, reboot=no)
         @Commit(param=apexDepiSessionConfigBlade6ApplyChange, value=2)
         @Save(apexSaveConfig, value=2)
         @File(depicfg.ini, type='ini')
        "
::= { apexDepiSessionConfigBlade6 2 }

apexDepiSessionConfigBlade6Entry OBJECT-TYPE
    SYNTAX ApexDepiSessionConfigBlade6Entry
    MAX-ACCESS not-accessible
    STATUS current
    DESCRIPTION
        "DEPI Session  Config Table Entry."
    INDEX { apexDepiSessionConfigBlade6OutputTsNum }
::= { apexDepiSessionConfigBlade6Table 8 }

ApexDepiSessionConfigBlade6Entry ::= SEQUENCE
    {
     apexDepiSessionConfigBlade6OutputTsNum     Integer32,
     apexDepiSessionConfigBlade6Enable          EnableDisableTYPE,
     apexDepiSessionConfigBlade6DocsisTsid      Unsigned32,
     apexDepiSessionConfigBlade6InterfaceNumber Integer32,
     apexDepiSessionConfigBlade6SourceIp        IpAddress
    }

apexDepiSessionConfigBlade6OutputTsNum OBJECT-TYPE
    SYNTAX Integer32(1..256)
    MAX-ACCESS not-accessible
    STATUS current
    DESCRIPTION
        "The QAM output transport stream number which to associate the DEPI Session.
        "
::= { apexDepiSessionConfigBlade6Entry 1 }

apexDepiSessionConfigBlade6Enable OBJECT-TYPE
    SYNTAX EnableDisableTYPE
    MAX-ACCESS read-write
    STATUS current
    DESCRIPTION
        "The enable setting for DEPI Session.

         Once written, the change to this parameter will take immediate
         effect.  In order for the change to persist through subsequent
         reboots or power cycles, the change must be saved via the
         apexSaveConfig parameter.
        "
::= { apexDepiSessionConfigBlade6Entry 2 }

apexDepiSessionConfigBlade6DocsisTsid OBJECT-TYPE
    SYNTAX Unsigned32(0..4294967295)
    MAX-ACCESS read-write
    STATUS current
    DESCRIPTION
        "The system wide unique M-CMTS TSID mapped to the QAM. This TSID is specified by the
         remote ID from the ICRQ message.
        "
::= { apexDepiSessionConfigBlade6Entry 3 }

apexDepiSessionConfigBlade6InterfaceNumber OBJECT-TYPE
    SYNTAX Integer32(1..12)
    MAX-ACCESS read-write
    STATUS current
    DESCRIPTION
        "Represents the Gigabit Ethernet interface number.
        "
::= { apexDepiSessionConfigBlade6Entry 4 }

apexDepiSessionConfigBlade6SourceIp OBJECT-TYPE
    SYNTAX IpAddress
    MAX-ACCESS read-write
    STATUS current
    DESCRIPTION
        "Represents the Source Ip Address for the session.
        "
::= { apexDepiSessionConfigBlade6Entry 5 }


-- ------------------------------------------------------------------------------
--
-- apexDepiSessionConfigBlade7
--
-- apexDepiSessionConfigBlade7ApplyTable
--

apexDepiSessionConfigBlade7ApplyTable OBJECT-TYPE
    SYNTAX SEQUENCE OF ApexDepiSessionConfigBlade7ApplyEntry
    MAX-ACCESS not-accessible
    STATUS current
    DESCRIPTION
        "Table of Apply Change for the data for apexDepiSessionConfigBlade7Table.
        "
::= { apexDepiSessionConfigBlade7 1 }

apexDepiSessionConfigBlade7ApplyEntry OBJECT-TYPE
    SYNTAX ApexDepiSessionConfigBlade7ApplyEntry
    MAX-ACCESS not-accessible
    STATUS current
    DESCRIPTION
        "DEPI Session Config Blade 7 Apply Table Entry."
    INDEX { apexDepiSessionConfigBlade7ApplyOutputTsNum }
::= { apexDepiSessionConfigBlade7ApplyTable 1 }

ApexDepiSessionConfigBlade7ApplyEntry ::= SEQUENCE
    {
     apexDepiSessionConfigBlade7ApplyOutputTsNum    Integer32,
     apexDepiSessionConfigBlade7ApplyChange         ApplyDataToDeviceTYPE
    }

apexDepiSessionConfigBlade7ApplyOutputTsNum OBJECT-TYPE
    SYNTAX Integer32(1..256)
    MAX-ACCESS not-accessible
    STATUS current
    DESCRIPTION
        "The index of the Depi Session Config Apply Table."
::= { apexDepiSessionConfigBlade7ApplyEntry 1 }

apexDepiSessionConfigBlade7ApplyChange OBJECT-TYPE
    SYNTAX ApplyDataToDeviceTYPE
    MAX-ACCESS read-write
    STATUS current
    DESCRIPTION
        "The Apply for any entries in the apexDepiSessionConfigBlade7Table.

         This parameter MUST be set to 'apply' in order for any of the data
         in the apexDepiSessionConfigBlade7Table to take effect.  This
         parameter MUST be set LAST after all other data in the table entry has
         been configured.

         Once written, the change to this parameter will take immediate effect.

         @Config(config=no, reboot=no)
        "
::= { apexDepiSessionConfigBlade7ApplyEntry 2 }


-- ------------------------------------------------------------------------------
--
-- apexDepiSessionConfigBlade7Table
--

apexDepiSessionConfigBlade7Table OBJECT-TYPE
    SYNTAX SEQUENCE OF ApexDepiSessionConfigBlade7Entry
    MAX-ACCESS not-accessible
    STATUS current
    DESCRIPTION
        "Table of data for DEPI Session Mapping. There are
         48 rows in this table mapping QAM output TS to DEPI Session.

         Once written, the change to this table will only take immediate
         effect after apexDepiSessionConfigBlade7ApplyChange is set to 'apply'.
         However, in order for the change to persist through subsequent
         reboots or power cycles, the change must be saved via apexSaveConfig.

         @Config(config=yes, reboot=no)
         @Commit(param=apexDepiSessionConfigBlade7ApplyChange, value=2)
         @Save(apexSaveConfig, value=2)
         @File(depicfg.ini, type='ini')
        "
::= { apexDepiSessionConfigBlade7 2 }

apexDepiSessionConfigBlade7Entry OBJECT-TYPE
    SYNTAX ApexDepiSessionConfigBlade7Entry
    MAX-ACCESS not-accessible
    STATUS current
    DESCRIPTION
        "DEPI Session  Config Table Entry."
    INDEX { apexDepiSessionConfigBlade7OutputTsNum }
::= { apexDepiSessionConfigBlade7Table 8 }

ApexDepiSessionConfigBlade7Entry ::= SEQUENCE
    {
     apexDepiSessionConfigBlade7OutputTsNum     Integer32,
     apexDepiSessionConfigBlade7Enable          EnableDisableTYPE,
     apexDepiSessionConfigBlade7DocsisTsid      Unsigned32,
     apexDepiSessionConfigBlade7InterfaceNumber Integer32,
     apexDepiSessionConfigBlade7SourceIp        IpAddress
    }

apexDepiSessionConfigBlade7OutputTsNum OBJECT-TYPE
    SYNTAX Integer32(1..256)
    MAX-ACCESS not-accessible
    STATUS current
    DESCRIPTION
        "The QAM output transport stream number which to associate the DEPI Session.
        "
::= { apexDepiSessionConfigBlade7Entry 1 }

apexDepiSessionConfigBlade7Enable OBJECT-TYPE
    SYNTAX EnableDisableTYPE
    MAX-ACCESS read-write
    STATUS current
    DESCRIPTION
        "The enable setting for DEPI Session.

         Once written, the change to this parameter will take immediate
         effect.  In order for the change to persist through subsequent
         reboots or power cycles, the change must be saved via the
         apexSaveConfig parameter.
        "
::= { apexDepiSessionConfigBlade7Entry 2 }

apexDepiSessionConfigBlade7DocsisTsid OBJECT-TYPE
    SYNTAX Unsigned32(0..4294967295)
    MAX-ACCESS read-write
    STATUS current
    DESCRIPTION
        "The system wide unique M-CMTS TSID mapped to the QAM. This TSID is specified by the
         remote ID from the ICRQ message.
        "
::= { apexDepiSessionConfigBlade7Entry 3 }

apexDepiSessionConfigBlade7InterfaceNumber OBJECT-TYPE
    SYNTAX Integer32(1..12)
    MAX-ACCESS read-write
    STATUS current
    DESCRIPTION
        "Represents the Gigabit Ethernet interface number.
        "
::= { apexDepiSessionConfigBlade7Entry 4 }

apexDepiSessionConfigBlade7SourceIp OBJECT-TYPE
    SYNTAX IpAddress
    MAX-ACCESS read-write
    STATUS current
    DESCRIPTION
        "Represents the Source Ip Address for the session.
        "
::= { apexDepiSessionConfigBlade7Entry 5 }


-- ------------------------------------------------------------------------------
--
-- apexDepiSessionConfigBlade8
--
-- apexDepiSessionConfigBlade8ApplyTable
--

apexDepiSessionConfigBlade8ApplyTable OBJECT-TYPE
    SYNTAX SEQUENCE OF ApexDepiSessionConfigBlade8ApplyEntry
    MAX-ACCESS not-accessible
    STATUS current
    DESCRIPTION
        "Table of Apply Change for the data for apexDepiSessionConfigBlade8Table.
        "
::= { apexDepiSessionConfigBlade8 1 }

apexDepiSessionConfigBlade8ApplyEntry OBJECT-TYPE
    SYNTAX ApexDepiSessionConfigBlade8ApplyEntry
    MAX-ACCESS not-accessible
    STATUS current
    DESCRIPTION
        "DEPI Session Config Blade 8 Apply Table Entry."
    INDEX { apexDepiSessionConfigBlade8ApplyOutputTsNum }
::= { apexDepiSessionConfigBlade8ApplyTable 1 }

ApexDepiSessionConfigBlade8ApplyEntry ::= SEQUENCE
    {
     apexDepiSessionConfigBlade8ApplyOutputTsNum    Integer32,
     apexDepiSessionConfigBlade8ApplyChange         ApplyDataToDeviceTYPE
    }

apexDepiSessionConfigBlade8ApplyOutputTsNum OBJECT-TYPE
    SYNTAX Integer32(1..256)
    MAX-ACCESS not-accessible
    STATUS current
    DESCRIPTION
        "The index of the Depi Session Config Apply Table."
::= { apexDepiSessionConfigBlade8ApplyEntry 1 }

apexDepiSessionConfigBlade8ApplyChange OBJECT-TYPE
    SYNTAX ApplyDataToDeviceTYPE
    MAX-ACCESS read-write
    STATUS current
    DESCRIPTION
        "The Apply for any entries in the apexDepiSessionConfigBlade8Table.

         This parameter MUST be set to 'apply' in order for any of the data
         in the apexDepiSessionConfigBlade8Table to take effect.  This
         parameter MUST be set LAST after all other data in the table entry has
         been configured.

         Once written, the change to this parameter will take immediate effect.

         @Config(config=no, reboot=no)
        "
::= { apexDepiSessionConfigBlade8ApplyEntry 2 }


-- ------------------------------------------------------------------------------
--
-- apexDepiSessionConfigBlade8Table
--

apexDepiSessionConfigBlade8Table OBJECT-TYPE
    SYNTAX SEQUENCE OF ApexDepiSessionConfigBlade8Entry
    MAX-ACCESS not-accessible
    STATUS current
    DESCRIPTION
        "Table of data for DEPI Session Mapping. There are
         48 rows in this table mapping QAM output TS to DEPI Session.

         Once written, the change to this table will only take immediate
         effect after apexDepiSessionConfigBlade8ApplyChange is set to 'apply'.
         However, in order for the change to persist through subsequent
         reboots or power cycles, the change must be saved via apexSaveConfig.

         @Config(config=yes, reboot=no)
         @Commit(param=apexDepiSessionConfigBlade8ApplyChange, value=2)
         @Save(apexSaveConfig, value=2)
         @File(depicfg.ini, type='ini')
        "
::= { apexDepiSessionConfigBlade8 2 }

apexDepiSessionConfigBlade8Entry OBJECT-TYPE
    SYNTAX ApexDepiSessionConfigBlade8Entry
    MAX-ACCESS not-accessible
    STATUS current
    DESCRIPTION
        "DEPI Session  Config Table Entry."
    INDEX { apexDepiSessionConfigBlade8OutputTsNum }
::= { apexDepiSessionConfigBlade8Table 8 }

ApexDepiSessionConfigBlade8Entry ::= SEQUENCE
    {
     apexDepiSessionConfigBlade8OutputTsNum     Integer32,
     apexDepiSessionConfigBlade8Enable          EnableDisableTYPE,
     apexDepiSessionConfigBlade8DocsisTsid      Unsigned32,
     apexDepiSessionConfigBlade8InterfaceNumber Integer32,
     apexDepiSessionConfigBlade8SourceIp        IpAddress
    }

apexDepiSessionConfigBlade8OutputTsNum OBJECT-TYPE
    SYNTAX Integer32(1..256)
    MAX-ACCESS not-accessible
    STATUS current
    DESCRIPTION
        "The QAM output transport stream number which to associate the DEPI Session.
        "
::= { apexDepiSessionConfigBlade8Entry 1 }

apexDepiSessionConfigBlade8Enable OBJECT-TYPE
    SYNTAX EnableDisableTYPE
    MAX-ACCESS read-write
    STATUS current
    DESCRIPTION
        "The enable setting for DEPI Session.

         Once written, the change to this parameter will take immediate
         effect.  In order for the change to persist through subsequent
         reboots or power cycles, the change must be saved via the
         apexSaveConfig parameter.
        "
::= { apexDepiSessionConfigBlade8Entry 2 }

apexDepiSessionConfigBlade8DocsisTsid OBJECT-TYPE
    SYNTAX Unsigned32(0..4294967295)
    MAX-ACCESS read-write
    STATUS current
    DESCRIPTION
        "The system wide unique M-CMTS TSID mapped to the QAM. This TSID is specified by the
         remote ID from the ICRQ message.
        "
::= { apexDepiSessionConfigBlade8Entry 3 }

apexDepiSessionConfigBlade8InterfaceNumber OBJECT-TYPE
    SYNTAX Integer32(1..12)
    MAX-ACCESS read-write
    STATUS current
    DESCRIPTION
        "Represents the Gigabit Ethernet interface number.
        "
::= { apexDepiSessionConfigBlade8Entry 4 }

apexDepiSessionConfigBlade8SourceIp OBJECT-TYPE
    SYNTAX IpAddress
    MAX-ACCESS read-write
    STATUS current
    DESCRIPTION
        "Represents the Source Ip Address for the session.
        "
::= { apexDepiSessionConfigBlade8Entry 5 }

apexDepiSessionEnableDisableApply OBJECT-TYPE
    SYNTAX EnableDisableAllTYPE
    MAX-ACCESS read-write
    STATUS current
    DESCRIPTION
        "Setting this causes all static DEPI sessions on the specified blade
         or on all blades to be enabled or disabled. When enabling routes,
         only routes that have a valid GigE interface and a valid session id 
         defined will be enabled. This allows for all static DEPI sessions
         to quickly be enabled or disabled.
         
         This affects manual routed services only.
         
         Upon setting this field, no changes will take affect until after
         the APEX sets this field back to notInProgress.
         
         @Config(config=no, reboot=no)
        "
::= { apexDepiSessionConfig 9 }


-- ------------------------------------------------------------------------------
--
-- apexDepiSessionStatus 
--
-- apexDepiSessionStatusGeneral
--

apexDepiSessionStatusGeneralInvalidApplyText OBJECT-TYPE
    SYNTAX DisplayString (SIZE (0..80))
    MAX-ACCESS read-only
    STATUS current
    DESCRIPTION
        "When apexDepiSessionConfigApplyChange is set to
         'applyNotInProgressInvalidData' this entry may contain
         a text description of what was wrong with the data. This
         entry contains the description for the most recent apply
         of a related entry that was invalid.
        "
::= { apexDepiSessionStatusGeneral 1 }

apexDepiSessionStatusGeneralTotalSessions  OBJECT-TYPE
    SYNTAX Unsigned32
    MAX-ACCESS read-only
    STATUS obsolete
    DESCRIPTION
        "This object is obsolete.
         Number of session established.
        "
::= { apexDepiSessionStatusGeneral 2 }

apexDepiSessionStatusGeneralDiscardedNoSession  OBJECT-TYPE
    SYNTAX Unsigned32
    MAX-ACCESS read-only
    STATUS obsolete
    DESCRIPTION
        "This object is obsolete.
         Number of discarded messages not belonging to any session.
        "
::= { apexDepiSessionStatusGeneral 3 }


-- ------------------------------------------------------------------------------
--
-- apexDepiSessionStatusBlade1
--
-- apexDepiSessionStatusBlade1Table
--

apexDepiSessionStatusBlade1Table OBJECT-TYPE
    SYNTAX SEQUENCE OF ApexDepiSessionStatusBlade1Entry
    MAX-ACCESS not-accessible
    STATUS obsolete
    DESCRIPTION
        "This object is obsolete.
         Table of read-only status information pertaining to the DEPI Sessions.
        "
::= { apexDepiSessionStatusBlade1 1 }

apexDepiSessionStatusBlade1Entry OBJECT-TYPE
    SYNTAX ApexDepiSessionStatusBlade1Entry
    MAX-ACCESS not-accessible
    STATUS obsolete
    DESCRIPTION
        "This object is obsolete.
         DEPI Session Status Table Entry.
        "
    INDEX { apexDepiSessionStatusBlade1Index}
::= { apexDepiSessionStatusBlade1Table 1 }

ApexDepiSessionStatusBlade1Entry ::= SEQUENCE
    {
      apexDepiSessionStatusBlade1Index                   Integer32,
      apexDepiSessionStatusBlade1OutputQAMChannel        Integer32,
      apexDepiSessionStatusBlade1Status                  INTEGER,
      apexDepiSessionStatusBlade1InDataPackets           Unsigned32,
      apexDepiSessionStatusBlade1InSequenceDiscards      Unsigned32,
      apexDepiSessionStatusBlade1InDataPacketDiscards    Unsigned32,
      apexDepiSessionStatusBlade1SessionID               Unsigned32,
      apexDepiSessionStatusBlade1InputIf                 Integer32,
      apexDepiSessionStatusBlade1DataRate                Integer32,
      apexDepiSessionStatusBlade1SourceIp                IpAddress
    }

apexDepiSessionStatusBlade1Index OBJECT-TYPE
    SYNTAX Integer32
    MAX-ACCESS not-accessible
    STATUS obsolete
    DESCRIPTION
        "DEPI Session ID."
::= { apexDepiSessionStatusBlade1Entry 1 }

apexDepiSessionStatusBlade1OutputQAMChannel OBJECT-TYPE
    SYNTAX Integer32
    MAX-ACCESS read-only
    STATUS obsolete
    DESCRIPTION
        "This object is obsolete.
         The QAM Channel number this session is mapped to.
        "
::= { apexDepiSessionStatusBlade1Entry 2 }

apexDepiSessionStatusBlade1Status OBJECT-TYPE
    SYNTAX INTEGER
        {
         terminated          (1),
         failed              (2),
         waiting             (3),
         established         (4)
        }
    MAX-ACCESS read-only
    STATUS obsolete
    DESCRIPTION
        "This object is obsolete.
         M-CMTS core to the EQAM control connection status
        "
::= { apexDepiSessionStatusBlade1Entry 3 }

apexDepiSessionStatusBlade1InDataPackets OBJECT-TYPE
    SYNTAX Unsigned32
    MAX-ACCESS read-only
    STATUS obsolete
    DESCRIPTION
        "This object is obsolete.
         Number of data packets received on this session.
        "
::= { apexDepiSessionStatusBlade1Entry 4 }

apexDepiSessionStatusBlade1InSequenceDiscards OBJECT-TYPE
    SYNTAX Unsigned32
    MAX-ACCESS read-only
    STATUS obsolete
    DESCRIPTION
        "This object is obsolete.
         Number of data packets received on this session that are discarded
         due to sequencing error.
        "
::= { apexDepiSessionStatusBlade1Entry 5 }

apexDepiSessionStatusBlade1InDataPacketDiscards OBJECT-TYPE
    SYNTAX Unsigned32
    MAX-ACCESS read-only
    STATUS obsolete
    DESCRIPTION
        "This object is obsolete.
         Number of data packets received on this session that are discarded
         for reasons other than sequencing errors.
        "
::= { apexDepiSessionStatusBlade1Entry 6 }

apexDepiSessionStatusBlade1SessionID OBJECT-TYPE
    SYNTAX Unsigned32
    MAX-ACCESS read-only
    STATUS obsolete
    DESCRIPTION
        "This object is obsolete.
         Local DEPI Session ID, used locally to bind the Session to a QAM Channel.
        "
::= { apexDepiSessionStatusBlade1Entry 7 }

apexDepiSessionStatusBlade1InputIf OBJECT-TYPE
    SYNTAX Integer32 (1..12)
    MAX-ACCESS read-only
    STATUS obsolete
    DESCRIPTION
        "This object is obsolete.
         Interface number.
        "
::= { apexDepiSessionStatusBlade1Entry 8 }

apexDepiSessionStatusBlade1DataRate OBJECT-TYPE
    SYNTAX Integer32
    MAX-ACCESS read-only
    STATUS obsolete
    DESCRIPTION
        "This object is obsolete.
         Data rate.
        "
::= { apexDepiSessionStatusBlade1Entry 9 }

apexDepiSessionStatusBlade1SourceIp OBJECT-TYPE
    SYNTAX IpAddress
    MAX-ACCESS read-only
    STATUS obsolete
    DESCRIPTION
        "This object is obsolete.
         Source IP Address.
        "
::= { apexDepiSessionStatusBlade1Entry 10 }


-- ------------------------------------------------------------------------------
--
-- apexDepiSessionStatusBlade1TotalSessions 
--

apexDepiSessionStatusBlade1TotalSessions  OBJECT-TYPE
    SYNTAX Unsigned32
    MAX-ACCESS read-only
    STATUS obsolete
    DESCRIPTION
        "This object is obsolete.
         Number of session established in this blade.
        "
::= { apexDepiSessionStatusBlade1 2 }


-- ------------------------------------------------------------------------------
--
-- apexDepiSessionBlade1StatusTable 
--

apexDepiSessionBlade1StatusTable OBJECT-TYPE
    SYNTAX SEQUENCE OF ApexDepiSessionBlade1StatusEntry
    MAX-ACCESS not-accessible
    STATUS current
    DESCRIPTION
        "Table of read-only status information pertaining to the DEPI Sessions."
::= { apexDepiSessionStatusBlade1 3 }

apexDepiSessionBlade1StatusEntry OBJECT-TYPE
    SYNTAX ApexDepiSessionBlade1StatusEntry
    MAX-ACCESS not-accessible
    STATUS current
    DESCRIPTION
        "DEPI Session Status Table Entry."
    INDEX { apexDepiSessionBlade1StatusOutputOtsNum, apexDepiSessionBlade1StatusIndex }
::= { apexDepiSessionBlade1StatusTable 1 }

ApexDepiSessionBlade1StatusEntry ::= SEQUENCE
    {
      apexDepiSessionBlade1StatusOutputOtsNum            Integer32,
      apexDepiSessionBlade1StatusIndex                   Integer32,
      apexDepiSessionBlade1StatusStatus                  INTEGER,
      apexDepiSessionBlade1StatusInDataPackets           Unsigned32,
      apexDepiSessionBlade1StatusInSequenceDiscards      Unsigned32,
      apexDepiSessionBlade1StatusInDataPacketDiscards    Unsigned32,
      apexDepiSessionBlade1StatusSessionID               Unsigned32,
      apexDepiSessionBlade1StatusInputIf                 Integer32,
      apexDepiSessionBlade1StatusDataRate                Integer32,
      apexDepiSessionBlade1StatusSourceIp                IpAddress,
      apexDepiSessionBlade1StatusActivationMode          INTEGER,
      apexDepiSessionBlade1StatusCCid                    Unsigned32,
      apexDepiSessionBlade1StatusSessionType             INTEGER,
      apexDepiSessionBlade1StatusSyncRequired            INTEGER,
      apexDepiSessionBlade1StatusRemoteSessionId         Unsigned32,
      apexDepiSessionBlade1StatusInputTsIndex            Integer32
    }

apexDepiSessionBlade1StatusOutputOtsNum OBJECT-TYPE
    SYNTAX Integer32 (1..256)
    MAX-ACCESS read-only
    STATUS current
    DESCRIPTION
        "The QAM Channel number this session is mapped to."
::= { apexDepiSessionBlade1StatusEntry 1 }

apexDepiSessionBlade1StatusIndex OBJECT-TYPE
    SYNTAX Integer32 (1..5)
    MAX-ACCESS read-only
    STATUS current
    DESCRIPTION
        "Indexes the position of the session entry inside this OTS."
::= { apexDepiSessionBlade1StatusEntry 2 }

apexDepiSessionBlade1StatusStatus OBJECT-TYPE
    SYNTAX INTEGER
        {
         idle        (1),
         down        (2),
         settingup   (3),
         established (4)
        }
    MAX-ACCESS read-only
    STATUS current
    DESCRIPTION
        "M-CMTS core to the EQAM control connection status."
::= { apexDepiSessionBlade1StatusEntry 3 }

apexDepiSessionBlade1StatusInDataPackets OBJECT-TYPE
    SYNTAX Unsigned32
    MAX-ACCESS read-only
    STATUS current
    DESCRIPTION
        "Number of data packets received on this session."
::= { apexDepiSessionBlade1StatusEntry 4 }

apexDepiSessionBlade1StatusInSequenceDiscards OBJECT-TYPE
    SYNTAX Unsigned32
    MAX-ACCESS read-only
    STATUS current
    DESCRIPTION
        "Number of data packets received on this session that are discarded
         due to sequencing error."
::= { apexDepiSessionBlade1StatusEntry 5 }

apexDepiSessionBlade1StatusInDataPacketDiscards OBJECT-TYPE
    SYNTAX Unsigned32
    MAX-ACCESS read-only
    STATUS current
    DESCRIPTION
        "Number of data packets received on this session that are discarded
         for reasons other than sequencing errors."
::= { apexDepiSessionBlade1StatusEntry 6 }

apexDepiSessionBlade1StatusSessionID OBJECT-TYPE
    SYNTAX Unsigned32
    MAX-ACCESS read-only
    STATUS current
    DESCRIPTION
        "Local DEPI Session ID, used locally to bind the Session to a QAM Channel."
::= { apexDepiSessionBlade1StatusEntry 7 }

apexDepiSessionBlade1StatusInputIf OBJECT-TYPE
    SYNTAX Integer32 (1..12)
    MAX-ACCESS read-only
    STATUS current
    DESCRIPTION
        "Interface number.
        "
::= { apexDepiSessionBlade1StatusEntry 8 }

apexDepiSessionBlade1StatusDataRate OBJECT-TYPE
    SYNTAX Integer32
    MAX-ACCESS read-only
    STATUS current
    DESCRIPTION
        "Data rate.
        "
::= { apexDepiSessionBlade1StatusEntry 9 }

apexDepiSessionBlade1StatusSourceIp OBJECT-TYPE
    SYNTAX IpAddress
    MAX-ACCESS read-only
    STATUS current
    DESCRIPTION
        "Source IP Address.
        "
::= { apexDepiSessionBlade1StatusEntry 10 }


apexDepiSessionBlade1StatusActivationMode OBJECT-TYPE
    SYNTAX INTEGER
        {
         unknown      (0),
         static       (1),
         controlplane (2)
        }
    MAX-ACCESS read-only
    STATUS current
    DESCRIPTION
        "Activation mode of the session.
        "
::= { apexDepiSessionBlade1StatusEntry 11 }
   
apexDepiSessionBlade1StatusCCid OBJECT-TYPE
    SYNTAX          Unsigned32
    MAX-ACCESS read-only
    STATUS current
    DESCRIPTION
        "Control connection id if applicable.
        "
::= { apexDepiSessionBlade1StatusEntry 12 }

apexDepiSessionBlade1StatusSessionType OBJECT-TYPE
    SYNTAX INTEGER
        {
         unknown   (0),
         primary   (1),
         secondary (2)
        }
    MAX-ACCESS read-only
    STATUS current
    DESCRIPTION
        "Primary/secondary.
        "
::= { apexDepiSessionBlade1StatusEntry 13 }

apexDepiSessionBlade1StatusSyncRequired OBJECT-TYPE
    SYNTAX INTEGER
        {
         unknown (0),
         yes     (1),
         no      (2)
        }
    MAX-ACCESS read-only
    STATUS current
    DESCRIPTION
        "Sync correction required.
        "
::= { apexDepiSessionBlade1StatusEntry 14 }

apexDepiSessionBlade1StatusRemoteSessionId OBJECT-TYPE
    SYNTAX Unsigned32
    MAX-ACCESS read-only
    STATUS current
    DESCRIPTION
        "Remote DEPI Session ID, used by the Remote End to identify the DEPI
         Session."
::= { apexDepiSessionBlade1StatusEntry 15 }

apexDepiSessionBlade1StatusInputTsIndex OBJECT-TYPE
    SYNTAX Integer32
    MAX-ACCESS read-only
    STATUS current
    DESCRIPTION
        "The index into the apexGbeStatusInputTsStatTable."
::= { apexDepiSessionBlade1StatusEntry 16 }


-- ------------------------------------------------------------------------------
--
-- apexDepiSessionStatusBlade2
--
-- apexDepiSessionStatusBlade2Table
--

apexDepiSessionStatusBlade2Table OBJECT-TYPE
    SYNTAX SEQUENCE OF ApexDepiSessionStatusBlade2Entry
    MAX-ACCESS not-accessible
    STATUS obsolete
    DESCRIPTION
        "This object is obsolete.
         Table of read-only status information pertaining to the DEPI Sessions.
        "
::= { apexDepiSessionStatusBlade2 1 }

apexDepiSessionStatusBlade2Entry OBJECT-TYPE
    SYNTAX ApexDepiSessionStatusBlade2Entry
    MAX-ACCESS not-accessible
    STATUS obsolete
    DESCRIPTION
        "This object is obsolete.
         DEPI Session Status Table Entry.
        "
    INDEX { apexDepiSessionStatusBlade2Index}
::= { apexDepiSessionStatusBlade2Table 1 }

ApexDepiSessionStatusBlade2Entry ::= SEQUENCE
    {
      apexDepiSessionStatusBlade2Index                   Integer32,
      apexDepiSessionStatusBlade2OutputQAMChannel        Integer32,
      apexDepiSessionStatusBlade2Status                  INTEGER,
      apexDepiSessionStatusBlade2InDataPackets           Unsigned32,
      apexDepiSessionStatusBlade2InSequenceDiscards      Unsigned32,
      apexDepiSessionStatusBlade2InDataPacketDiscards    Unsigned32,
      apexDepiSessionStatusBlade2SessionID               Unsigned32,
      apexDepiSessionStatusBlade2InputIf                 Integer32,
      apexDepiSessionStatusBlade2DataRate                Integer32,
      apexDepiSessionStatusBlade2SourceIp                IpAddress
    }

apexDepiSessionStatusBlade2Index OBJECT-TYPE
    SYNTAX Integer32
    MAX-ACCESS not-accessible
    STATUS obsolete
    DESCRIPTION
        "This object is obsolete.
         DEPI Session ID.
        "
::= { apexDepiSessionStatusBlade2Entry 1 }

apexDepiSessionStatusBlade2OutputQAMChannel OBJECT-TYPE
    SYNTAX Integer32
    MAX-ACCESS read-only
    STATUS obsolete
    DESCRIPTION
        "This object is obsolete.
         The QAM Channel number this session is mapped to.
        "
::= { apexDepiSessionStatusBlade2Entry 2 }

apexDepiSessionStatusBlade2Status OBJECT-TYPE
    SYNTAX INTEGER
        {
         terminated          (1),
         failed              (2),
         waiting             (3),
         established         (4)
        }
    MAX-ACCESS read-only
    STATUS obsolete
    DESCRIPTION
        "This object is obsolete.
         M-CMTS core to the EQAM control connection status
        "
::= { apexDepiSessionStatusBlade2Entry 3 }

apexDepiSessionStatusBlade2InDataPackets OBJECT-TYPE
    SYNTAX Unsigned32
    MAX-ACCESS read-only
    STATUS obsolete
    DESCRIPTION
        "This object is obsolete.
         Number of data packets received on this session.
        "
::= { apexDepiSessionStatusBlade2Entry 4 }

apexDepiSessionStatusBlade2InSequenceDiscards OBJECT-TYPE
    SYNTAX Unsigned32
    MAX-ACCESS read-only
    STATUS obsolete
    DESCRIPTION
        "This object is obsolete.
         Number of data packets received on this session that are discarded
         due to sequencing error.
        "
::= { apexDepiSessionStatusBlade2Entry 5 }

apexDepiSessionStatusBlade2InDataPacketDiscards OBJECT-TYPE
    SYNTAX Unsigned32
    MAX-ACCESS read-only
    STATUS obsolete
    DESCRIPTION
        "This object is obsolete.
         Number of data packets received on this session that are discarded
         for reasons other than sequencing errors.
        "
::= { apexDepiSessionStatusBlade2Entry 6 }

apexDepiSessionStatusBlade2SessionID OBJECT-TYPE
    SYNTAX Unsigned32
    MAX-ACCESS read-only
    STATUS obsolete
    DESCRIPTION
        "This object is obsolete.
         Local DEPI Session ID, used locally to bind the Session to a QAM Channel.
        "
::= { apexDepiSessionStatusBlade2Entry 7 }

apexDepiSessionStatusBlade2InputIf OBJECT-TYPE
    SYNTAX Integer32 (1..12)
    MAX-ACCESS read-only
    STATUS obsolete
    DESCRIPTION
        "This object is obsolete.
         Interface number.
        "
::= { apexDepiSessionStatusBlade2Entry 8 }

apexDepiSessionStatusBlade2DataRate OBJECT-TYPE
    SYNTAX Integer32
    MAX-ACCESS read-only
    STATUS obsolete
    DESCRIPTION
        "This object is obsolete.
         Data rate.
        "
::= { apexDepiSessionStatusBlade2Entry 9 }

apexDepiSessionStatusBlade2SourceIp OBJECT-TYPE
    SYNTAX IpAddress
    MAX-ACCESS read-only
    STATUS obsolete
    DESCRIPTION
        "This object is obsolete.
         Source IP Address.
        "
::= { apexDepiSessionStatusBlade2Entry 10 }


-- ------------------------------------------------------------------------------
--
-- apexDepiSessionStatusBlade2TotalSessions 
--

apexDepiSessionStatusBlade2TotalSessions  OBJECT-TYPE
    SYNTAX Unsigned32
    MAX-ACCESS read-only
    STATUS obsolete
    DESCRIPTION
        "This object is obsolete.
         Number of session established in this blade.
        "
::= { apexDepiSessionStatusBlade2 2 }


-- ------------------------------------------------------------------------------
--
-- apexDepiSessionBlade2StatusTable 
--

apexDepiSessionBlade2StatusTable OBJECT-TYPE
    SYNTAX SEQUENCE OF ApexDepiSessionBlade2StatusEntry
    MAX-ACCESS not-accessible
    STATUS current
    DESCRIPTION
        "Table of read-only status information pertaining to the DEPI Sessions."
::= { apexDepiSessionStatusBlade2 3 }

apexDepiSessionBlade2StatusEntry OBJECT-TYPE
    SYNTAX ApexDepiSessionBlade2StatusEntry
    MAX-ACCESS not-accessible
    STATUS current
    DESCRIPTION
        "DEPI Session Status Table Entry."
    INDEX { apexDepiSessionBlade2StatusOutputOtsNum, apexDepiSessionBlade2StatusIndex }
::= { apexDepiSessionBlade2StatusTable 1 }

ApexDepiSessionBlade2StatusEntry ::= SEQUENCE
    {
      apexDepiSessionBlade2StatusOutputOtsNum            Integer32,
      apexDepiSessionBlade2StatusIndex                   Integer32,
      apexDepiSessionBlade2StatusStatus                  INTEGER,
      apexDepiSessionBlade2StatusInDataPackets           Unsigned32,
      apexDepiSessionBlade2StatusInSequenceDiscards      Unsigned32,
      apexDepiSessionBlade2StatusInDataPacketDiscards    Unsigned32,
      apexDepiSessionBlade2StatusSessionID               Unsigned32,
      apexDepiSessionBlade2StatusInputIf                 Integer32,
      apexDepiSessionBlade2StatusDataRate                Integer32,
      apexDepiSessionBlade2StatusSourceIp                IpAddress,
      apexDepiSessionBlade2StatusActivationMode          INTEGER,
      apexDepiSessionBlade2StatusCCid                    Unsigned32,
      apexDepiSessionBlade2StatusSessionType             INTEGER,
      apexDepiSessionBlade2StatusSyncRequired            INTEGER,
      apexDepiSessionBlade2StatusRemoteSessionId         Unsigned32,
      apexDepiSessionBlade2StatusInputTsIndex            Integer32
    }

apexDepiSessionBlade2StatusOutputOtsNum OBJECT-TYPE
    SYNTAX Integer32 (1..256)
    MAX-ACCESS read-only
    STATUS current
    DESCRIPTION
        "The QAM Channel number this session is mapped to."
::= { apexDepiSessionBlade2StatusEntry 1 }

apexDepiSessionBlade2StatusIndex OBJECT-TYPE
    SYNTAX Integer32 (1..5)
    MAX-ACCESS read-only
    STATUS current
    DESCRIPTION
        "Indexes the position of the session entry inside this OTS."
::= { apexDepiSessionBlade2StatusEntry 2 }

apexDepiSessionBlade2StatusStatus OBJECT-TYPE
    SYNTAX INTEGER
        {
         idle        (1),
         down        (2),
         settingup   (3),
         established (4)
        }
    MAX-ACCESS read-only
    STATUS current
    DESCRIPTION
        "M-CMTS core to the EQAM control connection status."
::= { apexDepiSessionBlade2StatusEntry 3 }

apexDepiSessionBlade2StatusInDataPackets OBJECT-TYPE
    SYNTAX Unsigned32
    MAX-ACCESS read-only
    STATUS current
    DESCRIPTION
        "Number of data packets received on this session."
::= { apexDepiSessionBlade2StatusEntry 4 }

apexDepiSessionBlade2StatusInSequenceDiscards OBJECT-TYPE
    SYNTAX Unsigned32
    MAX-ACCESS read-only
    STATUS current
    DESCRIPTION
        "Number of data packets received on this session that are discarded
         due to sequencing error."
::= { apexDepiSessionBlade2StatusEntry 5 }

apexDepiSessionBlade2StatusInDataPacketDiscards OBJECT-TYPE
    SYNTAX Unsigned32
    MAX-ACCESS read-only
    STATUS current
    DESCRIPTION
        "Number of data packets received on this session that are discarded
         for reasons other than sequencing errors."
::= { apexDepiSessionBlade2StatusEntry 6 }

apexDepiSessionBlade2StatusSessionID OBJECT-TYPE
    SYNTAX Unsigned32
    MAX-ACCESS read-only
    STATUS current
    DESCRIPTION
        "Local DEPI Session ID, used locally to bind the Session to a QAM Channel."
::= { apexDepiSessionBlade2StatusEntry 7 }

apexDepiSessionBlade2StatusInputIf OBJECT-TYPE
    SYNTAX Integer32 (1..12)
    MAX-ACCESS read-only
    STATUS current
    DESCRIPTION
        "Interface number.
        "
::= { apexDepiSessionBlade2StatusEntry 8 }

apexDepiSessionBlade2StatusDataRate OBJECT-TYPE
    SYNTAX Integer32
    MAX-ACCESS read-only
    STATUS current
    DESCRIPTION
        "Data rate.
        "
::= { apexDepiSessionBlade2StatusEntry 9 }

apexDepiSessionBlade2StatusSourceIp OBJECT-TYPE
    SYNTAX IpAddress
    MAX-ACCESS read-only
    STATUS current
    DESCRIPTION
        "Source IP Address.
        "
::= { apexDepiSessionBlade2StatusEntry 10 }

apexDepiSessionBlade2StatusActivationMode OBJECT-TYPE
    SYNTAX INTEGER
        {
         unknown      (0),
         static       (1),
         controlplane (2)
        }
    MAX-ACCESS read-only
    STATUS current
    DESCRIPTION
        "Activation mode of the session.
        "
::= { apexDepiSessionBlade2StatusEntry 11 }
   
apexDepiSessionBlade2StatusCCid OBJECT-TYPE
    SYNTAX          Unsigned32
    MAX-ACCESS read-only
    STATUS current
    DESCRIPTION
        "Control connection id if applicable.
        "
::= { apexDepiSessionBlade2StatusEntry 12 }

apexDepiSessionBlade2StatusSessionType OBJECT-TYPE
    SYNTAX INTEGER
        {
         unknown   (0),
         primary   (1),
         secondary (2)
        }
    MAX-ACCESS read-only
    STATUS current
    DESCRIPTION
        "Primary/secondary.
        "
::= { apexDepiSessionBlade2StatusEntry 13 }

apexDepiSessionBlade2StatusSyncRequired OBJECT-TYPE
    SYNTAX INTEGER
        {
         unknown (0),
         yes     (1),
         no      (2)
        }
    MAX-ACCESS read-only
    STATUS current
    DESCRIPTION
        "Sync correction required.
        "
::= { apexDepiSessionBlade2StatusEntry 14 }

apexDepiSessionBlade2StatusRemoteSessionId OBJECT-TYPE
    SYNTAX Unsigned32
    MAX-ACCESS read-only
    STATUS current
    DESCRIPTION
        "Remote DEPI Session ID, used by the Remote End to identify the DEPI
         Session."
::= { apexDepiSessionBlade2StatusEntry 15 }

apexDepiSessionBlade2StatusInputTsIndex OBJECT-TYPE
    SYNTAX Integer32
    MAX-ACCESS read-only
    STATUS current
    DESCRIPTION
        "The index into the apexGbeStatusInputTsStatTable."
::= { apexDepiSessionBlade2StatusEntry 16 }


-- ------------------------------------------------------------------------------
--
-- apexDepiSessionStatusBlade3
--
-- apexDepiSessionStatusBlade3Table
--

apexDepiSessionStatusBlade3Table OBJECT-TYPE
    SYNTAX SEQUENCE OF ApexDepiSessionStatusBlade3Entry
    MAX-ACCESS not-accessible
    STATUS obsolete
    DESCRIPTION
        "This object is obsolete.
         Table of read-only status information pertaining to the DEPI Sessions.
        "
::= { apexDepiSessionStatusBlade3 1 }

apexDepiSessionStatusBlade3Entry OBJECT-TYPE
    SYNTAX ApexDepiSessionStatusBlade3Entry
    MAX-ACCESS not-accessible
    STATUS obsolete
    DESCRIPTION
        "This object is obsolete.
         DEPI Session Status Table Entry.
        "
    INDEX { apexDepiSessionStatusBlade3Index}
::= { apexDepiSessionStatusBlade3Table 1 }

ApexDepiSessionStatusBlade3Entry ::= SEQUENCE
    {
      apexDepiSessionStatusBlade3Index                   Integer32,
      apexDepiSessionStatusBlade3OutputQAMChannel        Integer32,
      apexDepiSessionStatusBlade3Status                  INTEGER,
      apexDepiSessionStatusBlade3InDataPackets           Unsigned32,
      apexDepiSessionStatusBlade3InSequenceDiscards      Unsigned32,
      apexDepiSessionStatusBlade3InDataPacketDiscards    Unsigned32,
      apexDepiSessionStatusBlade3SessionID               Unsigned32,
      apexDepiSessionStatusBlade3InputIf                 Integer32,
      apexDepiSessionStatusBlade3DataRate                Integer32,
      apexDepiSessionStatusBlade3SourceIp                IpAddress
    }

apexDepiSessionStatusBlade3Index OBJECT-TYPE
    SYNTAX Integer32
    MAX-ACCESS not-accessible
    STATUS obsolete
    DESCRIPTION
        "This object is obsolete.
         DEPI Session ID.
        "
::= { apexDepiSessionStatusBlade3Entry 1 }

apexDepiSessionStatusBlade3OutputQAMChannel OBJECT-TYPE
    SYNTAX Integer32
    MAX-ACCESS read-only
    STATUS obsolete
    DESCRIPTION
        "This object is obsolete.
         The QAM Channel number this session is mapped to.
        "
::= { apexDepiSessionStatusBlade3Entry 2 }

apexDepiSessionStatusBlade3Status OBJECT-TYPE
    SYNTAX INTEGER
        {
         terminated          (1),
         failed              (2),
         waiting             (3),
         established         (4)
        }
    MAX-ACCESS read-only
    STATUS obsolete
    DESCRIPTION
        "This object is obsolete.
         M-CMTS core to the EQAM control connection status
        "
::= { apexDepiSessionStatusBlade3Entry 3 }

apexDepiSessionStatusBlade3InDataPackets OBJECT-TYPE
    SYNTAX Unsigned32
    MAX-ACCESS read-only
    STATUS obsolete
    DESCRIPTION
        "This object is obsolete.
         Number of data packets received on this session.
        "
::= { apexDepiSessionStatusBlade3Entry 4 }

apexDepiSessionStatusBlade3InSequenceDiscards OBJECT-TYPE
    SYNTAX Unsigned32
    MAX-ACCESS read-only
    STATUS obsolete
    DESCRIPTION
        "This object is obsolete.
         Number of data packets received on this session that are discarded
         due to sequencing error.
        "
::= { apexDepiSessionStatusBlade3Entry 5 }

apexDepiSessionStatusBlade3InDataPacketDiscards OBJECT-TYPE
    SYNTAX Unsigned32
    MAX-ACCESS read-only
    STATUS obsolete
    DESCRIPTION
        "This object is obsolete.
         Number of data packets received on this session that are discarded
         for reasons other than sequencing errors.
        "
::= { apexDepiSessionStatusBlade3Entry 6 }

apexDepiSessionStatusBlade3SessionID OBJECT-TYPE
    SYNTAX Unsigned32
    MAX-ACCESS read-only
    STATUS obsolete
    DESCRIPTION
        "This object is obsolete.
         Local DEPI Session ID, used locally to bind the Session to a QAM Channel.
        "
::= { apexDepiSessionStatusBlade3Entry 7 }

apexDepiSessionStatusBlade3InputIf OBJECT-TYPE
    SYNTAX Integer32 (1..12)
    MAX-ACCESS read-only
    STATUS obsolete
    DESCRIPTION
        "This object is obsolete.
         Interface number.
        "
::= { apexDepiSessionStatusBlade3Entry 8 }

apexDepiSessionStatusBlade3DataRate OBJECT-TYPE
    SYNTAX Integer32
    MAX-ACCESS read-only
    STATUS obsolete
    DESCRIPTION
        "This object is obsolete.
         Data rate.
        "
::= { apexDepiSessionStatusBlade3Entry 9 }

apexDepiSessionStatusBlade3SourceIp OBJECT-TYPE
    SYNTAX IpAddress
    MAX-ACCESS read-only
    STATUS obsolete
    DESCRIPTION
        "This object is obsolete.
         Source IP Address.
        "
::= { apexDepiSessionStatusBlade3Entry 10 }


-- ------------------------------------------------------------------------------
--
-- apexDepiSessionStatusBlade3TotalSessions 
--

apexDepiSessionStatusBlade3TotalSessions  OBJECT-TYPE
    SYNTAX Unsigned32
    MAX-ACCESS read-only
    STATUS obsolete
    DESCRIPTION
        "This object is obsolete.
         Number of session established in this blade.
        "
::= { apexDepiSessionStatusBlade3 2 }


-- ------------------------------------------------------------------------------
--
-- apexDepiSessionBlade3StatusTable 
--

apexDepiSessionBlade3StatusTable OBJECT-TYPE
    SYNTAX SEQUENCE OF ApexDepiSessionBlade3StatusEntry
    MAX-ACCESS not-accessible
    STATUS current
    DESCRIPTION
        "Table of read-only status information pertaining to the DEPI Sessions."
::= { apexDepiSessionStatusBlade3 3 }

apexDepiSessionBlade3StatusEntry OBJECT-TYPE
    SYNTAX ApexDepiSessionBlade3StatusEntry
    MAX-ACCESS not-accessible
    STATUS current
    DESCRIPTION
        "DEPI Session Status Table Entry."
    INDEX { apexDepiSessionBlade3StatusOutputOtsNum, apexDepiSessionBlade3StatusIndex }
::= { apexDepiSessionBlade3StatusTable 1 }

ApexDepiSessionBlade3StatusEntry ::= SEQUENCE
    {
      apexDepiSessionBlade3StatusOutputOtsNum            Integer32,
      apexDepiSessionBlade3StatusIndex                   Integer32,
      apexDepiSessionBlade3StatusStatus                  INTEGER,
      apexDepiSessionBlade3StatusInDataPackets           Unsigned32,
      apexDepiSessionBlade3StatusInSequenceDiscards      Unsigned32,
      apexDepiSessionBlade3StatusInDataPacketDiscards    Unsigned32,
      apexDepiSessionBlade3StatusSessionID               Unsigned32,
      apexDepiSessionBlade3StatusInputIf                 Integer32,
      apexDepiSessionBlade3StatusDataRate                Integer32,
      apexDepiSessionBlade3StatusSourceIp                IpAddress,
      apexDepiSessionBlade3StatusActivationMode          INTEGER,
      apexDepiSessionBlade3StatusCCid                    Unsigned32,
      apexDepiSessionBlade3StatusSessionType             INTEGER,
      apexDepiSessionBlade3StatusSyncRequired            INTEGER,
      apexDepiSessionBlade3StatusRemoteSessionId         Unsigned32,
      apexDepiSessionBlade3StatusInputTsIndex            Integer32
    }

apexDepiSessionBlade3StatusOutputOtsNum OBJECT-TYPE
    SYNTAX Integer32 (1..256)
    MAX-ACCESS read-only
    STATUS current
    DESCRIPTION
        "The QAM Channel number this session is mapped to."
::= { apexDepiSessionBlade3StatusEntry 1 }

apexDepiSessionBlade3StatusIndex OBJECT-TYPE
    SYNTAX Integer32 (1..5)
    MAX-ACCESS read-only
    STATUS current
    DESCRIPTION
        "Indexes the position of the session entry inside this OTS."
::= { apexDepiSessionBlade3StatusEntry 2 }

apexDepiSessionBlade3StatusStatus OBJECT-TYPE
    SYNTAX INTEGER
        {
         idle        (1),
         down        (2),
         settingup   (3),
         established (4)
        }
    MAX-ACCESS read-only
    STATUS current
    DESCRIPTION
        "M-CMTS core to the EQAM control connection status."
::= { apexDepiSessionBlade3StatusEntry 3 }

apexDepiSessionBlade3StatusInDataPackets OBJECT-TYPE
    SYNTAX Unsigned32
    MAX-ACCESS read-only
    STATUS current
    DESCRIPTION
        "Number of data packets received on this session."
::= { apexDepiSessionBlade3StatusEntry 4 }

apexDepiSessionBlade3StatusInSequenceDiscards OBJECT-TYPE
    SYNTAX Unsigned32
    MAX-ACCESS read-only
    STATUS current
    DESCRIPTION
        "Number of data packets received on this session that are discarded
         due to sequencing error."
::= { apexDepiSessionBlade3StatusEntry 5 }

apexDepiSessionBlade3StatusInDataPacketDiscards OBJECT-TYPE
    SYNTAX Unsigned32
    MAX-ACCESS read-only
    STATUS current
    DESCRIPTION
        "Number of data packets received on this session that are discarded
         for reasons other than sequencing errors."
::= { apexDepiSessionBlade3StatusEntry 6 }

apexDepiSessionBlade3StatusSessionID OBJECT-TYPE
    SYNTAX Unsigned32
    MAX-ACCESS read-only
    STATUS current
    DESCRIPTION
        "Local DEPI Session ID, used locally to bind the Session to a QAM Channel."
::= { apexDepiSessionBlade3StatusEntry 7 }

apexDepiSessionBlade3StatusInputIf OBJECT-TYPE
    SYNTAX Integer32 (1..12)
    MAX-ACCESS read-only
    STATUS current
    DESCRIPTION
        "Interface number.
        "
::= { apexDepiSessionBlade3StatusEntry 8 }

apexDepiSessionBlade3StatusDataRate OBJECT-TYPE
    SYNTAX Integer32
    MAX-ACCESS read-only
    STATUS current
    DESCRIPTION
        "Data rate.
        "
::= { apexDepiSessionBlade3StatusEntry 9 }

apexDepiSessionBlade3StatusSourceIp OBJECT-TYPE
    SYNTAX IpAddress
    MAX-ACCESS read-only
    STATUS current
    DESCRIPTION
        "Source IP Address.
        "
::= { apexDepiSessionBlade3StatusEntry 10 }

apexDepiSessionBlade3StatusActivationMode OBJECT-TYPE
    SYNTAX INTEGER
        {
         unknown      (0),
         static       (1),
         controlplane (2)
        }
    MAX-ACCESS read-only
    STATUS current
    DESCRIPTION
        "Activation mode of the session.
        "
::= { apexDepiSessionBlade3StatusEntry 11 }
   
apexDepiSessionBlade3StatusCCid OBJECT-TYPE
    SYNTAX          Unsigned32
    MAX-ACCESS read-only
    STATUS current
    DESCRIPTION
        "Control connection id if applicable.
        "
::= { apexDepiSessionBlade3StatusEntry 12 }

apexDepiSessionBlade3StatusSessionType OBJECT-TYPE
    SYNTAX INTEGER
        {
         unknown   (0),
         primary   (1),
         secondary (2)
        }
    MAX-ACCESS read-only
    STATUS current
    DESCRIPTION
        "Primary/secondary.
        "
::= { apexDepiSessionBlade3StatusEntry 13 }

apexDepiSessionBlade3StatusSyncRequired OBJECT-TYPE
    SYNTAX INTEGER
        {
         unknown (0),
         yes     (1),
         no      (2)
        }
    MAX-ACCESS read-only
    STATUS current
    DESCRIPTION
        "Sync correction required.
        "
::= { apexDepiSessionBlade3StatusEntry 14 }

apexDepiSessionBlade3StatusRemoteSessionId OBJECT-TYPE
    SYNTAX Unsigned32
    MAX-ACCESS read-only
    STATUS current
    DESCRIPTION
        "Remote DEPI Session ID, used by the Remote End to identify the DEPI
         Session."
::= { apexDepiSessionBlade3StatusEntry 15 }

apexDepiSessionBlade3StatusInputTsIndex OBJECT-TYPE
    SYNTAX Integer32
    MAX-ACCESS read-only
    STATUS current
    DESCRIPTION
        "The index into the apexGbeStatusInputTsStatTable."
::= { apexDepiSessionBlade3StatusEntry 16 }


-- ------------------------------------------------------------------------------
--
-- apexDepiSessionStatusBlade4
--
-- apexDepiSessionStatusBlade4Table
--

apexDepiSessionStatusBlade4Table OBJECT-TYPE
    SYNTAX SEQUENCE OF ApexDepiSessionStatusBlade4Entry
    MAX-ACCESS not-accessible
    STATUS obsolete
    DESCRIPTION
        "This object is obsolete.
         Table of read-only status information pertaining to the DEPI Sessions.
        "
::= { apexDepiSessionStatusBlade4 1 }

apexDepiSessionStatusBlade4Entry OBJECT-TYPE
    SYNTAX ApexDepiSessionStatusBlade4Entry
    MAX-ACCESS not-accessible
    STATUS obsolete
    DESCRIPTION
        "This object is obsolete.
         DEPI Session Status Table Entry.
        "
    INDEX { apexDepiSessionStatusBlade4Index}
::= { apexDepiSessionStatusBlade4Table 1 }

ApexDepiSessionStatusBlade4Entry ::= SEQUENCE
    {
      apexDepiSessionStatusBlade4Index                   Integer32,
      apexDepiSessionStatusBlade4OutputQAMChannel        Integer32,
      apexDepiSessionStatusBlade4Status                  INTEGER,
      apexDepiSessionStatusBlade4InDataPackets           Unsigned32,
      apexDepiSessionStatusBlade4InSequenceDiscards      Unsigned32,
      apexDepiSessionStatusBlade4InDataPacketDiscards    Unsigned32,
      apexDepiSessionStatusBlade4SessionID               Unsigned32,
      apexDepiSessionStatusBlade4InputIf                 Integer32,
      apexDepiSessionStatusBlade4DataRate                Integer32,
      apexDepiSessionStatusBlade4SourceIp                IpAddress
    }

apexDepiSessionStatusBlade4Index OBJECT-TYPE
    SYNTAX Integer32
    MAX-ACCESS not-accessible
    STATUS obsolete
    DESCRIPTION
        "This object is obsolete.
         DEPI Session ID.
        "
::= { apexDepiSessionStatusBlade4Entry 1 }

apexDepiSessionStatusBlade4OutputQAMChannel OBJECT-TYPE
    SYNTAX Integer32
    MAX-ACCESS read-only
    STATUS obsolete
    DESCRIPTION
        "This object is obsolete.
         The QAM Channel number this session is mapped to.
        "
::= { apexDepiSessionStatusBlade4Entry 2 }

apexDepiSessionStatusBlade4Status OBJECT-TYPE
    SYNTAX INTEGER
        {
         terminated          (1),
         failed              (2),
         waiting             (3),
         established         (4)
        }
    MAX-ACCESS read-only
    STATUS obsolete
    DESCRIPTION
        "This object is obsolete.
         M-CMTS core to the EQAM control connection status.
        "
::= { apexDepiSessionStatusBlade4Entry 3 }

apexDepiSessionStatusBlade4InDataPackets OBJECT-TYPE
    SYNTAX Unsigned32
    MAX-ACCESS read-only
    STATUS obsolete
    DESCRIPTION
        "This object is obsolete.
         Number of data packets received on this session.
        "
::= { apexDepiSessionStatusBlade4Entry 4 }

apexDepiSessionStatusBlade4InSequenceDiscards OBJECT-TYPE
    SYNTAX Unsigned32
    MAX-ACCESS read-only
    STATUS obsolete
    DESCRIPTION
        "This object is obsolete.
         Number of data packets received on this session that are discarded
         due to sequencing error.
        "
::= { apexDepiSessionStatusBlade4Entry 5 }

apexDepiSessionStatusBlade4InDataPacketDiscards OBJECT-TYPE
    SYNTAX Unsigned32
    MAX-ACCESS read-only
    STATUS obsolete
    DESCRIPTION
        "This object is obsolete.
         Number of data packets received on this session that are discarded
         for reasons other than sequencing errors.
        "
::= { apexDepiSessionStatusBlade4Entry 6 }

apexDepiSessionStatusBlade4SessionID OBJECT-TYPE
    SYNTAX Unsigned32
    MAX-ACCESS read-only
    STATUS obsolete
    DESCRIPTION
        "This object is obsolete.
         Local DEPI Session ID, used locally to bind the Session to a QAM Channel.
        "
::= { apexDepiSessionStatusBlade4Entry 7 }

apexDepiSessionStatusBlade4InputIf OBJECT-TYPE
    SYNTAX Integer32 (1..12)
    MAX-ACCESS read-only
    STATUS obsolete
    DESCRIPTION
        "This object is obsolete.
         Interface number.
        "
::= { apexDepiSessionStatusBlade4Entry 8 }

apexDepiSessionStatusBlade4DataRate OBJECT-TYPE
    SYNTAX Integer32
    MAX-ACCESS read-only
    STATUS obsolete
    DESCRIPTION
        "This object is obsolete.
         Data rate.
        "
::= { apexDepiSessionStatusBlade4Entry 9 }

apexDepiSessionStatusBlade4SourceIp OBJECT-TYPE
    SYNTAX IpAddress
    MAX-ACCESS read-only
    STATUS obsolete
    DESCRIPTION
        "This object is obsolete.
         Source IP Address.
        "
::= { apexDepiSessionStatusBlade4Entry 10 }


-- ------------------------------------------------------------------------------
--
-- apexDepiSessionStatusBlade4TotalSessions
--

apexDepiSessionStatusBlade4TotalSessions  OBJECT-TYPE
    SYNTAX Unsigned32
    MAX-ACCESS read-only
    STATUS obsolete
    DESCRIPTION
        "This object is obsolete.
         Number of session established in this blade.
        "
::= { apexDepiSessionStatusBlade4 2 }


-- ------------------------------------------------------------------------------
--
-- apexDepiSessionBlade4StatusTable
--

apexDepiSessionBlade4StatusTable OBJECT-TYPE
    SYNTAX SEQUENCE OF ApexDepiSessionBlade4StatusEntry
    MAX-ACCESS not-accessible
    STATUS current
    DESCRIPTION
        "Table of read-only status information pertaining to the DEPI Sessions."
::= { apexDepiSessionStatusBlade4 3 }

apexDepiSessionBlade4StatusEntry OBJECT-TYPE
    SYNTAX ApexDepiSessionBlade4StatusEntry
    MAX-ACCESS not-accessible
    STATUS current
    DESCRIPTION
        "DEPI Session Status Table Entry."
    INDEX { apexDepiSessionBlade4StatusOutputOtsNum, apexDepiSessionBlade4StatusIndex }
::= { apexDepiSessionBlade4StatusTable 1 }

ApexDepiSessionBlade4StatusEntry ::= SEQUENCE
    {
      apexDepiSessionBlade4StatusOutputOtsNum            Integer32,
      apexDepiSessionBlade4StatusIndex                   Integer32,
      apexDepiSessionBlade4StatusStatus                  INTEGER,
      apexDepiSessionBlade4StatusInDataPackets           Unsigned32,
      apexDepiSessionBlade4StatusInSequenceDiscards      Unsigned32,
      apexDepiSessionBlade4StatusInDataPacketDiscards    Unsigned32,
      apexDepiSessionBlade4StatusSessionID               Unsigned32,
      apexDepiSessionBlade4StatusInputIf                 Integer32,
      apexDepiSessionBlade4StatusDataRate                Integer32,
      apexDepiSessionBlade4StatusSourceIp                IpAddress,
      apexDepiSessionBlade4StatusActivationMode          INTEGER,
      apexDepiSessionBlade4StatusCCid                    Unsigned32,
      apexDepiSessionBlade4StatusSessionType             INTEGER,
      apexDepiSessionBlade4StatusSyncRequired            INTEGER,
      apexDepiSessionBlade4StatusRemoteSessionId         Unsigned32,
      apexDepiSessionBlade4StatusInputTsIndex            Integer32
    }

apexDepiSessionBlade4StatusOutputOtsNum OBJECT-TYPE
    SYNTAX Integer32 (1..256)
    MAX-ACCESS read-only
    STATUS current
    DESCRIPTION
        "The QAM Channel number this session is mapped to."
::= { apexDepiSessionBlade4StatusEntry 1 }

apexDepiSessionBlade4StatusIndex OBJECT-TYPE
    SYNTAX Integer32 (1..5)
    MAX-ACCESS read-only
    STATUS current
    DESCRIPTION
        "Indexes the position of the session entry inside this OTS."
::= { apexDepiSessionBlade4StatusEntry 2 }

apexDepiSessionBlade4StatusStatus OBJECT-TYPE
    SYNTAX INTEGER
        {
         idle        (1),
         down        (2),
         settingup   (3),
         established (4)
        }
    MAX-ACCESS read-only
    STATUS current
    DESCRIPTION
        "M-CMTS core to the EQAM control connection status."
::= { apexDepiSessionBlade4StatusEntry 3 }

apexDepiSessionBlade4StatusInDataPackets OBJECT-TYPE
    SYNTAX Unsigned32
    MAX-ACCESS read-only
    STATUS current
    DESCRIPTION
        "Number of data packets received on this session."
::= { apexDepiSessionBlade4StatusEntry 4 }

apexDepiSessionBlade4StatusInSequenceDiscards OBJECT-TYPE
    SYNTAX Unsigned32
    MAX-ACCESS read-only
    STATUS current
    DESCRIPTION
        "Number of data packets received on this session that are discarded
         due to sequencing error."
::= { apexDepiSessionBlade4StatusEntry 5 }

apexDepiSessionBlade4StatusInDataPacketDiscards OBJECT-TYPE
    SYNTAX Unsigned32
    MAX-ACCESS read-only
    STATUS current
    DESCRIPTION
        "Number of data packets received on this session that are discarded
         for reasons other than sequencing errors."
::= { apexDepiSessionBlade4StatusEntry 6 }

apexDepiSessionBlade4StatusSessionID OBJECT-TYPE
    SYNTAX Unsigned32
    MAX-ACCESS read-only
    STATUS current
    DESCRIPTION
        "Local DEPI Session ID, used locally to bind the Session to a QAM Channel."
::= { apexDepiSessionBlade4StatusEntry 7 }

apexDepiSessionBlade4StatusInputIf OBJECT-TYPE
    SYNTAX Integer32 (1..12)
    MAX-ACCESS read-only
    STATUS current
    DESCRIPTION
        "Interface number.
        "
::= { apexDepiSessionBlade4StatusEntry 8 }

apexDepiSessionBlade4StatusDataRate OBJECT-TYPE
    SYNTAX Integer32
    MAX-ACCESS read-only
    STATUS current
    DESCRIPTION
        "Data rate.
        "
::= { apexDepiSessionBlade4StatusEntry 9 }

apexDepiSessionBlade4StatusSourceIp OBJECT-TYPE
    SYNTAX IpAddress
    MAX-ACCESS read-only
    STATUS current
    DESCRIPTION
        "Source IP Address.
        "
::= { apexDepiSessionBlade4StatusEntry 10 }

apexDepiSessionBlade4StatusActivationMode OBJECT-TYPE
    SYNTAX INTEGER
        {
         unknown      (0),
         static       (1),
         controlplane (2)
        }
    MAX-ACCESS read-only
    STATUS current
    DESCRIPTION
        "Activation mode of the session.
        "
::= { apexDepiSessionBlade4StatusEntry 11 }

apexDepiSessionBlade4StatusCCid OBJECT-TYPE
    SYNTAX          Unsigned32
    MAX-ACCESS read-only
    STATUS current
    DESCRIPTION
        "Control connection id if applicable.
        "
::= { apexDepiSessionBlade4StatusEntry 12 }

apexDepiSessionBlade4StatusSessionType OBJECT-TYPE
    SYNTAX INTEGER
        {
         unknown   (0),
         primary   (1),
         secondary (2)
        }
    MAX-ACCESS read-only
    STATUS current
    DESCRIPTION
        "Primary/secondary.
        "
::= { apexDepiSessionBlade4StatusEntry 13 }

apexDepiSessionBlade4StatusSyncRequired OBJECT-TYPE
    SYNTAX INTEGER
        {
         unknown (0),
         yes     (1),
         no      (2)
        }
    MAX-ACCESS read-only
    STATUS current
    DESCRIPTION
        "Sync correction required.
        "
::= { apexDepiSessionBlade4StatusEntry 14 }

apexDepiSessionBlade4StatusRemoteSessionId OBJECT-TYPE
    SYNTAX Unsigned32
    MAX-ACCESS read-only
    STATUS current
    DESCRIPTION
        "Remote DEPI Session ID, used by the Remote End to identify the DEPI
         Session."
::= { apexDepiSessionBlade4StatusEntry 15 }

apexDepiSessionBlade4StatusInputTsIndex OBJECT-TYPE
    SYNTAX Integer32
    MAX-ACCESS read-only
    STATUS current
    DESCRIPTION
        "The index into the apexGbeStatusInputTsStatTable."
::= { apexDepiSessionBlade4StatusEntry 16 }


-- ------------------------------------------------------------------------------
--
-- apexDepiSessionStatusBlade5
--
-- apexDepiSessionStatusBlade5Table
--

apexDepiSessionStatusBlade5Table OBJECT-TYPE
    SYNTAX SEQUENCE OF ApexDepiSessionStatusBlade5Entry
    MAX-ACCESS not-accessible
    STATUS obsolete
    DESCRIPTION
        "This object is obsolete.
         Table of read-only status information pertaining to the DEPI Sessions.
        "
::= { apexDepiSessionStatusBlade5 1 }

apexDepiSessionStatusBlade5Entry OBJECT-TYPE
    SYNTAX ApexDepiSessionStatusBlade5Entry
    MAX-ACCESS not-accessible
    STATUS obsolete
    DESCRIPTION
        "This object is obsolete.
         DEPI Session Status Table Entry.
        "
    INDEX { apexDepiSessionStatusBlade5Index}
::= { apexDepiSessionStatusBlade5Table 1 }

ApexDepiSessionStatusBlade5Entry ::= SEQUENCE
    {
      apexDepiSessionStatusBlade5Index                   Integer32,
      apexDepiSessionStatusBlade5OutputQAMChannel        Integer32,
      apexDepiSessionStatusBlade5Status                  INTEGER,
      apexDepiSessionStatusBlade5InDataPackets           Unsigned32,
      apexDepiSessionStatusBlade5InSequenceDiscards      Unsigned32,
      apexDepiSessionStatusBlade5InDataPacketDiscards    Unsigned32,
      apexDepiSessionStatusBlade5SessionID               Unsigned32,
      apexDepiSessionStatusBlade5InputIf                 Integer32,
      apexDepiSessionStatusBlade5DataRate                Integer32,
      apexDepiSessionStatusBlade5SourceIp                IpAddress
    }

apexDepiSessionStatusBlade5Index OBJECT-TYPE
    SYNTAX Integer32
    MAX-ACCESS not-accessible
    STATUS obsolete
    DESCRIPTION
        "This object is obsolete.
         DEPI Session ID.
        "
::= { apexDepiSessionStatusBlade5Entry 1 }

apexDepiSessionStatusBlade5OutputQAMChannel OBJECT-TYPE
    SYNTAX Integer32
    MAX-ACCESS read-only
    STATUS obsolete
    DESCRIPTION
        "This object is obsolete.
         The QAM Channel number this session is mapped to.
        "
::= { apexDepiSessionStatusBlade5Entry 2 }

apexDepiSessionStatusBlade5Status OBJECT-TYPE
    SYNTAX INTEGER
        {
         terminated          (1),
         failed              (2),
         waiting             (3),
         established         (4)
        }
    MAX-ACCESS read-only
    STATUS obsolete
    DESCRIPTION
        "This object is obsolete.
         M-CMTS core to the EQAM control connection status
        "
::= { apexDepiSessionStatusBlade5Entry 3 }

apexDepiSessionStatusBlade5InDataPackets OBJECT-TYPE
    SYNTAX Unsigned32
    MAX-ACCESS read-only
    STATUS obsolete
    DESCRIPTION
        "This object is obsolete.
         Number of data packets received on this session.
        "
::= { apexDepiSessionStatusBlade5Entry 4 }

apexDepiSessionStatusBlade5InSequenceDiscards OBJECT-TYPE
    SYNTAX Unsigned32
    MAX-ACCESS read-only
    STATUS obsolete
    DESCRIPTION
        "This object is obsolete.
         Number of data packets received on this session that are discarded
         due to sequencing error.
        "
::= { apexDepiSessionStatusBlade5Entry 5 }

apexDepiSessionStatusBlade5InDataPacketDiscards OBJECT-TYPE
    SYNTAX Unsigned32
    MAX-ACCESS read-only
    STATUS obsolete
    DESCRIPTION
        "This object is obsolete.
         Number of data packets received on this session that are discarded
         for reasons other than sequencing errors.
        "
::= { apexDepiSessionStatusBlade5Entry 6 }

apexDepiSessionStatusBlade5SessionID OBJECT-TYPE
    SYNTAX Unsigned32
    MAX-ACCESS read-only
    STATUS obsolete
    DESCRIPTION
        "This object is obsolete.
         Local DEPI Session ID, used locally to bind the Session to a QAM Channel.
        "
::= { apexDepiSessionStatusBlade5Entry 7 }

apexDepiSessionStatusBlade5InputIf OBJECT-TYPE
    SYNTAX Integer32 (1..12)
    MAX-ACCESS read-only
    STATUS obsolete
    DESCRIPTION
        "This object is obsolete.
         Interface number.
        "
::= { apexDepiSessionStatusBlade5Entry 8 }

apexDepiSessionStatusBlade5DataRate OBJECT-TYPE
    SYNTAX Integer32
    MAX-ACCESS read-only
    STATUS obsolete
    DESCRIPTION
        "This object is obsolete.
         Data rate.
        "
::= { apexDepiSessionStatusBlade5Entry 9 }

apexDepiSessionStatusBlade5SourceIp OBJECT-TYPE
    SYNTAX IpAddress
    MAX-ACCESS read-only
    STATUS obsolete
    DESCRIPTION
        "This object is obsolete.
         Source IP Address.
        "
::= { apexDepiSessionStatusBlade5Entry 10 }


-- ------------------------------------------------------------------------------
--
-- apexDepiSessionStatusBlade5TotalSessions
--

apexDepiSessionStatusBlade5TotalSessions  OBJECT-TYPE
    SYNTAX Unsigned32
    MAX-ACCESS read-only
    STATUS obsolete
    DESCRIPTION
        "This object is obsolete.
         Number of session established in this blade.
        "
::= { apexDepiSessionStatusBlade5 2 }


-- ------------------------------------------------------------------------------
--
-- apexDepiSessionBlade5StatusTable
--

apexDepiSessionBlade5StatusTable OBJECT-TYPE
    SYNTAX SEQUENCE OF ApexDepiSessionBlade5StatusEntry
    MAX-ACCESS not-accessible
    STATUS current
    DESCRIPTION
        "Table of read-only status information pertaining to the DEPI Sessions."
::= { apexDepiSessionStatusBlade5 3 }

apexDepiSessionBlade5StatusEntry OBJECT-TYPE
    SYNTAX ApexDepiSessionBlade5StatusEntry
    MAX-ACCESS not-accessible
    STATUS current
    DESCRIPTION
        "DEPI Session Status Table Entry."
    INDEX { apexDepiSessionBlade5StatusOutputOtsNum, apexDepiSessionBlade5StatusIndex }
::= { apexDepiSessionBlade5StatusTable 1 }

ApexDepiSessionBlade5StatusEntry ::= SEQUENCE
    {
      apexDepiSessionBlade5StatusOutputOtsNum            Integer32,
      apexDepiSessionBlade5StatusIndex                   Integer32,
      apexDepiSessionBlade5StatusStatus                  INTEGER,
      apexDepiSessionBlade5StatusInDataPackets           Unsigned32,
      apexDepiSessionBlade5StatusInSequenceDiscards      Unsigned32,
      apexDepiSessionBlade5StatusInDataPacketDiscards    Unsigned32,
      apexDepiSessionBlade5StatusSessionID               Unsigned32,
      apexDepiSessionBlade5StatusInputIf                 Integer32,
      apexDepiSessionBlade5StatusDataRate                Integer32,
      apexDepiSessionBlade5StatusSourceIp                IpAddress,
      apexDepiSessionBlade5StatusActivationMode          INTEGER,
      apexDepiSessionBlade5StatusCCid                    Unsigned32,
      apexDepiSessionBlade5StatusSessionType             INTEGER,
      apexDepiSessionBlade5StatusSyncRequired            INTEGER,
      apexDepiSessionBlade5StatusRemoteSessionId         Unsigned32,
      apexDepiSessionBlade5StatusInputTsIndex            Integer32
    }

apexDepiSessionBlade5StatusOutputOtsNum OBJECT-TYPE
    SYNTAX Integer32 (1..256)
    MAX-ACCESS read-only
    STATUS current
    DESCRIPTION
        "The QAM Channel number this session is mapped to."
::= { apexDepiSessionBlade5StatusEntry 1 }

apexDepiSessionBlade5StatusIndex OBJECT-TYPE
    SYNTAX Integer32 (1..5)
    MAX-ACCESS read-only
    STATUS current
    DESCRIPTION
        "Indexes the position of the session entry inside this OTS."
::= { apexDepiSessionBlade5StatusEntry 2 }

apexDepiSessionBlade5StatusStatus OBJECT-TYPE
    SYNTAX INTEGER
        {
         idle        (1),
         down        (2),
         settingup   (3),
         established (4)
        }
    MAX-ACCESS read-only
    STATUS current
    DESCRIPTION
        "M-CMTS core to the EQAM control connection status."
::= { apexDepiSessionBlade5StatusEntry 3 }

apexDepiSessionBlade5StatusInDataPackets OBJECT-TYPE
    SYNTAX Unsigned32
    MAX-ACCESS read-only
    STATUS current
    DESCRIPTION
        "Number of data packets received on this session."
::= { apexDepiSessionBlade5StatusEntry 4 }

apexDepiSessionBlade5StatusInSequenceDiscards OBJECT-TYPE
    SYNTAX Unsigned32
    MAX-ACCESS read-only
    STATUS current
    DESCRIPTION
        "Number of data packets received on this session that are discarded
         due to sequencing error."
::= { apexDepiSessionBlade5StatusEntry 5 }

apexDepiSessionBlade5StatusInDataPacketDiscards OBJECT-TYPE
    SYNTAX Unsigned32
    MAX-ACCESS read-only
    STATUS current
    DESCRIPTION
        "Number of data packets received on this session that are discarded
         for reasons other than sequencing errors."
::= { apexDepiSessionBlade5StatusEntry 6 }

apexDepiSessionBlade5StatusSessionID OBJECT-TYPE
    SYNTAX Unsigned32
    MAX-ACCESS read-only
    STATUS current
    DESCRIPTION
        "Local DEPI Session ID, used locally to bind the Session to a QAM Channel."
::= { apexDepiSessionBlade5StatusEntry 7 }

apexDepiSessionBlade5StatusInputIf OBJECT-TYPE
    SYNTAX Integer32 (1..12)
    MAX-ACCESS read-only
    STATUS current
    DESCRIPTION
        "Interface number.
        "
::= { apexDepiSessionBlade5StatusEntry 8 }

apexDepiSessionBlade5StatusDataRate OBJECT-TYPE
    SYNTAX Integer32
    MAX-ACCESS read-only
    STATUS current
    DESCRIPTION
        "Data rate.
        "
::= { apexDepiSessionBlade5StatusEntry 9 }

apexDepiSessionBlade5StatusSourceIp OBJECT-TYPE
    SYNTAX IpAddress
    MAX-ACCESS read-only
    STATUS current
    DESCRIPTION
        "Source IP Address.
        "
::= { apexDepiSessionBlade5StatusEntry 10 }

apexDepiSessionBlade5StatusActivationMode OBJECT-TYPE
    SYNTAX INTEGER
        {
         unknown      (0),
         static       (1),
         controlplane (2)
        }
    MAX-ACCESS read-only
    STATUS current
    DESCRIPTION
        "Activation mode of the session.
        "
::= { apexDepiSessionBlade5StatusEntry 11 }
   
apexDepiSessionBlade5StatusCCid OBJECT-TYPE
    SYNTAX          Unsigned32
    MAX-ACCESS read-only
    STATUS current
    DESCRIPTION
        "Control connection id if applicable.
        "
::= { apexDepiSessionBlade5StatusEntry 12 }

apexDepiSessionBlade5StatusSessionType OBJECT-TYPE
    SYNTAX INTEGER
        {
         unknown   (0),
         primary   (1),
         secondary (2)
        }
    MAX-ACCESS read-only
    STATUS current
    DESCRIPTION
        "Primary/secondary.
        "
::= { apexDepiSessionBlade5StatusEntry 13 }

apexDepiSessionBlade5StatusSyncRequired OBJECT-TYPE
    SYNTAX INTEGER
        {
         unknown (0),
         yes     (1),
         no      (2)
        }
    MAX-ACCESS read-only
    STATUS current
    DESCRIPTION
        "Sync correction required.
        "
::= { apexDepiSessionBlade5StatusEntry 14 }

apexDepiSessionBlade5StatusRemoteSessionId OBJECT-TYPE
    SYNTAX Unsigned32
    MAX-ACCESS read-only
    STATUS current
    DESCRIPTION
        "Remote DEPI Session ID, used by the Remote End to identify the DEPI
         Session."
::= { apexDepiSessionBlade5StatusEntry 15 }

apexDepiSessionBlade5StatusInputTsIndex OBJECT-TYPE
    SYNTAX Integer32
    MAX-ACCESS read-only
    STATUS current
    DESCRIPTION
        "The index into the apexGbeStatusInputTsStatTable."
::= { apexDepiSessionBlade5StatusEntry 16 }


-- ------------------------------------------------------------------------------
--
-- apexDepiSessionStatusBlade6
--
-- apexDepiSessionStatusBlade6Table
--

apexDepiSessionStatusBlade6Table OBJECT-TYPE
    SYNTAX SEQUENCE OF ApexDepiSessionStatusBlade6Entry
    MAX-ACCESS not-accessible
    STATUS obsolete
    DESCRIPTION
        "This object is obsolete.
         Table of read-only status information pertaining to the DEPI Sessions.
        "
::= { apexDepiSessionStatusBlade6 1 }

apexDepiSessionStatusBlade6Entry OBJECT-TYPE
    SYNTAX ApexDepiSessionStatusBlade6Entry
    MAX-ACCESS not-accessible
    STATUS obsolete
    DESCRIPTION
        "This object is obsolete.
         DEPI Session Status Table Entry.
        "
    INDEX { apexDepiSessionStatusBlade6Index}
::= { apexDepiSessionStatusBlade6Table 1 }

ApexDepiSessionStatusBlade6Entry ::= SEQUENCE
    {
      apexDepiSessionStatusBlade6Index                   Integer32,
      apexDepiSessionStatusBlade6OutputQAMChannel        Integer32,
      apexDepiSessionStatusBlade6Status                  INTEGER,
      apexDepiSessionStatusBlade6InDataPackets           Unsigned32,
      apexDepiSessionStatusBlade6InSequenceDiscards      Unsigned32,
      apexDepiSessionStatusBlade6InDataPacketDiscards    Unsigned32,
      apexDepiSessionStatusBlade6SessionID               Unsigned32,
      apexDepiSessionStatusBlade6InputIf                 Integer32,
      apexDepiSessionStatusBlade6DataRate                Integer32,
      apexDepiSessionStatusBlade6SourceIp                IpAddress
    }

apexDepiSessionStatusBlade6Index OBJECT-TYPE
    SYNTAX Integer32
    MAX-ACCESS not-accessible
    STATUS obsolete
    DESCRIPTION
        "This object is obsolete.
         DEPI Session ID.
        "
::= { apexDepiSessionStatusBlade6Entry 1 }

apexDepiSessionStatusBlade6OutputQAMChannel OBJECT-TYPE
    SYNTAX Integer32
    MAX-ACCESS read-only
    STATUS obsolete
    DESCRIPTION
        "This object is obsolete.
         The QAM Channel number this session is mapped to.
        "
::= { apexDepiSessionStatusBlade6Entry 2 }

apexDepiSessionStatusBlade6Status OBJECT-TYPE
    SYNTAX INTEGER
        {
         terminated          (1),
         failed              (2),
         waiting             (3),
         established         (4)
        }
    MAX-ACCESS read-only
    STATUS obsolete
    DESCRIPTION
        "This object is obsolete.
         M-CMTS core to the EQAM control connection status
        "
::= { apexDepiSessionStatusBlade6Entry 3 }

apexDepiSessionStatusBlade6InDataPackets OBJECT-TYPE
    SYNTAX Unsigned32
    MAX-ACCESS read-only
    STATUS obsolete
    DESCRIPTION
        "This object is obsolete.
         Number of data packets received on this session.
        "
::= { apexDepiSessionStatusBlade6Entry 4 }

apexDepiSessionStatusBlade6InSequenceDiscards OBJECT-TYPE
    SYNTAX Unsigned32
    MAX-ACCESS read-only
    STATUS obsolete
    DESCRIPTION
        "This object is obsolete.
         Number of data packets received on this session that are discarded
         due to sequencing error.
        "
::= { apexDepiSessionStatusBlade6Entry 5 }

apexDepiSessionStatusBlade6InDataPacketDiscards OBJECT-TYPE
    SYNTAX Unsigned32
    MAX-ACCESS read-only
    STATUS obsolete
    DESCRIPTION
        "This object is obsolete.
         Number of data packets received on this session that are discarded
         for reasons other than sequencing errors.
        "
::= { apexDepiSessionStatusBlade6Entry 6 }

apexDepiSessionStatusBlade6SessionID OBJECT-TYPE
    SYNTAX Unsigned32
    MAX-ACCESS read-only
    STATUS obsolete
    DESCRIPTION
        "This object is obsolete.
         Local DEPI Session ID, used locally to bind the Session to a QAM Channel.
        "
::= { apexDepiSessionStatusBlade6Entry 7 }

apexDepiSessionStatusBlade6InputIf OBJECT-TYPE
    SYNTAX Integer32 (1..12)
    MAX-ACCESS read-only
    STATUS obsolete
    DESCRIPTION
        "This object is obsolete.
         Interface number.
        "
::= { apexDepiSessionStatusBlade6Entry 8 }

apexDepiSessionStatusBlade6DataRate OBJECT-TYPE
    SYNTAX Integer32
    MAX-ACCESS read-only
    STATUS obsolete
    DESCRIPTION
        "This object is obsolete.
         Data rate.
        "
::= { apexDepiSessionStatusBlade6Entry 9 }

apexDepiSessionStatusBlade6SourceIp OBJECT-TYPE
    SYNTAX IpAddress
    MAX-ACCESS read-only
    STATUS obsolete
    DESCRIPTION
        "This object is obsolete.
         Source IP Address.
        "
::= { apexDepiSessionStatusBlade6Entry 10 }


-- ------------------------------------------------------------------------------
--
-- apexDepiSessionStatusBlade6TotalSessions
--

apexDepiSessionStatusBlade6TotalSessions  OBJECT-TYPE
    SYNTAX Unsigned32
    MAX-ACCESS read-only
    STATUS obsolete
    DESCRIPTION
        "This object is obsolete.
         Number of session established in this blade.
        "
::= { apexDepiSessionStatusBlade6 2 }


-- ------------------------------------------------------------------------------
--
-- apexDepiSessionBlade6StatusTable
--

apexDepiSessionBlade6StatusTable OBJECT-TYPE
    SYNTAX SEQUENCE OF ApexDepiSessionBlade6StatusEntry
    MAX-ACCESS not-accessible
    STATUS current
    DESCRIPTION
        "Table of read-only status information pertaining to the DEPI Sessions."
::= { apexDepiSessionStatusBlade6 3 }

apexDepiSessionBlade6StatusEntry OBJECT-TYPE
    SYNTAX ApexDepiSessionBlade6StatusEntry
    MAX-ACCESS not-accessible
    STATUS current
    DESCRIPTION
        "DEPI Session Status Table Entry."
    INDEX { apexDepiSessionBlade6StatusOutputOtsNum, apexDepiSessionBlade6StatusIndex }
::= { apexDepiSessionBlade6StatusTable 1 }

ApexDepiSessionBlade6StatusEntry ::= SEQUENCE
    {
      apexDepiSessionBlade6StatusOutputOtsNum            Integer32,
      apexDepiSessionBlade6StatusIndex                   Integer32,
      apexDepiSessionBlade6StatusStatus                  INTEGER,
      apexDepiSessionBlade6StatusInDataPackets           Unsigned32,
      apexDepiSessionBlade6StatusInSequenceDiscards      Unsigned32,
      apexDepiSessionBlade6StatusInDataPacketDiscards    Unsigned32,
      apexDepiSessionBlade6StatusSessionID               Unsigned32,
      apexDepiSessionBlade6StatusInputIf                 Integer32,
      apexDepiSessionBlade6StatusDataRate                Integer32,
      apexDepiSessionBlade6StatusSourceIp                IpAddress,
      apexDepiSessionBlade6StatusActivationMode          INTEGER,
      apexDepiSessionBlade6StatusCCid                    Unsigned32,
      apexDepiSessionBlade6StatusSessionType             INTEGER,
      apexDepiSessionBlade6StatusSyncRequired            INTEGER,
      apexDepiSessionBlade6StatusRemoteSessionId         Unsigned32,
      apexDepiSessionBlade6StatusInputTsIndex            Integer32
    }

apexDepiSessionBlade6StatusOutputOtsNum OBJECT-TYPE
    SYNTAX Integer32 (1..256)
    MAX-ACCESS read-only
    STATUS current
    DESCRIPTION
        "The QAM Channel number this session is mapped to."
::= { apexDepiSessionBlade6StatusEntry 1 }

apexDepiSessionBlade6StatusIndex OBJECT-TYPE
    SYNTAX Integer32 (1..5)
    MAX-ACCESS read-only
    STATUS current
    DESCRIPTION
        "Indexes the position of the session entry inside this OTS."
::= { apexDepiSessionBlade6StatusEntry 2 }

apexDepiSessionBlade6StatusStatus OBJECT-TYPE
    SYNTAX INTEGER
        {
         idle        (1),
         down        (2),
         settingup   (3),
         established (4)
        }
    MAX-ACCESS read-only
    STATUS current
    DESCRIPTION
        "M-CMTS core to the EQAM control connection status."
::= { apexDepiSessionBlade6StatusEntry 3 }

apexDepiSessionBlade6StatusInDataPackets OBJECT-TYPE
    SYNTAX Unsigned32
    MAX-ACCESS read-only
    STATUS current
    DESCRIPTION
        "Number of data packets received on this session."
::= { apexDepiSessionBlade6StatusEntry 4 }

apexDepiSessionBlade6StatusInSequenceDiscards OBJECT-TYPE
    SYNTAX Unsigned32
    MAX-ACCESS read-only
    STATUS current
    DESCRIPTION
        "Number of data packets received on this session that are discarded
         due to sequencing error."
::= { apexDepiSessionBlade6StatusEntry 5 }

apexDepiSessionBlade6StatusInDataPacketDiscards OBJECT-TYPE
    SYNTAX Unsigned32
    MAX-ACCESS read-only
    STATUS current
    DESCRIPTION
        "Number of data packets received on this session that are discarded
         for reasons other than sequencing errors."
::= { apexDepiSessionBlade6StatusEntry 6 }

apexDepiSessionBlade6StatusSessionID OBJECT-TYPE
    SYNTAX Unsigned32
    MAX-ACCESS read-only
    STATUS current
    DESCRIPTION
        "Local DEPI Session ID, used locally to bind the Session to a QAM Channel."
::= { apexDepiSessionBlade6StatusEntry 7 }

apexDepiSessionBlade6StatusInputIf OBJECT-TYPE
    SYNTAX Integer32 (1..12)
    MAX-ACCESS read-only
    STATUS current
    DESCRIPTION
        "Interface number.
        "
::= { apexDepiSessionBlade6StatusEntry 8 }

apexDepiSessionBlade6StatusDataRate OBJECT-TYPE
    SYNTAX Integer32
    MAX-ACCESS read-only
    STATUS current
    DESCRIPTION
        "Data rate.
        "
::= { apexDepiSessionBlade6StatusEntry 9 }

apexDepiSessionBlade6StatusSourceIp OBJECT-TYPE
    SYNTAX IpAddress
    MAX-ACCESS read-only
    STATUS current
    DESCRIPTION
        "Source IP Address.
        "
::= { apexDepiSessionBlade6StatusEntry 10 }

apexDepiSessionBlade6StatusActivationMode OBJECT-TYPE
    SYNTAX INTEGER
        {
         unknown      (0),
         static       (1),
         controlplane (2)
        }
    MAX-ACCESS read-only
    STATUS current
    DESCRIPTION
        "Activation mode of the session.
        "
::= { apexDepiSessionBlade6StatusEntry 11 }
   
apexDepiSessionBlade6StatusCCid OBJECT-TYPE
    SYNTAX          Unsigned32
    MAX-ACCESS read-only
    STATUS current
    DESCRIPTION
        "Control connection id if applicable.
        "
::= { apexDepiSessionBlade6StatusEntry 12 }

apexDepiSessionBlade6StatusSessionType OBJECT-TYPE
    SYNTAX INTEGER
        {
         unknown   (0),
         primary   (1),
         secondary (2)
        }
    MAX-ACCESS read-only
    STATUS current
    DESCRIPTION
        "Primary/secondary.
        "
::= { apexDepiSessionBlade6StatusEntry 13 }

apexDepiSessionBlade6StatusSyncRequired OBJECT-TYPE
    SYNTAX INTEGER
        {
         unknown (0),
         yes     (1),
         no      (2)
        }
    MAX-ACCESS read-only
    STATUS current
    DESCRIPTION
        "Sync correction required.
        "
::= { apexDepiSessionBlade6StatusEntry 14 }

apexDepiSessionBlade6StatusRemoteSessionId OBJECT-TYPE
    SYNTAX Unsigned32
    MAX-ACCESS read-only
    STATUS current
    DESCRIPTION
        "Remote DEPI Session ID, used by the Remote End to identify the DEPI
         Session."
::= { apexDepiSessionBlade6StatusEntry 15 }

apexDepiSessionBlade6StatusInputTsIndex OBJECT-TYPE
    SYNTAX Integer32
    MAX-ACCESS read-only
    STATUS current
    DESCRIPTION
        "The index into the apexGbeStatusInputTsStatTable."
::= { apexDepiSessionBlade6StatusEntry 16 }


-- ------------------------------------------------------------------------------
--
-- apexDepiSessionStatusBlade7
--
-- apexDepiSessionStatusBlade7Table
--

apexDepiSessionStatusBlade7Table OBJECT-TYPE
    SYNTAX SEQUENCE OF ApexDepiSessionStatusBlade7Entry
    MAX-ACCESS not-accessible
    STATUS obsolete
    DESCRIPTION
        "This object is obsolete.
         Table of read-only status information pertaining to the DEPI Sessions.
        "
::= { apexDepiSessionStatusBlade7 1 }

apexDepiSessionStatusBlade7Entry OBJECT-TYPE
    SYNTAX ApexDepiSessionStatusBlade7Entry
    MAX-ACCESS not-accessible
    STATUS obsolete
    DESCRIPTION
        "This object is obsolete.
         DEPI Session Status Table Entry.
        "
    INDEX { apexDepiSessionStatusBlade7Index}
::= { apexDepiSessionStatusBlade7Table 1 }

ApexDepiSessionStatusBlade7Entry ::= SEQUENCE
    {
      apexDepiSessionStatusBlade7Index                   Integer32,
      apexDepiSessionStatusBlade7OutputQAMChannel        Integer32,
      apexDepiSessionStatusBlade7Status                  INTEGER,
      apexDepiSessionStatusBlade7InDataPackets           Unsigned32,
      apexDepiSessionStatusBlade7InSequenceDiscards      Unsigned32,
      apexDepiSessionStatusBlade7InDataPacketDiscards    Unsigned32,
      apexDepiSessionStatusBlade7SessionID               Unsigned32,
      apexDepiSessionStatusBlade7InputIf                 Integer32,
      apexDepiSessionStatusBlade7DataRate                Integer32,
      apexDepiSessionStatusBlade7SourceIp                IpAddress
    }

apexDepiSessionStatusBlade7Index OBJECT-TYPE
    SYNTAX Integer32
    MAX-ACCESS not-accessible
    STATUS obsolete
    DESCRIPTION
        "This object is obsolete.
         DEPI Session ID.
        "
::= { apexDepiSessionStatusBlade7Entry 1 }

apexDepiSessionStatusBlade7OutputQAMChannel OBJECT-TYPE
    SYNTAX Integer32
    MAX-ACCESS read-only
    STATUS obsolete
    DESCRIPTION
        "This object is obsolete.
         The QAM Channel number this session is mapped to.
        "
::= { apexDepiSessionStatusBlade7Entry 2 }

apexDepiSessionStatusBlade7Status OBJECT-TYPE
    SYNTAX INTEGER
        {
         terminated          (1),
         failed              (2),
         waiting             (3),
         established         (4)
        }
    MAX-ACCESS read-only
    STATUS obsolete
    DESCRIPTION
        "This object is obsolete.
         M-CMTS core to the EQAM control connection status
        "
::= { apexDepiSessionStatusBlade7Entry 3 }

apexDepiSessionStatusBlade7InDataPackets OBJECT-TYPE
    SYNTAX Unsigned32
    MAX-ACCESS read-only
    STATUS obsolete
    DESCRIPTION
        "This object is obsolete.
         Number of data packets received on this session.
        "
::= { apexDepiSessionStatusBlade7Entry 4 }

apexDepiSessionStatusBlade7InSequenceDiscards OBJECT-TYPE
    SYNTAX Unsigned32
    MAX-ACCESS read-only
    STATUS obsolete
    DESCRIPTION
        "This object is obsolete.
         Number of data packets received on this session that are discarded
         due to sequencing error.
        "
::= { apexDepiSessionStatusBlade7Entry 5 }

apexDepiSessionStatusBlade7InDataPacketDiscards OBJECT-TYPE
    SYNTAX Unsigned32
    MAX-ACCESS read-only
    STATUS obsolete
    DESCRIPTION
        "This object is obsolete.
         Number of data packets received on this session that are discarded
         for reasons other than sequencing errors.
        "
::= { apexDepiSessionStatusBlade7Entry 6 }

apexDepiSessionStatusBlade7SessionID OBJECT-TYPE
    SYNTAX Unsigned32
    MAX-ACCESS read-only
    STATUS obsolete
    DESCRIPTION
        "This object is obsolete.
         Local DEPI Session ID, used locally to bind the Session to a QAM Channel.
        "
::= { apexDepiSessionStatusBlade7Entry 7 }

apexDepiSessionStatusBlade7InputIf OBJECT-TYPE
    SYNTAX Integer32 (1..12)
    MAX-ACCESS read-only
    STATUS obsolete
    DESCRIPTION
        "This object is obsolete.
         Interface number.
        "
::= { apexDepiSessionStatusBlade7Entry 8 }

apexDepiSessionStatusBlade7DataRate OBJECT-TYPE
    SYNTAX Integer32
    MAX-ACCESS read-only
    STATUS obsolete
    DESCRIPTION
        "This object is obsolete.
         Data rate.
        "
::= { apexDepiSessionStatusBlade7Entry 9 }

apexDepiSessionStatusBlade7SourceIp OBJECT-TYPE
    SYNTAX IpAddress
    MAX-ACCESS read-only
    STATUS obsolete
    DESCRIPTION
        "This object is obsolete.
         Source IP Address.
        "
::= { apexDepiSessionStatusBlade7Entry 10 }


-- ------------------------------------------------------------------------------
--
-- apexDepiSessionStatusBlade7TotalSessions
--

apexDepiSessionStatusBlade7TotalSessions  OBJECT-TYPE
    SYNTAX Unsigned32
    MAX-ACCESS read-only
    STATUS obsolete
    DESCRIPTION
        "This object is obsolete.
         Number of session established in this blade.
        "
::= { apexDepiSessionStatusBlade7 2 }


-- ------------------------------------------------------------------------------
--
-- apexDepiSessionBlade7StatusTable
--

apexDepiSessionBlade7StatusTable OBJECT-TYPE
    SYNTAX SEQUENCE OF ApexDepiSessionBlade7StatusEntry
    MAX-ACCESS not-accessible
    STATUS current
    DESCRIPTION
        "Table of read-only status information pertaining to the DEPI Sessions."
::= { apexDepiSessionStatusBlade7 3 }

apexDepiSessionBlade7StatusEntry OBJECT-TYPE
    SYNTAX ApexDepiSessionBlade7StatusEntry
    MAX-ACCESS not-accessible
    STATUS current
    DESCRIPTION
        "DEPI Session Status Table Entry."
    INDEX { apexDepiSessionBlade7StatusOutputOtsNum, apexDepiSessionBlade7StatusIndex }
::= { apexDepiSessionBlade7StatusTable 1 }

ApexDepiSessionBlade7StatusEntry ::= SEQUENCE
    {
      apexDepiSessionBlade7StatusOutputOtsNum            Integer32,
      apexDepiSessionBlade7StatusIndex                   Integer32,
      apexDepiSessionBlade7StatusStatus                  INTEGER,
      apexDepiSessionBlade7StatusInDataPackets           Unsigned32,
      apexDepiSessionBlade7StatusInSequenceDiscards      Unsigned32,
      apexDepiSessionBlade7StatusInDataPacketDiscards    Unsigned32,
      apexDepiSessionBlade7StatusSessionID               Unsigned32,
      apexDepiSessionBlade7StatusInputIf                 Integer32,
      apexDepiSessionBlade7StatusDataRate                Integer32,
      apexDepiSessionBlade7StatusSourceIp                IpAddress,
      apexDepiSessionBlade7StatusActivationMode          INTEGER,
      apexDepiSessionBlade7StatusCCid                    Unsigned32,
      apexDepiSessionBlade7StatusSessionType             INTEGER,
      apexDepiSessionBlade7StatusSyncRequired            INTEGER,
      apexDepiSessionBlade7StatusRemoteSessionId         Unsigned32,
      apexDepiSessionBlade7StatusInputTsIndex            Integer32
    }

apexDepiSessionBlade7StatusOutputOtsNum OBJECT-TYPE
    SYNTAX Integer32 (1..256)
    MAX-ACCESS read-only
    STATUS current
    DESCRIPTION
        "The QAM Channel number this session is mapped to."
::= { apexDepiSessionBlade7StatusEntry 1 }

apexDepiSessionBlade7StatusIndex OBJECT-TYPE
    SYNTAX Integer32 (1..5)
    MAX-ACCESS read-only
    STATUS current
    DESCRIPTION
        "Indexes the position of the session entry inside this OTS."
::= { apexDepiSessionBlade7StatusEntry 2 }

apexDepiSessionBlade7StatusStatus OBJECT-TYPE
    SYNTAX INTEGER
        {
         idle        (1),
         down        (2),
         settingup   (3),
         established (4)
        }
    MAX-ACCESS read-only
    STATUS current
    DESCRIPTION
        "M-CMTS core to the EQAM control connection status."
::= { apexDepiSessionBlade7StatusEntry 3 }

apexDepiSessionBlade7StatusInDataPackets OBJECT-TYPE
    SYNTAX Unsigned32
    MAX-ACCESS read-only
    STATUS current
    DESCRIPTION
        "Number of data packets received on this session."
::= { apexDepiSessionBlade7StatusEntry 4 }

apexDepiSessionBlade7StatusInSequenceDiscards OBJECT-TYPE
    SYNTAX Unsigned32
    MAX-ACCESS read-only
    STATUS current
    DESCRIPTION
        "Number of data packets received on this session that are discarded
         due to sequencing error."
::= { apexDepiSessionBlade7StatusEntry 5 }

apexDepiSessionBlade7StatusInDataPacketDiscards OBJECT-TYPE
    SYNTAX Unsigned32
    MAX-ACCESS read-only
    STATUS current
    DESCRIPTION
        "Number of data packets received on this session that are discarded
         for reasons other than sequencing errors."
::= { apexDepiSessionBlade7StatusEntry 6 }

apexDepiSessionBlade7StatusSessionID OBJECT-TYPE
    SYNTAX Unsigned32
    MAX-ACCESS read-only
    STATUS current
    DESCRIPTION
        "Local DEPI Session ID, used locally to bind the Session to a QAM Channel."
::= { apexDepiSessionBlade7StatusEntry 7 }

apexDepiSessionBlade7StatusInputIf OBJECT-TYPE
    SYNTAX Integer32 (1..12)
    MAX-ACCESS read-only
    STATUS current
    DESCRIPTION
        "Interface number.
        "
::= { apexDepiSessionBlade7StatusEntry 8 }

apexDepiSessionBlade7StatusDataRate OBJECT-TYPE
    SYNTAX Integer32
    MAX-ACCESS read-only
    STATUS current
    DESCRIPTION
        "Data rate.
        "
::= { apexDepiSessionBlade7StatusEntry 9 }

apexDepiSessionBlade7StatusSourceIp OBJECT-TYPE
    SYNTAX IpAddress
    MAX-ACCESS read-only
    STATUS current
    DESCRIPTION
        "Source IP Address.
        "
::= { apexDepiSessionBlade7StatusEntry 10 }

apexDepiSessionBlade7StatusActivationMode OBJECT-TYPE
    SYNTAX INTEGER
        {
         unknown      (0),
         static       (1),
         controlplane (2)
        }
    MAX-ACCESS read-only
    STATUS current
    DESCRIPTION
        "Activation mode of the session.
        "
::= { apexDepiSessionBlade7StatusEntry 11 }
   
apexDepiSessionBlade7StatusCCid OBJECT-TYPE
    SYNTAX          Unsigned32
    MAX-ACCESS read-only
    STATUS current
    DESCRIPTION
        "Control connection id if applicable.
        "
::= { apexDepiSessionBlade7StatusEntry 12 }

apexDepiSessionBlade7StatusSessionType OBJECT-TYPE
    SYNTAX INTEGER
        {
         unknown   (0),
         primary   (1),
         secondary (2)
        }
    MAX-ACCESS read-only
    STATUS current
    DESCRIPTION
        "Primary/secondary.
        "
::= { apexDepiSessionBlade7StatusEntry 13 }

apexDepiSessionBlade7StatusSyncRequired OBJECT-TYPE
    SYNTAX INTEGER
        {
         unknown (0),
         yes     (1),
         no      (2)
        }
    MAX-ACCESS read-only
    STATUS current
    DESCRIPTION
        "Sync correction required.
        "
::= { apexDepiSessionBlade7StatusEntry 14 }

apexDepiSessionBlade7StatusRemoteSessionId OBJECT-TYPE
    SYNTAX Unsigned32
    MAX-ACCESS read-only
    STATUS current
    DESCRIPTION
        "Remote DEPI Session ID, used by the Remote End to identify the DEPI
         Session."
::= { apexDepiSessionBlade7StatusEntry 15 }

apexDepiSessionBlade7StatusInputTsIndex OBJECT-TYPE
    SYNTAX Integer32
    MAX-ACCESS read-only
    STATUS current
    DESCRIPTION
        "The index into the apexGbeStatusInputTsStatTable."
::= { apexDepiSessionBlade7StatusEntry 16 }


-- ------------------------------------------------------------------------------
--
-- apexDepiSessionStatusBlade8
--
-- apexDepiSessionStatusBlade8Table
--

apexDepiSessionStatusBlade8Table OBJECT-TYPE
    SYNTAX SEQUENCE OF ApexDepiSessionStatusBlade8Entry
    MAX-ACCESS not-accessible
    STATUS obsolete
    DESCRIPTION
        "This object is obsolete.
         Table of read-only status information pertaining to the DEPI Sessions.
        "
::= { apexDepiSessionStatusBlade8 1 }

apexDepiSessionStatusBlade8Entry OBJECT-TYPE
    SYNTAX ApexDepiSessionStatusBlade8Entry
    MAX-ACCESS not-accessible
    STATUS obsolete
    DESCRIPTION
        "This object is obsolete.
         DEPI Session Status Table Entry.
        "
    INDEX { apexDepiSessionStatusBlade8Index }
::= { apexDepiSessionStatusBlade8Table 1 }

ApexDepiSessionStatusBlade8Entry ::= SEQUENCE
    {
      apexDepiSessionStatusBlade8Index                   Integer32,
      apexDepiSessionStatusBlade8OutputQAMChannel        Integer32,
      apexDepiSessionStatusBlade8Status                  INTEGER,
      apexDepiSessionStatusBlade8InDataPackets           Unsigned32,
      apexDepiSessionStatusBlade8InSequenceDiscards      Unsigned32,
      apexDepiSessionStatusBlade8InDataPacketDiscards    Unsigned32,
      apexDepiSessionStatusBlade8SessionID               Unsigned32,
      apexDepiSessionStatusBlade8InputIf                 Integer32,
      apexDepiSessionStatusBlade8DataRate                Integer32,
      apexDepiSessionStatusBlade8SourceIp                IpAddress
    }

apexDepiSessionStatusBlade8Index OBJECT-TYPE
    SYNTAX Integer32
    MAX-ACCESS not-accessible
    STATUS obsolete
    DESCRIPTION
        "This object is obsolete.
         DEPI Session ID.
        "
::= { apexDepiSessionStatusBlade8Entry 1 }

apexDepiSessionStatusBlade8OutputQAMChannel OBJECT-TYPE
    SYNTAX Integer32
    MAX-ACCESS read-only
    STATUS obsolete
    DESCRIPTION
        "This object is obsolete.
         The QAM Channel number this session is mapped to.
        "
::= { apexDepiSessionStatusBlade8Entry 2 }

apexDepiSessionStatusBlade8Status OBJECT-TYPE
    SYNTAX INTEGER
        {
         terminated          (1),
         failed              (2),
         waiting             (3),
         established         (4)
        }
    MAX-ACCESS read-only
    STATUS obsolete
    DESCRIPTION
        "This object is obsolete.
         M-CMTS core to the EQAM control connection status
        "
::= { apexDepiSessionStatusBlade8Entry 3 }

apexDepiSessionStatusBlade8InDataPackets OBJECT-TYPE
    SYNTAX Unsigned32
    MAX-ACCESS read-only
    STATUS obsolete
    DESCRIPTION
        "This object is obsolete.
         Number of data packets received on this session.
        "
::= { apexDepiSessionStatusBlade8Entry 4 }

apexDepiSessionStatusBlade8InSequenceDiscards OBJECT-TYPE
    SYNTAX Unsigned32
    MAX-ACCESS read-only
    STATUS obsolete
    DESCRIPTION
        "This object is obsolete.
         Number of data packets received on this session that are discarded
         due to sequencing error.
        "
::= { apexDepiSessionStatusBlade8Entry 5 }

apexDepiSessionStatusBlade8InDataPacketDiscards OBJECT-TYPE
    SYNTAX Unsigned32
    MAX-ACCESS read-only
    STATUS obsolete
    DESCRIPTION
        "This object is obsolete.
         Number of data packets received on this session that are discarded
         for reasons other than sequencing errors.
        "
::= { apexDepiSessionStatusBlade8Entry 6 }

apexDepiSessionStatusBlade8SessionID OBJECT-TYPE
    SYNTAX Unsigned32
    MAX-ACCESS read-only
    STATUS obsolete
    DESCRIPTION
        "This object is obsolete.
         Local DEPI Session ID, used locally to bind the Session to a QAM Channel.
        "
::= { apexDepiSessionStatusBlade8Entry 7 }

apexDepiSessionStatusBlade8InputIf OBJECT-TYPE
    SYNTAX Integer32 (1..12)
    MAX-ACCESS read-only
    STATUS obsolete
    DESCRIPTION
        "This object is obsolete.
         Interface number.
        "
::= { apexDepiSessionStatusBlade8Entry 8 }

apexDepiSessionStatusBlade8DataRate OBJECT-TYPE
    SYNTAX Integer32
    MAX-ACCESS read-only
    STATUS obsolete
    DESCRIPTION
        "This object is obsolete.
         Data rate.
        "
::= { apexDepiSessionStatusBlade8Entry 9 }

apexDepiSessionStatusBlade8SourceIp OBJECT-TYPE
    SYNTAX IpAddress
    MAX-ACCESS read-only
    STATUS obsolete
    DESCRIPTION
        "This object is obsolete.
         Source IP Address.
        "
::= { apexDepiSessionStatusBlade8Entry 10 }


-- ------------------------------------------------------------------------------
--
-- apexDepiSessionStatusBlade8TotalSessions
--

apexDepiSessionStatusBlade8TotalSessions  OBJECT-TYPE
    SYNTAX Unsigned32
    MAX-ACCESS read-only
    STATUS obsolete
    DESCRIPTION
        "This object is obsolete.
         Number of session established in this blade.
        "
::= { apexDepiSessionStatusBlade8 2 }


-- ------------------------------------------------------------------------------
--
-- apexDepiSessionBlade8StatusTable
--

apexDepiSessionBlade8StatusTable OBJECT-TYPE
    SYNTAX SEQUENCE OF ApexDepiSessionBlade8StatusEntry
    MAX-ACCESS not-accessible
    STATUS current
    DESCRIPTION
        "Table of read-only status information pertaining to the DEPI Sessions."
::= { apexDepiSessionStatusBlade8 3 }

apexDepiSessionBlade8StatusEntry OBJECT-TYPE
    SYNTAX ApexDepiSessionBlade8StatusEntry
    MAX-ACCESS not-accessible
    STATUS current
    DESCRIPTION
        "DEPI Session Status Table Entry."
    INDEX { apexDepiSessionBlade8StatusOutputOtsNum, apexDepiSessionBlade8StatusIndex }
::= { apexDepiSessionBlade8StatusTable 1 }

ApexDepiSessionBlade8StatusEntry ::= SEQUENCE
    {
      apexDepiSessionBlade8StatusOutputOtsNum            Integer32,
      apexDepiSessionBlade8StatusIndex                   Integer32,
      apexDepiSessionBlade8StatusStatus                  INTEGER,
      apexDepiSessionBlade8StatusInDataPackets           Unsigned32,
      apexDepiSessionBlade8StatusInSequenceDiscards      Unsigned32,
      apexDepiSessionBlade8StatusInDataPacketDiscards    Unsigned32,
      apexDepiSessionBlade8StatusSessionID               Unsigned32,
      apexDepiSessionBlade8StatusInputIf                 Integer32,
      apexDepiSessionBlade8StatusDataRate                Integer32,
      apexDepiSessionBlade8StatusSourceIp                IpAddress,
      apexDepiSessionBlade8StatusActivationMode          INTEGER,
      apexDepiSessionBlade8StatusCCid                    Unsigned32,
      apexDepiSessionBlade8StatusSessionType             INTEGER,
      apexDepiSessionBlade8StatusSyncRequired            INTEGER,
      apexDepiSessionBlade8StatusRemoteSessionId         Unsigned32,
      apexDepiSessionBlade8StatusInputTsIndex            Integer32
    }

apexDepiSessionBlade8StatusOutputOtsNum OBJECT-TYPE
    SYNTAX Integer32 (1..256)
    MAX-ACCESS read-only
    STATUS current
    DESCRIPTION
        "The QAM Channel number this session is mapped to."
::= { apexDepiSessionBlade8StatusEntry 1 }

apexDepiSessionBlade8StatusIndex OBJECT-TYPE
    SYNTAX Integer32 (1..5)
    MAX-ACCESS read-only
    STATUS current
    DESCRIPTION
        "Indexes the position of the session entry inside this OTS."
::= { apexDepiSessionBlade8StatusEntry 2 }

apexDepiSessionBlade8StatusStatus OBJECT-TYPE
    SYNTAX INTEGER
        {
         idle        (1),
         down        (2),
         settingup   (3),
         established (4)
        }
    MAX-ACCESS read-only
    STATUS current
    DESCRIPTION
        "M-CMTS core to the EQAM control connection status."
::= { apexDepiSessionBlade8StatusEntry 3 }

apexDepiSessionBlade8StatusInDataPackets OBJECT-TYPE
    SYNTAX Unsigned32
    MAX-ACCESS read-only
    STATUS current
    DESCRIPTION
        "Number of data packets received on this session."
::= { apexDepiSessionBlade8StatusEntry 4 }

apexDepiSessionBlade8StatusInSequenceDiscards OBJECT-TYPE
    SYNTAX Unsigned32
    MAX-ACCESS read-only
    STATUS current
    DESCRIPTION
        "Number of data packets received on this session that are discarded
         due to sequencing error."
::= { apexDepiSessionBlade8StatusEntry 5 }

apexDepiSessionBlade8StatusInDataPacketDiscards OBJECT-TYPE
    SYNTAX Unsigned32
    MAX-ACCESS read-only
    STATUS current
    DESCRIPTION
        "Number of data packets received on this session that are discarded
         for reasons other than sequencing errors."
::= { apexDepiSessionBlade8StatusEntry 6 }

apexDepiSessionBlade8StatusSessionID OBJECT-TYPE
    SYNTAX Unsigned32
    MAX-ACCESS read-only
    STATUS current
    DESCRIPTION
        "Local DEPI Session ID, used locally to bind the Session to a QAM Channel."
::= { apexDepiSessionBlade8StatusEntry 7 }

apexDepiSessionBlade8StatusInputIf OBJECT-TYPE
    SYNTAX Integer32 (1..12)
    MAX-ACCESS read-only
    STATUS current
    DESCRIPTION
        "Interface number.
        "
::= { apexDepiSessionBlade8StatusEntry 8 }

apexDepiSessionBlade8StatusDataRate OBJECT-TYPE
    SYNTAX Integer32
    MAX-ACCESS read-only
    STATUS current
    DESCRIPTION
        "Data rate.
        "
::= { apexDepiSessionBlade8StatusEntry 9 }

apexDepiSessionBlade8StatusSourceIp OBJECT-TYPE
    SYNTAX IpAddress
    MAX-ACCESS read-only
    STATUS current
    DESCRIPTION
        "Source IP Address.
        "
::= { apexDepiSessionBlade8StatusEntry 10 }

apexDepiSessionBlade8StatusActivationMode OBJECT-TYPE
    SYNTAX INTEGER
        {
         unknown      (0),
         static       (1),
         controlplane (2)
        }
    MAX-ACCESS read-only
    STATUS current
    DESCRIPTION
        "Activation mode of the session.
        "
::= { apexDepiSessionBlade8StatusEntry 11 }
   
apexDepiSessionBlade8StatusCCid OBJECT-TYPE
    SYNTAX          Unsigned32
    MAX-ACCESS read-only
    STATUS current
    DESCRIPTION
        "Control connection id if applicable.
        "
::= { apexDepiSessionBlade8StatusEntry 12 }

apexDepiSessionBlade8StatusSessionType OBJECT-TYPE
    SYNTAX INTEGER
        {
         unknown   (0),
         primary   (1),
         secondary (2)
        }
    MAX-ACCESS read-only
    STATUS current
    DESCRIPTION
        "Primary/secondary.
        "
::= { apexDepiSessionBlade8StatusEntry 13 }

apexDepiSessionBlade8StatusSyncRequired OBJECT-TYPE
    SYNTAX INTEGER
        {
         unknown (0),
         yes     (1),
         no      (2)
        }
    MAX-ACCESS read-only
    STATUS current
    DESCRIPTION
        "Sync correction required.
        "
::= { apexDepiSessionBlade8StatusEntry 14 }

apexDepiSessionBlade8StatusRemoteSessionId OBJECT-TYPE
    SYNTAX Unsigned32
    MAX-ACCESS read-only
    STATUS current
    DESCRIPTION
        "Remote DEPI Session ID, used by the Remote End to identify the DEPI
         Session."
::= { apexDepiSessionBlade8StatusEntry 15 }

apexDepiSessionBlade8StatusInputTsIndex OBJECT-TYPE
    SYNTAX Integer32
    MAX-ACCESS read-only
    STATUS current
    DESCRIPTION
        "The index into the apexGbeStatusInputTsStatTable."
::= { apexDepiSessionBlade8StatusEntry 16 }


-- ------------------------------------------------------------------------------
--
-- apexDepiControlConfig
--
-- apexDepiControlConfigGeneral
--

apexDepiAllowUnsupportedMandatoryAvps  OBJECT-TYPE
    SYNTAX EnableDisableTYPE
    MAX-ACCESS read-write
    STATUS current
    DESCRIPTION
        "Determines if a message with not expected AVPs marked as mandatory
         should be accepted or ignored.
         
         @Commit(param=apexDepiControlPlaneConfigApplyChange, value=2)
         @Config(config=yes, reboot=no)
         @Save(apexSaveConfig, value=2)
         @File(depicfg.ini, type='ini')
        "
::= { apexDepiControlConfigGeneral 1}

apexDepiKeepaliveTimeout  OBJECT-TYPE
    SYNTAX Integer32(1..3600)
    MAX-ACCESS read-write
    STATUS current
    DESCRIPTION
        "Keepalive Timeout used for the procedure to detect loss of connectivity with an M-CMTS core entity. 
         Default is set to 60 seconds.
         
         @Commit(param=apexDepiControlPlaneConfigApplyChange, value=2)
         @Config(config=yes, reboot=no)
         @Save(apexSaveConfig, value=2)
         @File(depicfg.ini, type='ini')
        "
::= { apexDepiControlConfigGeneral 2}

apexDepiKeepalive  OBJECT-TYPE
    SYNTAX EnableDisableTYPE
    MAX-ACCESS read-write
    STATUS current
    DESCRIPTION
        "Procedure to detect loss of connectivity with an M-CMTS core entity.

         When 'enabled', the APEX will use the value in apexDepiKeepaliveTimeout.
         When 'disabled', the APEX will not detect the loss of connectivity.

         Once written, the change to this parameter will take immediate
         effect.  In order for the change to persist through subsequent
         reboots or power cycles, the change must be saved via the
         apexSaveConfig parameter.
         
         @Commit(param=apexDepiControlPlaneConfigApplyChange, value=2)
         @Config(config=yes, reboot=no)
         @Save(apexSaveConfig, value=2)
         @File(depicfg.ini, type='ini')
        "
::= { apexDepiControlConfigGeneral 3}

apexDepiNumberRetransmissions  OBJECT-TYPE
    SYNTAX Integer32(1..10)
    MAX-ACCESS read-write
    STATUS current
    DESCRIPTION
        "Number of message retransmissions for not acknowledged messages sent before determining the message is lost. 
         Range is 1 to 10, in steps of 1.
         
         @Commit(param=apexDepiControlPlaneConfigApplyChange, value=2)
         @Config(config=yes, reboot=no)
         @Save(apexSaveConfig, value=2)
         @File(depicfg.ini, type='ini')
        "
::= { apexDepiControlConfigGeneral 4}

apexDepiControlPlaneConfigApplyChange  OBJECT-TYPE
    SYNTAX ApplyDataToDeviceTYPE
    MAX-ACCESS read-write 
    STATUS current
    DESCRIPTION
        "Applies the Depi control plane configuration changes.
        
        @Config(config=no, reboot=no)
        "
::= { apexDepiControlConfigGeneral 5 }

apexDepiControlPlaneConfigInvalidApplyText OBJECT-TYPE
    SYNTAX DisplayString (SIZE (0..80))
    MAX-ACCESS read-only
    STATUS current
    DESCRIPTION
        "When apexDepiControlPlaneConfigApplyChange is set to
         'applyNotInProgressInvalidData' this entry may contain
         a text description of what was wrong with the data. This
         entry contains the description for the most recent apply
         of a related entry that was invalid.
        "
::= { apexDepiControlConfigGeneral 6 }


-- ------------------------------------------------------------------------------
--
-- apexDepiControlConfigApplyTable
--

apexDepiControlConfigApplyTable OBJECT-TYPE
    SYNTAX SEQUENCE OF ApexDepiControlConfigApplyEntry
    MAX-ACCESS not-accessible
    STATUS current
    DESCRIPTION
        "Table of Apply Change for the data for apexDepiControlConfigTable.

         Entries in the apexDepiControlConfigTable cannot be modified while DEPI Control
         Connections and DEPI Sessions currently exist.
        "
::= { apexDepiControlConfig 2 }

apexDepiControlConfigApplyEntry OBJECT-TYPE
    SYNTAX ApexDepiControlConfigApplyEntry
    MAX-ACCESS not-accessible
    STATUS current
    DESCRIPTION
        "DEPI Control Configuration Apply Table Entry.
        "
    INDEX { apexDepiControlConfigApplyIndex }
::= { apexDepiControlConfigApplyTable 1 }

ApexDepiControlConfigApplyEntry ::= SEQUENCE
    {
     apexDepiControlConfigApplyIndex    Integer32,
     apexDepiControlConfigApplyChange   ApplyDataToDeviceTYPE
    }

apexDepiControlConfigApplyIndex OBJECT-TYPE
    SYNTAX Integer32(1..24)
    MAX-ACCESS not-accessible
    STATUS current
    DESCRIPTION
        "The index of the Depi Control Config Apply Table."
::= { apexDepiControlConfigApplyEntry 1 }

apexDepiControlConfigApplyChange OBJECT-TYPE
    SYNTAX ApplyDataToDeviceTYPE
    MAX-ACCESS read-write
    STATUS current
    DESCRIPTION
        "The Apply for any entries in the apexDepiControlConfigTable.

         Entries in the apexDepiControlConfigTable cannot be modified while DEPI Control
         Connections and DEPI Sessions currently exist.

         This parameter MUST be set to 'apply' in order for any of the data
         in the apexDepiControlConfigTable to take effect.  This
         parameter MUST be set LAST after all other data in the group has
         been configured.

         Once written, the change to this parameter will take immediate effect.

         @Config(config=no, reboot=no)
        "
::= { apexDepiControlConfigApplyEntry 2 }


-- ------------------------------------------------------------------------------
--
-- apexDepiControlConfigTable
--

apexDepiControlConfigTable OBJECT-TYPE
    SYNTAX SEQUENCE OF ApexDepiControlConfigEntry
    MAX-ACCESS not-accessible
    STATUS current
    DESCRIPTION
        "This table provides a list of DEPI Control Connections initiated by
         M-CMTS Cores.  A maximum of 10 connections is accepted.

         Entries in the apexDepiControlConfigTable cannot be modified while DEPI Control
         Connections and DEPI Sessions currently exist.

         @Config(config=yes, reboot=no)
         @Commit(param=apexDepiControlConfigApplyChange, value=2)
         @Save(apexSaveConfig, value=2)
         @File(depicfg.ini, type='ini')
        "
::= { apexDepiControlConfig 3 }

apexDepiControlConfigEntry OBJECT-TYPE
    SYNTAX ApexDepiControlConfigEntry
    MAX-ACCESS not-accessible
    STATUS current
    DESCRIPTION
        "DEPI Control Configuration Table Entry.
        "
    INDEX { apexDepiControlConfigIndex }
::= { apexDepiControlConfigTable 1 }

ApexDepiControlConfigEntry ::= SEQUENCE
    {
     apexDepiControlConfigIndex            Integer32,
     apexDepiControlConfigEnable           EnableDisableTYPE,
     apexDepiControlConfigInterfaceNumber  Integer32,
     apexDepiControlConfigSrcIpAddr        IpAddress
    }

apexDepiControlConfigIndex OBJECT-TYPE
    SYNTAX Integer32(1..24)
    MAX-ACCESS not-accessible
    STATUS current
    DESCRIPTION
        "The index of the Depi Control Config Table."
::= { apexDepiControlConfigEntry 1 }

apexDepiControlConfigEnable OBJECT-TYPE
    SYNTAX EnableDisableTYPE
    MAX-ACCESS read-write
    STATUS current
    DESCRIPTION
        "The enable setting for DEPI Control Connection.

         Once written, the change to this parameter will take immediate
         effect.  In order for the change to persist through subsequent
         reboots or power cycles, the change must be saved via the
         apexSaveConfig parameter.
        "
::= { apexDepiControlConfigEntry 2 }

apexDepiControlConfigInterfaceNumber OBJECT-TYPE
    SYNTAX Integer32(1..12)
    MAX-ACCESS read-write
    STATUS current
    DESCRIPTION
        "Represents the Gigabit Ethernet interface number.
         Range:
            '0'      = Not Applicable
            GBE      = 1-12
        "
::= { apexDepiControlConfigEntry 3 }

apexDepiControlConfigSrcIpAddr OBJECT-TYPE
    SYNTAX IpAddress
    MAX-ACCESS read-write
    STATUS current
    DESCRIPTION
        "This parameter indicates the M-CMTS Core IP address.
        "
::= { apexDepiControlConfigEntry 4 }


-- ------------------------------------------------------------------------------
--
-- apexDepiControlStatus
--
-- apexDepiControlStatusGeneral
--

apexDepiControlStatusGeneralInvalidApplyText OBJECT-TYPE
    SYNTAX DisplayString (SIZE (0..80))
    MAX-ACCESS read-only
    STATUS current
    DESCRIPTION
        "When apexDepiControlConfigApplyChange is set to
         'applyNotInProgressInvalidData' this entry may contain
         a text description of what was wrong with the data. This
         entry contains the description for the most recent apply
         of a related entry that was invalid.
        "
::= { apexDepiControlStatusGeneral 4 }


-- ------------------------------------------------------------------------------
--
-- apexDepiControlStatusTable
--

apexDepiControlStatusTable OBJECT-TYPE
    SYNTAX SEQUENCE OF ApexDepiControlStatusEntry
    MAX-ACCESS not-accessible
    STATUS current
    DESCRIPTION
        "Table of read-only status information pertaining to the DEPI Control
         Connections."
::= { apexDepiControlStatus 2 }

apexDepiControlStatusEntry OBJECT-TYPE
    SYNTAX ApexDepiControlStatusEntry
    MAX-ACCESS not-accessible
    STATUS current
    DESCRIPTION
        "DEPI Control Status Table Entry."
    INDEX { apexDepiControlStatusIndex }
::= { apexDepiControlStatusTable 1 }

ApexDepiControlStatusEntry ::= SEQUENCE
    {
      apexDepiControlStatusIndex              Integer32,
      apexDepiControlStatusConnectionStatus   INTEGER,
      apexDepiControlStatusTotalSessions      Unsigned32,
      apexDepiControlStatusInterfaceNumber    Integer32,
      apexDepiControlStatusSrcIpAddr          IpAddress,
      apexDepiControlStatusLocalConnId        Unsigned32,
      apexDepiControlStatusRemoteConnId       Unsigned32,
      apexDepiControlStatusRelatedConfigIndex Integer32
    }

apexDepiControlStatusIndex OBJECT-TYPE
    SYNTAX Integer32
    MAX-ACCESS not-accessible
    STATUS current
    DESCRIPTION
        "DEPI Session ID"
::= { apexDepiControlStatusEntry 1 }

apexDepiControlStatusConnectionStatus OBJECT-TYPE
    SYNTAX INTEGER
        {
         idle                (1),
         closing             (2),
         waiting             (3),
         established         (4)
        }
    MAX-ACCESS read-only
    STATUS current
    DESCRIPTION
        "M-CMTS core to the EQAM control connection status."
::= { apexDepiControlStatusEntry 2 }

apexDepiControlStatusTotalSessions OBJECT-TYPE
    SYNTAX Unsigned32
    MAX-ACCESS read-only
    STATUS current
    DESCRIPTION
        "Total number of sessions established on this control connection since
         EQAM reboot. Only valid for dynamically established connections.
        "
::= { apexDepiControlStatusEntry 3}

apexDepiControlStatusInterfaceNumber OBJECT-TYPE
    SYNTAX Integer32(1..12)
    MAX-ACCESS read-only
    STATUS current
    DESCRIPTION
        "Represents the Gigabit Ethernet interface number.
         Range:
            '0'      = Not Applicable
            GBE      = 1-8
        "
::= { apexDepiControlStatusEntry 4 }

apexDepiControlStatusSrcIpAddr OBJECT-TYPE
    SYNTAX IpAddress
    MAX-ACCESS read-only
    STATUS current
    DESCRIPTION
        "This parameter indicates the M-CMTS Core IP address.
        "
::= { apexDepiControlStatusEntry 5 }

apexDepiControlStatusLocalConnId OBJECT-TYPE
    SYNTAX Unsigned32
    MAX-ACCESS read-only
    STATUS current
    DESCRIPTION
        "Local connection ID for the control connection
        "
::= { apexDepiControlStatusEntry 6 }

apexDepiControlStatusRemoteConnId OBJECT-TYPE
    SYNTAX Unsigned32
    MAX-ACCESS read-only
    STATUS current
    DESCRIPTION
        "Remote connection ID for the control connection
        "
::= { apexDepiControlStatusEntry 7 }

apexDepiControlStatusRelatedConfigIndex OBJECT-TYPE
    SYNTAX Integer32 (1..24)
    MAX-ACCESS read-only
    STATUS current
    DESCRIPTION
        "Index of the entry in apexDepiControlConfigTable this connection belongs to.
         Speeds up processing time.
        "
::= { apexDepiControlStatusEntry 8 }


-- ------------------------------------------------------------------------------
--
-- apexUls
--
-- apexUlsConfig
--
-- apexUlsConfigGeneral
--

apexUlsConfigGenerateRequest OBJECT-TYPE
    SYNTAX ApplyDataToDeviceTYPE
    MAX-ACCESS read-write
    STATUS current
    DESCRIPTION
        "The Apply for generating ULS Feature Requests.
        
         This parameter MUST be set to 'apply' in order for 
         apexUlsConfigDocsisChannelsRequest, apexUlsConfigQamAnnexAChannelsRequest,
         and apexUlsConfigQamAnnexBChannelsRequest to take effect.
         This parameter MUST be set LAST after all other data has been configured.

         @Config(config=no, reboot=no)
        "
::= { apexUlsConfigGeneral 1 }

apexUlsConfigValidateResponse OBJECT-TYPE
    SYNTAX ApplyDataToDeviceTYPE
    MAX-ACCESS read-write
    STATUS current
    DESCRIPTION
        "The Apply for validating ULS Feature Response.
        
         This parameter MUST be set to 'apply' in order for 
         ULS-generated feature key file to be submitted.
         This parameter MUST be set after the binary key file 
         has been SFTP to the target device.

         @Config(config=no, reboot=no)
        "
::= { apexUlsConfigGeneral 2 }

apexUlsConfigCommitNewFeatures OBJECT-TYPE
    SYNTAX ApplyDataToDeviceTYPE
    MAX-ACCESS read-write
    STATUS current
    DESCRIPTION
        "The Apply for committing ULS feature Keys.
        
         This parameter MUST be set to 'apply' in order for 
         the validated feature keys to be committed.

         @Config(config=no, reboot=no)
        "
::= { apexUlsConfigGeneral 3 }


-- ------------------------------------------------------------------------------
--
-- apexUlsConfigDocsisFeatures
--

apexUlsConfigDocsisChannelsRequest OBJECT-TYPE
    SYNTAX Integer32
    MAX-ACCESS read-write
    STATUS current
    DESCRIPTION
        "Number of DOCSIS channels, being requested in this feature.
         
         @Config(config=no, reboot=no)
         @Commit(param=apexUlsConfigGenerateRequest , value=2)
        "
::= { apexUlsConfigDocsisFeatures 1 }


-- ------------------------------------------------------------------------------
--
-- apexUlsConfigQamAnnexAChannels
--

apexUlsConfigQamAnnexAChannelsRequest OBJECT-TYPE
    SYNTAX Integer32
    MAX-ACCESS read-write
    STATUS current
    DESCRIPTION
        "Number of QAM Annex A channels, being requested in this feature.
         
         @Config(config=no, reboot=no)
         @Commit(param=apexUlsConfigGenerateRequest , value=2)
        "
::= { apexUlsConfigQamAnnexAChannels 1 }


-- ------------------------------------------------------------------------------
--
-- apexUlsConfigQamAnnexBChannels
--

apexUlsConfigQamAnnexBChannelsRequest OBJECT-TYPE
    SYNTAX Integer32
    MAX-ACCESS read-write
    STATUS current
    DESCRIPTION
        "Number of QAM Annex B channels, being requested in this feature.
         
         @Config(config=no, reboot=no)
         @Commit(param=apexUlsConfigGenerateRequest , value=2)
        "
::= { apexUlsConfigQamAnnexBChannels 1 }


-- ------------------------------------------------------------------------------
--
-- apexUlsStatus
--
-- apexUlsStatusGeneral
--

apexUlsStatusGenerateRequestText OBJECT-TYPE
    SYNTAX DisplayString (SIZE (0..80))
    MAX-ACCESS read-only
    STATUS current
    DESCRIPTION
        "When apexUlsConfigGenerateRequest is set to applyNotInProgressInvalidData
         this entry may contain a text description of what was wrong with the data.
         This entry contains the description for the most recent apply that was invalid.
        "
::= { apexUlsStatusGeneral 1 }

apexUlsStatusValidateResponseText OBJECT-TYPE
    SYNTAX DisplayString (SIZE (0..80))
    MAX-ACCESS read-only
    STATUS current
    DESCRIPTION
        "When apexUlsConfigValidateResponse is set to applyNotInProgressInvalidData
         this entry may contain a text description of what was wrong with the data.
         This entry contains the description for the most recent apply that was invalid.
        "
::= { apexUlsStatusGeneral 2 }

apexUlsStatusCommitNewFeaturesText OBJECT-TYPE
    SYNTAX DisplayString (SIZE (0..80))
    MAX-ACCESS read-only
    STATUS current
    DESCRIPTION
        "When apexUlsConfigCommitNewFeatures is set to applyNotInProgressInvalidData
         this entry may contain a text description of what was wrong with the data.
         This entry contains the description for the most recent apply that was invalid.
        "
::= { apexUlsStatusGeneral 3 }


-- ------------------------------------------------------------------------------
--
-- apexUlsStatusDocsisFeatures
--

apexUlsStatusDocsisChannelsCurrent OBJECT-TYPE
    SYNTAX Integer32
    MAX-ACCESS read-only
    STATUS current
    DESCRIPTION
        "Number of DOCSIS channels, currently allowed in this feature."
::= { apexUlsStatusDocsisFeatures 1 }

apexUlsStatusDocsisChannelsInUse OBJECT-TYPE
    SYNTAX Integer32
    MAX-ACCESS read-only
    STATUS current
    DESCRIPTION
        "Number of DOCSIS channels, in use."
::= { apexUlsStatusDocsisFeatures 2 }


-- ------------------------------------------------------------------------------
--
-- apexUlsStatusQamAnnexAChannels
--

apexUlsStatusQamAnnexAChannelsCurrent OBJECT-TYPE
    SYNTAX Integer32
    MAX-ACCESS read-only
    STATUS current
    DESCRIPTION
        "Number of QAM Annex A channels, currently allowed in this feature."
::= { apexUlsStatusQamAnnexAChannels 1 }

apexUlsStatusQamAnnexAChannelsInUse OBJECT-TYPE
    SYNTAX Integer32
    MAX-ACCESS read-only
    STATUS current
    DESCRIPTION
        "Number of QAM Annex A channels, in use."
::= { apexUlsStatusQamAnnexAChannels 2 }


-- ------------------------------------------------------------------------------
--
-- apexUlsStatusQamAnnexBChannels
--

apexUlsStatusQamAnnexBChannelsCurrent OBJECT-TYPE
    SYNTAX Integer32
    MAX-ACCESS read-only
    STATUS current
    DESCRIPTION
        "Number of QAM Annex B channels, currently allowed in this feature."
::= { apexUlsStatusQamAnnexBChannels 1 }

apexUlsStatusQamAnnexBChannelsInUse OBJECT-TYPE
    SYNTAX Integer32
    MAX-ACCESS read-only
    STATUS current
    DESCRIPTION
        "Number of QAM Annex B channels, in use."
::= { apexUlsStatusQamAnnexBChannels 2 }


-- ------------------------------------------------------------------------------
--
-- apexQamEntitlement
--
-- apexQamEntConfig
--
-- apexQamEntConfigGeneral
--

apexQamEntConfigApplyChange OBJECT-TYPE
    SYNTAX ApplyDataToDeviceTYPE
    MAX-ACCESS read-write
    STATUS current
    DESCRIPTION
        "The Apply for all data in the apexQamEntConfigAssignTable.
         
         This parameter MUST be set to 'apply' in order for any of the data
         in the apexQamEntConfigAssignTable to take effect in the APEX.
         This parameter MUST be set LAST after all other data in the
         apexQamEntConfigAssignTable has been configured.

         @Config(config=no, reboot=no)
        "
::= { apexQamEntConfigGeneral 1 }


-- ------------------------------------------------------------------------------
--
-- apexQamEntConfigAssignTable
--

apexQamEntConfigAssignTable OBJECT-TYPE
    SYNTAX SEQUENCE OF ApexQamEntConfigAssignEntry
    MAX-ACCESS not-accessible
    STATUS current
    DESCRIPTION
        "Table of QAM Entitlement Assignment configuration.
         
         Once written, the change to this table will only take immediate
         effect after apexQamEntConfigApplyChange is set to 'apply'.
         In order for the change to persist through subsequent reboots
         or power cycles, the change must be saved via the apexSaveConfig
         parameter.
         
         @Config(config=yes, reboot=no)
         @Commit(param=apexQamEntConfigApplyChange, value=2)
         @Save(apexSaveConfig, value=2)
         @File(qamcfg.ini, type='ini')
        "
::= { apexQamEntConfig 3 }

apexQamEntConfigAssignEntry OBJECT-TYPE
    SYNTAX ApexQamEntConfigAssignEntry
    MAX-ACCESS not-accessible
    STATUS current
    DESCRIPTION
        "QAM Entitlement Configuration Apply Table Entry."
    INDEX { apexQamEntConfigAssignBladeNum,
            apexQamEntConfigAssignRfNum }
::= { apexQamEntConfigAssignTable 1 }

ApexQamEntConfigAssignEntry ::= SEQUENCE
    {
     apexQamEntConfigAssignBladeNum     Integer32,
     apexQamEntConfigAssignRfNum        Integer32,
     apexQamEntConfigAssignChannels     Integer32
    }

apexQamEntConfigAssignBladeNum OBJECT-TYPE
    SYNTAX Integer32(1..8)
    MAX-ACCESS not-accessible
    STATUS current
    DESCRIPTION
        "Blade number."
::= { apexQamEntConfigAssignEntry 1 }

apexQamEntConfigAssignRfNum OBJECT-TYPE
    SYNTAX Integer32(1..4)
    MAX-ACCESS not-accessible
    STATUS current
    DESCRIPTION
        "RF Port Number."
::= { apexQamEntConfigAssignEntry 2 }

apexQamEntConfigAssignChannels OBJECT-TYPE
    SYNTAX Integer32(0..64)
    MAX-ACCESS read-write
    STATUS current
    DESCRIPTION
        "The number of Chassis QAM Channel Entitlements assigned to this
         RF port from the chassis pools (apexUlsStatusQamAnnexAChannelsCurrent or
         apexUlsStatusQamAnnexBChannelsCurrent depending on current
         apexRfStatusTransmissionMode).  This setting is the number of channels
         to be added to the base level of channels (apexQamEntStatusMinChannels)
         for the RF port.  The total channels for the RF port (base plus chassis
         entitlements) will be represented in apexQamEntStatusTotalChannels
         after this parameter is applied.
         
         Valid values are in the range of:
            zero to (apexQamEntStatusMaxChannels - apexQamEntStatusMinChannels)
         
         Chassis QAM channel entitlements cannot be assigned to an RF port unless
         apexQamEntStatusHwSupport indicates 'supported'.
        "
::= { apexQamEntConfigAssignEntry 3 }


-- ------------------------------------------------------------------------------
--
-- apexQamEntStatus
--
-- apexQamEntStatusGeneral
--

apexQamEntStatusInvalidApplyText OBJECT-TYPE
    SYNTAX DisplayString (SIZE (0..80))
    MAX-ACCESS read-only
    STATUS current
    DESCRIPTION
        "When apexQamEntConfigApplyChange is set to applyNotInProgressInvalidData
         this entry may contain a text description of what was wrong with the data.
         This entry contains the description for the most recent apply of a
         table entry that was invalid.
        "
::= { apexQamEntStatusGeneral 1 }


-- ------------------------------------------------------------------------------
--
-- apexQamEntStatusTable
--

apexQamEntStatusTable OBJECT-TYPE
    SYNTAX SEQUENCE OF ApexQamEntStatusEntry
    MAX-ACCESS not-accessible
    STATUS current
    DESCRIPTION
        "QAM RF Port RF Counts Table.
         
         Contains counts of various status on an RF
         Port basis.
        "
::= { apexQamEntStatus 2 }

apexQamEntStatusEntry OBJECT-TYPE
    SYNTAX ApexQamEntStatusEntry
    MAX-ACCESS not-accessible
    STATUS current
    DESCRIPTION
        "QAM RF Port Counts Table Entry."
    INDEX { apexQamEntStatusBladeNum,
            apexQamEntStatusRfNum }
::= { apexQamEntStatusTable 1 }

ApexQamEntStatusEntry ::= SEQUENCE
    {
     apexQamEntStatusBladeNum       Integer32,
     apexQamEntStatusRfNum          Integer32,
     apexQamEntStatusHwSupport      INTEGER,
     apexQamEntStatusMinChannels    Integer32,
     apexQamEntStatusMaxChannels    Integer32,
     apexQamEntStatusTotalChannels  Integer32
    }

apexQamEntStatusBladeNum OBJECT-TYPE
    SYNTAX Integer32(1..8)
    MAX-ACCESS not-accessible
    STATUS current
    DESCRIPTION
        "QAM Blade Number.
        "
::= { apexQamEntStatusEntry 1 }

apexQamEntStatusRfNum OBJECT-TYPE
    SYNTAX Integer32(1..4)
    MAX-ACCESS not-accessible
    STATUS current
    DESCRIPTION
        "RF Port Number.
        "
::= { apexQamEntStatusEntry 2 }

apexQamEntStatusHwSupport OBJECT-TYPE
    SYNTAX INTEGER
        {
         unknown      (0),
         notSupported (1),
         supported    (2),
         overridden   (3)
        }
    MAX-ACCESS read-only
    STATUS current
    DESCRIPTION
        "Indicates whether HW supports assignment of Chassis QAM
         Channel Entitlements to this RF port.
         
         If 'notSupported', the HW must be converted before
         QAM channel entitlements can be applied.
         
         If 'overridden', it indicates entitlement checking is 
         bypassed.
        "
::= { apexQamEntStatusEntry 3 }

apexQamEntStatusMinChannels OBJECT-TYPE
    SYNTAX Integer32
    MAX-ACCESS read-only
    STATUS current
    DESCRIPTION
        "Minimum total QAM channels for this RF port.  This is a 'base' level
         of QAM channels and is HW dependant.
         The RF port cannot be authorized for less than this number.
         Chassis QAM Channel Entitlements are not included in this number.
         Chassis QAM Channel Entitlements are applied on top of this 'base'.
        "
::= { apexQamEntStatusEntry 4 }

apexQamEntStatusMaxChannels OBJECT-TYPE
    SYNTAX Integer32
    MAX-ACCESS read-only
    STATUS current
    DESCRIPTION
        "Maximum total QAM channels for this RF port.  This is a 'ceiling' level
         of QAM channels and is HW dependant.
         The RF port cannot be authorized for more than this number.
         Chassis QAM Channel Entitlements are applied up to this 'ceiling'.
        "
::= { apexQamEntStatusEntry 5 }

apexQamEntStatusTotalChannels OBJECT-TYPE
    SYNTAX Integer32
    MAX-ACCESS read-only
    STATUS current
    DESCRIPTION
        "Total QAM Channels authorized for use on this RF port.
         This is the sum of the 'base' (apexQamEntStatusMinChannels) and
         the assigned Chassis QAM Entitlements (apexQamEntConfigAssignChannels).
        "
::= { apexQamEntStatusEntry 6 }

-- ------------------------------------------------------------------------------
--
-- apexImportFile
--
-- apexImportFileConfig
--
-- apexImportFileConfigGeneral
--

apexImportFileRequest OBJECT-TYPE
    SYNTAX INTEGER
        {
         notApplicable            (0),
         importFileNotInProgress  (1),
         importFileRequest        (2),
         importFileInProgress     (3),
         importFileError          (4),
         importFileCompleted      (5)
        }
    MAX-ACCESS read-write
    STATUS current
    DESCRIPTION
        "This object handles file import interactions between EM and APEX3000.
         This request is used to start a configuration file import. The APEX3000
         will request files from the EM to import. All configuration files known
         to the APEX3000 will be imported from the user specified directory.
         
         The configuration files to import are defined by the APEX3000. The names
         must match the internally stored configuration file names. The user must
         ensure that all configuration files to import are correctly named and 
         stored in the user specified directory.
         
         'notApplicable'
          - default value (no import in progress)
          
         'importFileNotInProgress' 
          - no import in progress
          
         'importFileRequest' 
         - set by the EM to start a file import.
         
         'importFileInProgress' 
         - set by the APEX3000 when the File Import is in progress.

         'importFileError' 
         - set by the APEX3000 if some error makes the file import not possible. 
           Additional information is provided in apexImportFileStatusText.

         'importFileCompleted' 
         - set by the APEX3000 when the file import is completed.

         @Config(config=no, reboot=no)
        "
::= { apexImportFileConfigGeneral 1 }

apexImportFileOperation OBJECT-TYPE
    SYNTAX INTEGER
        {
         fileTransferRequestNotInProgress (0),
         fileTransferRequest              (1),
         fileIsReady                      (2),
         errorWhenUploadingfile           (3)
        }
    MAX-ACCESS read-write
    STATUS current
    DESCRIPTION
        "This object is used by the APEX to request a file transfer during the upgrade procedure.

         'fileTransferRequestNotInProgress' 
         - default value.
 
         'fileTransferRequest' 
         - set by the APEX to request a file transfer. The filename should
           be previously set in the apexImportFileRequestedFile object.

         'fileIsReady' 
         - set by the EM once the file is uploaded correctly on the APEX.

         'errorWhenUploadingfile' 
         - set by the EM when some error occurs during the upload operation.

         @Config(config=no, reboot=no)
        "
::= { apexImportFileConfigGeneral 2 }

apexImportFileRequestedFile OBJECT-TYPE
    SYNTAX DisplayString (SIZE (0..127))
    MAX-ACCESS read-write
    STATUS current
    DESCRIPTION
        "This object is used by the APEX to indicate the requested file during 
         the file import procedure. It's formatted using the following syntax:

         'local_file_name, destination_path'.

         Where local_file_name refers to the local path (user side), and 
         destination path is the remote directory where the EM should upload the file.
        
         for example:

         'config.ini, /config1/config.ini'.

         Indicates to the EM that it should upload the file 'config.ini' to the destination
         '/config1/config.ini'.

         @Config(config=no, reboot=no)
        "
::= { apexImportFileConfigGeneral 3 }


-- ------------------------------------------------------------------------------
--
-- apexImportFileStatus
--
-- apexImportFileStatusGeneral
--

apexImportFileStatusText OBJECT-TYPE
    SYNTAX DisplayString (SIZE (0..127))
    MAX-ACCESS read-only
    STATUS current
    DESCRIPTION
        "Additional information about the file import progress set by the APEX3000.
        "
::= { apexImportFileStatusGeneral 1 }

apexImportFileOperationalState OBJECT-TYPE
    SYNTAX INTEGER
        {
         importFileNotInProgress (0),
         importFileInProgress    (1)
        }
    MAX-ACCESS read-only
    STATUS current
    DESCRIPTION
        "Indicates if the Import of files is in progress or not. When set to
        'importFileInProgress', this indicates the APEX is actively importing
        files.
        "
::= { apexImportFileStatusGeneral 2 }

-- ------------------------------------------------------------------------------
--
-- apexAlarms
--

apexAlarmHardwareFault OBJECT-TYPE
    SYNTAX INTEGER
        {
         ok(1),
         indeterminate(2),
         warning(3),
         minor(4),
         major(5),
         critical(6)
        }
    MAX-ACCESS read-only
    STATUS current
    DESCRIPTION
        "Indicates that a Hardware related error occurred.
        
         Examples include:
         missing or uncommunicative HW, failures in initialization of HW, and
         failures to configure HW.  These can occur at startup or when the
         system is operational.  Types of HW Faults include:  Application File(s)
         Download failure; SPI Interface Initialization failure; PCI Interface
         Initialization failure; GigE Configuration failure; MUX Configuration
         failure; QAM Blade Communication failure; Unsupported/Incorrect
         HW/FW Version (QAM, etc.); Fatal Host Firmware Exception.

         'critical' indicates a fatal error occurred that prevents the APEX
          from performing operational requirements.

         'warning' indicates an error that does not prevent the APEX from
         performing operational requirements.
        "
        --MOT-MIBCOMP-BE-EXT <DbHint map="SCALAR" crs_fmt="1" crs_desc="Hardware Fault"
        --crs_define="EC_HARDWARE_FAULT_ALARM"></DbHint>
::= { apexAlarms 8000 }

apexAlarmInvalidConfigData OBJECT-TYPE
    SYNTAX INTEGER
        {
         ok(1),
         indeterminate(2),
         warning(3),
         minor(4),
         major(5),
         critical(6)
        }
    MAX-ACCESS read-only
    STATUS current
    DESCRIPTION
        "Set to 'warning' when invalid Initialization data (ini files) is encountered.
        "
        --MOT-MIBCOMP-BE-EXT <DbHint map="SCALAR" crs_fmt="1" crs_desc="Invalid Initialization"
        --crs_define="EC_INVALID_INIT_DATA_ALARM"></DbHint>
::= { apexAlarms 8001 }

apexAlarmTemperatureFault OBJECT-TYPE
    SYNTAX INTEGER
        {
         ok(1),
         indeterminate(2),
         warning(3),
         minor(4),
         major(5),
         critical(6)
        }
    MAX-ACCESS read-only
    STATUS current
    DESCRIPTION
        "'critical' indicates one or more temperature sensors is reporting a
         high temperature condition.
        "
        --MOT-MIBCOMP-BE-EXT <DbHint map="SCALAR" crs_fmt="1" crs_desc="Temperature Fault"
        --crs_define="EC_TEMPERATURE_ALARM"></DbHint>
::= { apexAlarms 8002 }

apexAlarmFanFault OBJECT-TYPE
    SYNTAX INTEGER
        {
         ok(1),
         indeterminate(2),
         warning(3),
         minor(4),
         major(5),
         critical(6)
        }
    MAX-ACCESS read-only
    STATUS current
    DESCRIPTION
        "'major' indicates one or more fans has reduced RPM readings.
        "
        --MOT-MIBCOMP-BE-EXT <DbHint map="SCALAR" crs_fmt="1" crs_desc="Fan Fault"
        --crs_define="EC_FAN_FAULT_ALARM"></DbHint>
::= { apexAlarms 8003 }

apexAlarmPowerSupplyFault OBJECT-TYPE
    SYNTAX INTEGER
        {
         ok(1),
         indeterminate(2),
         warning(3),
         minor(4),
         major(5),
         critical(6)
        }
    MAX-ACCESS read-only
    STATUS current
    DESCRIPTION
        "Power Supply Fault Alarm.

         'critical' indicates power supply input power fault (apexPsStatusInputPowerStatus),
            output power fault (apexPsStatusOutputPowerStatus), or comm fault
            (apexPsStatusCommError).
        "
        --MOT-MIBCOMP-BE-EXT <DbHint map="SCALAR" crs_fmt="1" crs_desc="Power Fault"
        --crs_define="EC_POWER_FAULT_ALARM"></DbHint>
::= { apexAlarms 8004 }

apexAlarmFanModuleFault OBJECT-TYPE
    SYNTAX INTEGER
        {
         ok(1),
         indeterminate(2),
         warning(3),
         minor(4),
         major(5),
         critical(6)
        }
    MAX-ACCESS read-only
    STATUS current
    DESCRIPTION
        "Fan Module Fault Alarm.

         'major' indicates the fan module on a QAM blade or a blade filler module is removed.
        "
        --MOT-MIBCOMP-BE-EXT <DbHint map="SCALAR" crs_fmt="1" crs_desc="Fan Module Fault"
        --crs_define="EC_FAN_MODULE_FAULT_ALARM"></DbHint>
::= { apexAlarms 8005 }

apexAlarmHostModuleFault OBJECT-TYPE
    SYNTAX INTEGER
        {
         ok(1),
         indeterminate(2),
         warning(3),
         minor(4),
         major(5),
         critical(6)
        }
    MAX-ACCESS read-only
    STATUS current
    DESCRIPTION
        "Host Module Fault Alarm.

         'critical' indicates a critical fault on a host module. This indicates a loss of 
         Ethernet connectivity or a critical HW fault of the module. This may cause a 
         host module failover in the case host redundancy is available.
        "
        --MOT-MIBCOMP-BE-EXT <DbHint map="SCALAR" crs_fmt="1" crs_desc="Host Module Fault"
        --crs_define="EC_HOST_MODULE_FAULT_ALARM"></DbHint>
::= { apexAlarms 8006 }

apexAlarmFrontPanelModuleFault OBJECT-TYPE
    SYNTAX INTEGER
        {
         ok(1),
         indeterminate(2),
         warning(3),
         minor(4),
         major(5),
         critical(6)
        }
    MAX-ACCESS read-only
    STATUS current
    DESCRIPTION
        "Front Panel Module Fault Alarm.

         'major' indicates module removed or failed, examples include unsupported
         module installed, no module installed, power fault, module offline.
        "
        --MOT-MIBCOMP-BE-EXT <DbHint map="SCALAR" crs_fmt="1" crs_desc="Front Panel Module Fault"
        --crs_define="EC_FRONT_PANEL_MODULE_FAULT_ALARM"></DbHint>
::= { apexAlarms 8007 }

apexAlarmRfSwitchModuleFault OBJECT-TYPE
    SYNTAX INTEGER
        {
         ok(1),
         indeterminate(2),
         warning(3),
         minor(4),
         major(5),
         critical(6)
        }
    MAX-ACCESS read-only
    STATUS current
    DESCRIPTION
        "RF Switch Module Fault Alarm.

         'critical' indicates module removed or failed, examples include unsupported
         module installed, no module installed, power fault, module offline.
        "
        --MOT-MIBCOMP-BE-EXT <DbHint map="SCALAR" crs_fmt="1" crs_desc="RF Switch Module Fault"
        --crs_define="EC_RF_SWITCH_ALARM"></DbHint>
::= { apexAlarms 8008 }

apexAlarm10GbeModuleFault OBJECT-TYPE
    SYNTAX INTEGER
        {
         ok(1),
         indeterminate(2),
         warning(3),
         minor(4),
         major(5),
         critical(6)
        }
    MAX-ACCESS read-only
    STATUS current
    DESCRIPTION
        "10GigE Module Fault Alarm.

         'major' indicates module removed or failed, examples include unsupported
         module installed, no module installed, power fault, module offline.
        "
        --MOT-MIBCOMP-BE-EXT <DbHint map="SCALAR" crs_fmt="1" crs_desc="10GigE Module Fault"
        --crs_define="EC_10GIGE_MODULE_ALARM"></DbHint>
::= { apexAlarms 8009 }

apexAlarmDtiModuleFault OBJECT-TYPE
    SYNTAX INTEGER
        {
         ok(1),
         indeterminate(2),
         warning(3),
         minor(4),
         major(5),
         critical(6)
        }
    MAX-ACCESS read-only
    STATUS current
    DESCRIPTION
        "DTI Module Fault Alarm.

         'major' indicates module not detected or fault with the module found. 
        "
        --MOT-MIBCOMP-BE-EXT <DbHint map="SCALAR" crs_fmt="1" crs_desc="DTI Module Fault"
        --crs_define="EC_DTI_MODULE_ALARM"></DbHint>
::= { apexAlarms 8010 }

apexAlarmGbeLossOfPhysicalInput OBJECT-TYPE
    SYNTAX INTEGER
        {
         ok(1),
         indeterminate(2),
         warning(3),
         minor(4),
         major(5),
         critical(6)
        }
    MAX-ACCESS read-only
    STATUS current
    DESCRIPTION
        "Loss of Physical Gigabit Ethernet Input Alarm.

         'critical' indicates that one or more physical interfaces that are
         configured as enabled to receive input have a failure
         (apexGbeStatusLossOfPhysicalInput).

         Physical input interfaces can be disabled to prevent this alarm
         when no input is connected.
        "
        --MOT-MIBCOMP-BE-EXT <DbHint map="SCALAR" crs_fmt="1" crs_desc="GigE Physical Input Failure"
        --crs_define="EC_GBE_PHYS_INPUT_FAILURE_ALARM"></DbHint>
::= { apexAlarms 8020 }

apexAlarmGbeBufferFullness OBJECT-TYPE
    SYNTAX INTEGER
        {
         ok(1),
         indeterminate(2),
         warning(3),
         minor(4),
         major(5),
         critical(6)
        }
    MAX-ACCESS read-only
    STATUS current
    DESCRIPTION
        "Gigabit Ethernet Frame Buffer Fullness Alarm.

         This alarm is used to inform the user when one or more Gigabit Ethernet
         Frame buffers are about to overflow. The overflow level is based on the
         actual input data rate.

         'major' when the frame buffer level crosses a user specified threshold
         (apexGbeConfFrameBufferAlarmThreshold).  Cleared when the buffer level drops
         below the threshold.

         'critical' when the frame buffer is completely full and frames are being
         dropped.  Cleared when the overflow condition no longer is detected.

         A Major alarm, depending on the threshold setting, indicates that the
         APEX is getting close to crossing the reset level associated with it's internal
         Gigabit Ethernet frame buffers.

         A Critical alarm indicates that the frame buffer reset levels have been crossed.
         This will cause loss of packets and may result in tiling and other output
         anomalies.
        "
        --MOT-MIBCOMP-BE-EXT <DbHint map="SCALAR" crs_fmt="1" crs_desc="GigE Buffer Fullness"
        --crs_define="EC_GBE_BUFFER_FULLNESS_ALARM"></DbHint>
::= { apexAlarms 8021 }

apexAlarmGbeInputStreamHighBitRate OBJECT-TYPE
    SYNTAX INTEGER
        {
         ok(1),
         indeterminate(2),
         warning(3),
         minor(4),
         major(5),
         critical(6)
        }
    MAX-ACCESS read-only
    STATUS current
    DESCRIPTION
        "Gigabit Ethernet Input Stream High Bit Rate Alarm.

         This alarm is used to inform the user when one or more Gigabit Ethernet
         Input Streams as configured in apexManRteGbeInRedTable or via a Session
         Controller have a high bit rate condition.  For alarm status of each
         stream refer to entry apexGbeStatInTsPriHighBitRateAlarm and
         apexGbeStatInTsSecHighBitRateAlarm.

         'major' when one or more input stream bit rates are above their defined
         bandwidth.  Clears when all streams have been restored to at or below
         their defined bandwidth.
        "
        --MOT-MIBCOMP-BE-EXT <DbHint map="SCALAR" crs_fmt="1" crs_desc="GigE Input High Bit Rate"
        --crs_define="EC_GBE_IN_HIGH_BIT_RATE_ALARM"></DbHint>
::= { apexAlarms 8022 }

apexAlarmGbeInputTsRedundFailover OBJECT-TYPE
    SYNTAX INTEGER
        {
         ok(1),
         indeterminate(2),
         warning(3),
         minor(4),
         major(5),
         critical(6)
        }
    MAX-ACCESS read-only
    STATUS current
    DESCRIPTION
        "Gigabit Ethernet Input MPTS Redundant Fail Over Alarm.

         This alarm is used to inform the user when one or more Gigabit Ethernet
         Input Streams configured in apexManRteGbeInRedTable as being the Primary
         stream of a Redundant Pair have Failed Over to the Secondary stream.
         For alarm status of each stream refer to entry apexGbeStatInTsRedundFailoverError.

         'major' when one or more Redundant Primary streams have failed over to
         the Secondary.  Clears when all Primary streams have been restored and the
         APEX has switched back to the Primary from the Secondary.
        "
        --MOT-MIBCOMP-BE-EXT <DbHint map="SCALAR" crs_fmt="1" crs_desc="Input TS Redundant Fail Over"
        --crs_define="EC_INPUT_TS_FAILOVER_ALARM"></DbHint>
::= { apexAlarms 8023 }

apexAlarmServiceInError OBJECT-TYPE
    SYNTAX INTEGER
        {
         ok(1),
         indeterminate(2),
         warning(3),
         minor(4),
         major(5),
         critical(6)
        }
    MAX-ACCESS read-only
    STATUS current
    DESCRIPTION
        "Alarm Service In Error.

         'major' indicates that one or more services is in error (unable
         to fully continue processing). However, this is only for very
         specific errors where the error could be caused by either the
         input stream being invalid or another command along with the
         input stream is causing the error. For example, if mapping an
         input service to an output and that PMT is not referenced in
         the PAT, or the number of PIDs in the PMT is greater than the
         number of PIDs supported, then the command is in error. This
         error condition would be cleared if a new PAT is received
         referencing the PMT or in the other case, if a new PMT is
         received referencing a valid number of PIDs.

         Refer to apexOutputProgramRoutingStatus for more information.

         This alarm occurs on the first error.  It is not issued for
         additional errors.  It is cleared when all errors are cleared.
        "
        --MOT-MIBCOMP-BE-EXT <DbHint map="SCALAR" crs_fmt="1" crs_desc="Service In Error"
        --crs_define="EC_SERVICE_IN_ERROR_ALARM"></DbHint>
::= { apexAlarms 8024 }

apexAlarmGbeLossOfInputStream OBJECT-TYPE
    SYNTAX INTEGER
        {
         ok(1),
         indeterminate(2),
         warning(3),
         minor(4),
         major(5),
         critical(6)
        }
    MAX-ACCESS read-only
    STATUS current
    DESCRIPTION
        "Gigabit Ethernet Loss of Input Stream Alarm.

         This alarm is used to inform the user when one or more Gigabit Ethernet
         Input Streams is missing. A missing input stream is determined based 
         on user configured data or stream rate and detection timeout value. This
         alarm is only applicable when the input streams are configured to be
         monitored for loss of input stream.          

         This alarm occurs on the first error.  It is not issued for
         additional errors.  It is cleared when all errors are cleared.
         'major' when one or more input streams have been lost.  Clears when all input streams 
         have been restored.
        "
        --MOT-MIBCOMP-BE-EXT <DbHint map="SCALAR" crs_fmt="1" crs_desc="GigE Loss of Input Stream"
        --crs_define="EC_GBE_LOSS_OF_INPUT_TS_ALARM"></DbHint>
::= { apexAlarms 8025 }

apexAlarmNpuToHostCommFault OBJECT-TYPE
    SYNTAX INTEGER
        {
         ok           (1),
         indeterminate(2),
         warning      (3),
         minor        (4),
         major        (5),
         critical     (6)
        }
    MAX-ACCESS read-only
    STATUS current
    DESCRIPTION
        "Loss of Communications from Gige to Host Alarm.

         This alarm is used to inform the user when the Host processor is no longer receiving
         periodic status messages from the NPU processor.
         
         This alarm occurs on the first error.  It is not issued for
         additional errors. It is cleared when the condition is resolved.
        "
        --MOT-MIBCOMP-BE-EXT <DbHint map="SCALAR" crs_fmt="1" crs_desc="NPU to Host Communication Fault"
        --crs_define="EC_NPU_TO_HOST_LOSS_COMM_ALARM"></DbHint>
::= { apexAlarms 8026 }

apexAlarmGbeInterfaceRedundFailover OBJECT-TYPE
    SYNTAX INTEGER
        {
         ok(1),
         indeterminate(2),
         warning(3),
         minor(4),
         major(5),
         critical(6)
        }
    MAX-ACCESS read-only
    STATUS current
    DESCRIPTION
        "Gigabit Ethernet Interface Redundant Fail Over Alarm.

         This alarm is used to inform the user when one or more Gigabit Ethernet
         interfaces have Failed Over to the Secondary interface.  The APEX determines an
         interface as failed when link has been lost.

         'major' when one or more Primary interfaces have failed over to
         the Secondary.  Clears when all Primary interfaces have been restored and the
         APEX has switched back to the Primary from the Secondary.
        "
        --MOT-MIBCOMP-BE-EXT <DbHint map="SCALAR" crs_fmt="1" crs_desc="GigE Interface Redundancy Fail Over"
        --crs_define="EC_GBE_INTERFACE_REDUND_ALARM"></DbHint>
::= { apexAlarms 8027 }

apexAlarmServiceInactiveError OBJECT-TYPE
    SYNTAX INTEGER
        {
         ok(1),
         indeterminate(2),
         warning(3),
         minor(4),
         major(5),
         critical(6)
        }
    MAX-ACCESS read-only
    STATUS current
    DESCRIPTION
        "Alarm Service In Error.

         'warning' indicates that one or more services is inactive. Indicates
         a service is mapped to a QAM blade that has inactive outputs. This is
         typically caused by a QAM fault, but can occur when an output streams
         are removed from an output.
         
         This alarm occurs on the first error.  It is not issued for
         additional errors.  It is cleared when all errors are cleared.
        "
        --MOT-MIBCOMP-BE-EXT <DbHint map="SCALAR" crs_fmt="1" crs_desc="Service Inactive Error"
        --crs_define="EC_SERVICE_INACTIVE_ERROR_ALARM"></DbHint>
::= { apexAlarms 8028 }

apexAlarmOutputUtilizationFault OBJECT-TYPE
    SYNTAX INTEGER
        {
         ok(1),
         indeterminate(2),
         warning(3),
         minor(4),
         major(5),
         critical(6)
        }
    MAX-ACCESS read-only
    STATUS current
    DESCRIPTION
        "Output Transport Stream Utilization Threshold Alarm.

         'minor' when apexOutputTsUtilMonAlarmThreshold is met or
         exceeded for apexOutputTsUtilMonSetAlarmDelay for an OTS.

         The alarm will clear after the OTS remains below
         apexOutputTsUtilMonAlarmThreshold for
         apexOutputTsUtilMonClearAlarmDelay.
        "
        --MOT-MIBCOMP-BE-EXT <DbHint map="SCALAR" crs_fmt="1" crs_desc="Output Utilization Fault"
        --crs_define="EC_OTS_UTILIZATION_ALARM"></DbHint>
::= { apexAlarms 8040 }

apexAlarmOutputOverflow OBJECT-TYPE
    SYNTAX INTEGER
        {
         ok(1),
         indeterminate(2),
         warning(3),
         minor(4),
         major(5),
         critical(6)
        }
    MAX-ACCESS read-only
    STATUS current
    DESCRIPTION
        "Output Transport Stream Overflow Alarm.

         'critical' when apexOutputTsOverflowAlarm occurs for an OTS.

         The alarm will clear when OTS no longer in overflow.
        "
        --MOT-MIBCOMP-BE-EXT <DbHint map="SCALAR" crs_fmt="1" crs_desc="Output Overflow"
        --crs_define="EC_OTS_OVERFLOW_ALARM"></DbHint>
::= { apexAlarms 8041 }

apexAlarmQamBladeFault OBJECT-TYPE
    SYNTAX INTEGER
        {
         ok(1),
         indeterminate(2),
         warning(3),
         minor(4),
         major(5),
         critical(6)
        }
    MAX-ACCESS read-only
    STATUS current
    DESCRIPTION
        "QAM Blade Fault Alarm.
        
         'critical' when apexQamBladeStatusFaultCondition is set.

         The alarm will clear after all faults clear on the QAM Module.

         The current alarm status on a QAM Module basis can be found in
         apexQamBladeStatusFaultCondition.
        "
        --MOT-MIBCOMP-BE-EXT <DbHint map="SCALAR" crs_fmt="1" crs_desc="QAM Blade Fault"
        --crs_define="EC_QAM_MODULE_ALARM"></DbHint>
::= { apexAlarms 8042 }

apexAlarmQamRfPortFault OBJECT-TYPE
    SYNTAX INTEGER
        {
         ok(1),
         indeterminate(2),
         warning(3),
         minor(4),
         major(5),
         critical(6)
        }
    MAX-ACCESS read-only
    STATUS current
    DESCRIPTION
        "QAM RF Port Fault Alarm.

         'major' when RF output level is not within the user specified thresholds.

         'critical' when RF output level exceeds +/- 10 dB of set level or other
         fatal error occurs.

         The alarm will clear after all faults clear for the RF Port.

         The current alarm status on an RF port basis can be found in
         apexRfErrorRfPortFaultCondition.
        "
        --MOT-MIBCOMP-BE-EXT <DbHint map="SCALAR" crs_fmt="1" crs_desc="QAM RF Port Fault"
        --crs_define="EC_QAM_RF_PORT_ALARM"></DbHint>
::= { apexAlarms 8043 }

apexAlarmQamChannelFault OBJECT-TYPE
    SYNTAX INTEGER
        {
         ok(1),
         indeterminate(2),
         warning(3),
         minor(4),
         major(5),
         critical(6)
        }
    MAX-ACCESS read-only
    STATUS current
    DESCRIPTION
        "QAM Channel Fault Alarm.

         'critical' when one or more QAM Channels on an RF Port has an error.

         The alarm will clear after errors all QAM channels on the RF Port are clear.

         The current alarm status on a QAM channel basis can be found in
         apexRfErrorChannelFaultCondition.
        "
        --MOT-MIBCOMP-BE-EXT <DbHint map="SCALAR" crs_fmt="1" crs_desc="QAM Channel Fault"
        --crs_define="EC_QAM_CHANNEL_ALARM"></DbHint>
::= { apexAlarms 8044 }

apexAlarmQamBladeRedundFailover OBJECT-TYPE
    SYNTAX INTEGER
        {
         ok(1),
         indeterminate(2),
         warning(3),
         minor(4),
         major(5),
         critical(6)
        }
    MAX-ACCESS read-only
    STATUS current
    DESCRIPTION
        "QAM Blade Redundancy Fail Over Alarm.

         'major' when the backup QAM Blade status is 'active' (apexQamBladeRedundStatusBackupBlade).
                 This occurs when a primary QAM Blade has failed over to the backup blade or
                 the user has forced a primary to the backup.

         The alarm will clear when the backup QAM Blade status returns to 'standby'.
         The alarm is relevant only when apexQamBladeRedundConfigEnable is 'enabled'.
         The current QAM Blade that is active on the backup can be found
         in apexQamBladeRedundStatusFailedBlade.
        "
        --MOT-MIBCOMP-BE-EXT <DbHint map="SCALAR" crs_fmt="1" crs_desc="QAM Blade Redundant Fail Over"
        --crs_define="EC_QAM_RF_FAILOVER_ALARM"></DbHint>
::= { apexAlarms 8045 }

apexAlarmQamBladeRedundMismatch OBJECT-TYPE
    SYNTAX INTEGER
        {
         ok(1),
         indeterminate(2),
         warning(3),
         minor(4),
         major(5),
         critical(6)
        }
    MAX-ACCESS read-only
    STATUS current
    DESCRIPTION
        "QAM Blade Redundancy Mismatch Alarm.

         'major' when channels could be lost on QAM Fail Over to backup.
                 Refer to apexQamBladeRedundStatusMismatch for more information.

         The alarm will clear when mismatch condition clears.
         The alarm is relevant only when apexQamBladeRedundConfigEnable is 'enabled'.
        "
        --MOT-MIBCOMP-BE-EXT <DbHint map="SCALAR" crs_fmt="1" crs_desc="QAM Blade Redundant Mismatch"
        --crs_define="EC_QAM_RF_MISMATCH_ALARM"></DbHint>
::= { apexAlarms 8046 }

apexAlarmQamBladePhysicalLatchFault OBJECT-TYPE
    SYNTAX INTEGER
        {
         ok(1),
         indeterminate(2),
         warning(3),
         minor(4),
         major(5),
         critical(6)
        }
    MAX-ACCESS read-only
    STATUS current
    DESCRIPTION
        "QAM Blade Physical Latch Fault Alarm.

         'warning' Indicates Raptor QAM Blade that Raptor QAM Blade has been
          inserted and started without closing the latch.
  
         The alarm will clear when latched is closed.

         The alarm may NOT be disabled.

         Module # represents the physical slot number of active QAM blade.
         The alarm will clear when physical latch is closed and the condition clears.
        "
        --MOT-MIBCOMP-BE-EXT <DbHint map="SCALAR" crs_fmt="1" crs_desc="QAM Blade Physical Latch Fault"
        --crs_define="EC_QAM_MODULE_LATCH_ALARM"></DbHint>
::= { apexAlarms 8047 }

apexAlarmRtspControllerCommFault OBJECT-TYPE
    SYNTAX INTEGER
        {
         ok(1),
         indeterminate(2),
         warning(3),
         minor(4),
         major(5),
         critical(6)
        }
    MAX-ACCESS read-only
    STATUS current
    DESCRIPTION
        "RTSP Controller Communication Fault.

         'major' when the RTSP Controller is experiencing a
         communication fault.

         The alarm will clear when connection is restored the RTSP
         controller.
        "
        --MOT-MIBCOMP-BE-EXT <DbHint map="SCALAR" crs_fmt="1" crs_desc="RTSP Controller Communication Fault"
        --crs_define="EC_RTSP_CONTROL_COMM_ALARM"></DbHint>
::= { apexAlarms 8060 }

apexAlarmRdsCommFault OBJECT-TYPE
    SYNTAX INTEGER
        {
         ok(1),
         indeterminate(2),
         warning(3),
         minor(4),
         major(5),
         critical(6)
        }
    MAX-ACCESS read-only
    STATUS current
    DESCRIPTION
        "RTSP Controller Communication Fault.

         'major' when experiencing an RDS
         communication fault.

         The alarm will clear when RDS connection is restored.
        "
        --MOT-MIBCOMP-BE-EXT <DbHint map="SCALAR" crs_fmt="1" crs_desc="RDS Communication Fault"
        --crs_define="EC_RDS_COMM_ALARM"></DbHint>
::= { apexAlarms 8070 }

apexAlarmHostModuleRedundFailover OBJECT-TYPE
    SYNTAX INTEGER
        {
         ok(1),
         indeterminate(2),
         warning(3),
         minor(4),
         major(5),
         critical(6)
        }
    MAX-ACCESS read-only
    STATUS current
    DESCRIPTION
        "Host Module Redundant Fail Over.

         'major' when failover from active to standby.

         The alarm will clear when the standby host module completes the failover process 
         and becomes active.
        "
        --MOT-MIBCOMP-BE-EXT <DbHint map="SCALAR" crs_fmt="1" crs_desc="Host Module Redundancy Failover"
        --crs_define="EC_HOST_FAILOVER_ALARM"></DbHint>
::= { apexAlarms 8080 }

apexAlarmHostModuleRedundFault OBJECT-TYPE
    SYNTAX INTEGER
        {
         ok(1),
         indeterminate(2),
         warning(3),
         minor(4),
         major(5),
         critical(6)
        }
    MAX-ACCESS read-only
    STATUS current
    DESCRIPTION
        "Host Module Redundancy Availability Fault.

         'major' when any host module is in failure or not present (host
          module redundancy not available).

         The alarm will clear when errors in both host modules are cleared 
         or redundancy is suspended.
        "
        --MOT-MIBCOMP-BE-EXT <DbHint map="SCALAR" crs_fmt="1" crs_desc="Host Module Redundancy Fault"
        --crs_define="EC_HOST_REDUND_FAULT_ALARM"></DbHint>
::= { apexAlarms 8081 }

apexAlarmDtiSyncLossFault OBJECT-TYPE
    SYNTAX INTEGER
        {
         ok           (1),
         indeterminate(2),
         warning      (3),
         minor        (4),
         major        (5),
         critical     (6)
        }
    MAX-ACCESS read-only
    STATUS current
    DESCRIPTION
        "EQAM lost SYNC with the DTI Server.
        "
        --MOT-MIBCOMP-BE-EXT <DbHint map="SCALAR" crs_fmt="1" crs_desc="DTI SYNC LOSS FAULT"
        --crs_define="EC_DTI_SYNC_LOSS_ALARM"></DbHint>

::= { apexAlarms 8090 }

apexAlarmDepiControlConnectionFault OBJECT-TYPE
    SYNTAX INTEGER
        {
         ok           (1),
         indeterminate(2),
         warning      (3),
         minor        (4),
         major        (5),
         critical     (6)
        }
    MAX-ACCESS read-only
    STATUS current
    DESCRIPTION
        "DEPI Control connection setup Fault.
        "
        --MOT-MIBCOMP-BE-EXT <DbHint map="SCALAR" crs_fmt="1" crs_desc="DEPI CONTROL CONNECTION FAULT"
        --crs_define="EC_DEPI_CONTROL_CONNECTION_ALARM"></DbHint>

::= { apexAlarms 8091 }


-- ------------------------------------------------------------------------------
--
-- apexEvents
--

apexEventEmUserLoginFailed OBJECT-TYPE
    SYNTAX Unsigned32
    MAX-ACCESS read-only
    STATUS current
    DESCRIPTION
        "Event to indicate APEX EM User login failed 5 times."
        --MOT-MIBCOMP-BE-EXT <DbHint map="SCALAR" crs_fmt="1" crs_desc="EM USER Login Failed 5 Times"
        --crs_define="EC_EM_USER_LOGIN_FAILED_EVENT"></DbHint>
::= { apexEvents 8500 }


-- ------------------------------------------------------------------------------
--
-- apexConfigAlarms
--
-- apexConfAlarmEnable
--

apexEnableInvalidConfigData OBJECT-TYPE
    SYNTAX EnableDisableTYPE
    MAX-ACCESS read-write
    STATUS current
    DESCRIPTION
        "This setting enables or disables apexAlarmInvalidConfigData.

         When set to 'enabled' the alarm will operate as described.

         When set to 'disabled' the alarm will not be reported or wrapped
         into unitAlarmStatus and the alarm condition will remain 'ok'.
         If the alarm condition is not 'ok' when it is 'disabled', the
         alarm will be cleared.

         Once written, the change to this parameter will take immediate
         effect.  However, in order for the change to persist through
         subsequent reboots or power cycles, the change must be saved via
         the apexSaveConfig parameter.

         @Config(config=yes, reboot=no)
         @Save(apexSaveConfig, value=2)
         @File(config.ini, type='ini')
        "
::= { apexConfAlarmEnable 8001 }

apexEnableGbeLossOfPhysicalInput OBJECT-TYPE
    SYNTAX EnableDisableTYPE
    MAX-ACCESS read-write
    STATUS current
    DESCRIPTION
        "This setting enables or disables apexAlarmGbeLossOfPhysicalInput.

         When set to 'enabled' the alarm will operate as described.

         When set to 'disabled' the alarm will not be reported or wrapped
         into unitAlarmStatus and the alarm condition will remain 'ok'.
         If the alarm condition is not 'ok' when it is 'disabled', the
         alarm will be cleared.

         Once written, the change to this parameter will take immediate
         effect.  However, in order for the change to persist through
         subsequent reboots or power cycles, the change must be saved via
         the apexSaveConfig parameter.

         @Config(config=yes, reboot=no)
         @Save(apexSaveConfig, value=2)
         @File(config.ini, type='ini')
        "
::= { apexConfAlarmEnable 8020 }

apexEnableGbeBufferFullness OBJECT-TYPE
    SYNTAX EnableDisableTYPE
    MAX-ACCESS read-write
    STATUS current
    DESCRIPTION
        "This setting enables or disables apexAlarmGbeBufferFullness.

         When set to 'enabled' the alarm will operate as described.

         When set to 'disabled' the alarm will not be reported or wrapped
         into unitAlarmStatus and the alarm condition will remain 'ok'.
         If the alarm condition is not 'ok' when it is 'disabled', the
         alarm will be cleared.

         Once written, the change to this parameter will take immediate
         effect.  However, in order for the change to persist through
         subsequent reboots or power cycles, the change must be saved via
         the apexSaveConfig parameter.

         @Config(config=yes, reboot=no)
         @Save(apexSaveConfig, value=2)
         @File(config.ini, type='ini')
        "
::= { apexConfAlarmEnable 8021 }

apexEnableGbeInputStreamHighBitRate OBJECT-TYPE
    SYNTAX EnableDisableTYPE
    MAX-ACCESS read-write
    STATUS current
    DESCRIPTION
        "This setting enables or disables apexAlarmGbeInputStreamHighBitRate.

         When set to 'enabled' the alarm will operate as described.

         When set to 'disabled' the alarm will not be reported or wrapped
         into unitAlarmStatus and the alarm condition will remain 'ok'.
         If the alarm condition is not 'ok' when it is 'disabled', the
         alarm will be cleared.

         Once written, the change to this parameter will take immediate
         effect.  However, in order for the change to persist through
         subsequent reboots or power cycles, the change must be saved via
         the apexSaveConfig parameter.

         @Config(config=yes, reboot=no)
         @Save(apexSaveConfig, value=2)
         @File(config.ini, type='ini')
        "
::= { apexConfAlarmEnable 8022 }

apexEnableGbeInputTsRedundFailover OBJECT-TYPE
    SYNTAX EnableDisableTYPE
    MAX-ACCESS read-write
    STATUS current
    DESCRIPTION
        "This setting enables or disables apexAlarmGbeInputTsRedundFailover.

         When set to 'enabled' the alarm will operate as described.

         When set to 'disabled' the alarm will not be reported or wrapped
         into unitAlarmStatus and the alarm condition will remain 'ok'.
         If the alarm condition is not 'ok' when it is 'disabled', the
         alarm will be cleared.

         Once written, the change to this parameter will take immediate
         effect.  However, in order for the change to persist through
         subsequent reboots or power cycles, the change must be saved via
         the apexSaveConfig parameter.

         @Config(config=yes, reboot=no)
         @Save(apexSaveConfig, value=2)
         @File(config.ini, type='ini')
        "
::= { apexConfAlarmEnable 8023 }

apexEnableServiceInError OBJECT-TYPE
    SYNTAX EnableDisableTYPE
    MAX-ACCESS read-write
    STATUS current
    DESCRIPTION
        "This setting enables or disables apexAlarmServiceInError.

         When set to 'enabled' the alarm will operate as described.

         When set to 'disabled' the alarm will not be reported or wrapped
         into unitAlarmStatus and the alarm condition will remain 'ok'.
         If the alarm condition is not 'ok' when it is 'disabled', the
         alarm will be cleared.

         Once written, the change to this parameter will take immediate
         effect.  However, in order for the change to persist through
         subsequent reboots or power cycles, the change must be saved via
         the apexSaveConfig parameter.

         @Config(config=yes, reboot=no)
         @Save(apexSaveConfig, value=2)
         @File(config.ini, type='ini')
        "
::= { apexConfAlarmEnable 8024 }

apexEnableGbeLossOfInputStream OBJECT-TYPE
    SYNTAX EnableDisableTYPE
    MAX-ACCESS read-write
    STATUS current
    DESCRIPTION
        "This setting enables or disables apexAlarmGbeLossOfInputStream.

         When set to 'enabled' the alarm will operate as described.

         When set to 'disabled' the alarm will not be reported or wrapped
         into unitAlarmStatus and the alarm condition will remain 'ok'.
         If the alarm condition is not 'ok' when it is 'disabled', the
         alarm will be cleared.

         Once written, the change to this parameter will take immediate
         effect.  However, in order for the change to persist through
         subsequent reboots or power cycles, the change must be saved via
         the apexSaveConfig parameter.

         @Config(config=yes, reboot=no)
         @Save(apexSaveConfig, value=2)
         @File(config.ini, type='ini')
        "
::= { apexConfAlarmEnable 8025 }

apexEnableGbeInterfaceRedundFailover OBJECT-TYPE
    SYNTAX EnableDisableTYPE
    MAX-ACCESS read-write
    STATUS current
    DESCRIPTION
        "This setting enables or disables apexAlarmGbeInterfaceRedundFailover.

         When set to 'enabled' the alarm will operate as described.

         When set to 'disabled' the alarm will not be reported or wrapped
         into unitAlarmStatus and the alarm condition will remain 'ok'.
         If the alarm condition is not 'ok' when it is 'disabled', the
         alarm will be cleared.

         Once written, the change to this parameter will take immediate
         effect.  However, in order for the change to persist through
         subsequent reboots or power cycles, the change must be saved via
         the apexSaveConfig parameter.

         @Config(config=yes, reboot=no)
         @Save(apexSaveConfig, value=2)
         @File(config.ini, type='ini')
        "
::= { apexConfAlarmEnable 8027 }

apexEnableServiceInactiveError OBJECT-TYPE
    SYNTAX EnableDisableTYPE
    MAX-ACCESS read-write
    STATUS current
    DESCRIPTION
        "This setting enables or disables apexAlarmServiceInactiveError.

         When set to 'enabled' the alarm will operate as described.

         When set to 'disabled' the alarm will not be reported or wrapped
         into unitAlarmStatus and the alarm condition will remain 'ok'.
         If the alarm condition is not 'ok' when it is 'disabled', the
         alarm will be cleared.

         Once written, the change to this parameter will take immediate
         effect.  However, in order for the change to persist through
         subsequent reboots or power cycles, the change must be saved via
         the apexSaveConfig parameter.

         @Config(config=yes, reboot=no)
         @Save(apexSaveConfig, value=2)
         @File(config.ini, type='ini')
        "
::= { apexConfAlarmEnable 8028 }

apexEnableOutputUtilizationFault OBJECT-TYPE
    SYNTAX EnableDisableTYPE
    MAX-ACCESS read-write
    STATUS current
    DESCRIPTION
        "This setting enables or disables apexAlarmOutputUtilizationFault.

         When set to 'enabled' the alarm will operate as described.

         When set to 'disabled' the alarm will not be reported or wrapped
         into unitAlarmStatus and the alarm condition will remain 'ok'.
         If the alarm condition is not 'ok' when it is 'disabled', the
         alarm will be cleared.

         Once written, the change to this parameter will take immediate
         effect.  However, in order for the change to persist through
         subsequent reboots or power cycles, the change must be saved via
         the apexSaveConfig parameter.

         @Config(config=yes, reboot=no)
         @Save(apexSaveConfig, value=2)
         @File(config.ini, type='ini')
        "
::= { apexConfAlarmEnable 8040 }

apexEnableOutputOverflow OBJECT-TYPE
    SYNTAX EnableDisableTYPE
    MAX-ACCESS read-write
    STATUS current
    DESCRIPTION
        "This setting enables or disables apexAlarmOutputOverflow.

         When set to 'enabled' the alarm will operate as described.

         When set to 'disabled' the alarm will not be reported or wrapped
         into unitAlarmStatus and the alarm condition will remain 'ok'.
         If the alarm condition is not 'ok' when it is 'disabled', the
         alarm will be cleared.

         Once written, the change to this parameter will take immediate
         effect.  However, in order for the change to persist through
         subsequent reboots or power cycles, the change must be saved via
         the apexSaveConfig parameter.

         @Config(config=yes, reboot=no)
         @Save(apexSaveConfig, value=2)
         @File(config.ini, type='ini')
        "
::= { apexConfAlarmEnable 8041 }

apexEnableQamRfPortFault OBJECT-TYPE
    SYNTAX EnableDisableTYPE
    MAX-ACCESS read-write
    STATUS current
    DESCRIPTION
        "This setting enables or disables apexAlarmQamRfPortFault.

         When set to 'enabled' the alarm will operate as described.

         When set to 'disabled' the alarm will not be reported or wrapped
         into unitAlarmStatus and the alarm condition will remain 'ok'.
         If the alarm condition is not 'ok' when it is 'disabled', the
         alarm will be cleared.

         Once written, the change to this parameter will take immediate
         effect.  However, in order for the change to persist through
         subsequent reboots or power cycles, the change must be saved via
         the apexSaveConfig parameter.

         @Config(config=yes, reboot=no)
         @Save(apexSaveConfig, value=2)
         @File(config.ini, type='ini')
        "
::= { apexConfAlarmEnable 8043 }

apexEnableQamChannelFault OBJECT-TYPE
    SYNTAX EnableDisableTYPE
    MAX-ACCESS read-write
    STATUS current
    DESCRIPTION
        "This setting enables or disables apexAlarmQamChannelFault.

         When set to 'enabled' the alarm will operate as described.

         When set to 'disabled' the alarm will not be reported or wrapped
         into unitAlarmStatus and the alarm condition will remain 'ok'.
         If the alarm condition is not 'ok' when it is 'disabled', the
         alarm will be cleared.

         Once written, the change to this parameter will take immediate
         effect.  However, in order for the change to persist through
         subsequent reboots or power cycles, the change must be saved via
         the apexSaveConfig parameter.

         @Config(config=yes, reboot=no)
         @Save(apexSaveConfig, value=2)
         @File(config.ini, type='ini')
        "
::= { apexConfAlarmEnable 8044 }

apexEnableQamBladeRedundFailover OBJECT-TYPE
    SYNTAX EnableDisableTYPE
    MAX-ACCESS read-write
    STATUS current
    DESCRIPTION
        "This setting enables or disables apexAlarmQamBladeRedundFailover.

         When set to 'enabled' the alarm will operate as described.

         When set to 'disabled' the alarm will not be reported or wrapped
         into unitAlarmStatus and the alarm condition will remain 'ok'.
         If the alarm condition is not 'ok' when it is 'disabled', the
         alarm will be cleared.

         Once written, the change to this parameter will take immediate
         effect.  However, in order for the change to persist through
         subsequent reboots or power cycles, the change must be saved via
         the apexSaveConfig parameter.

         @Config(config=yes, reboot=no)
         @Save(apexSaveConfig, value=2)
         @File(config.ini, type='ini')
        "
::= { apexConfAlarmEnable 8045 }

apexEnableQamBladeRedundMismatch OBJECT-TYPE
    SYNTAX EnableDisableTYPE
    MAX-ACCESS read-write
    STATUS current
    DESCRIPTION
        "This setting enables or disables apexAlarmQamBladeRedundMismatch.

         When set to 'enabled' the alarm will operate as described.

         When set to 'disabled' the alarm will not be reported or wrapped
         into unitAlarmStatus and the alarm condition will remain 'ok'.
         If the alarm condition is not 'ok' when it is 'disabled', the
         alarm will be cleared.

         Once written, the change to this parameter will take immediate
         effect.  However, in order for the change to persist through
         subsequent reboots or power cycles, the change must be saved via
         the apexSaveConfig parameter.

         @Config(config=yes, reboot=no)
         @Save(apexSaveConfig, value=2)
         @File(config.ini, type='ini')
        "
::= { apexConfAlarmEnable 8046 }

apexEnableRtspControllerCommFault OBJECT-TYPE
    SYNTAX EnableDisableTYPE
    MAX-ACCESS read-write
    STATUS current
    DESCRIPTION
        "This setting enables or disables apexAlarmRtspControllerCommFault.

         When set to 'enabled' the alarm will operate as described.

         When set to 'disabled' the alarm will not be reported or wrapped
         into unitAlarmStatus and the alarm condition will remain 'ok'.
         If the alarm condition is not 'ok' when it is 'disabled', the
         alarm will be cleared.

         Once written, the change to this parameter will take immediate
         effect.  However, in order for the change to persist through
         subsequent reboots or power cycles, the change must be saved via
         the apexSaveConfig parameter.

         @Config(config=yes, reboot=no)
         @Save(apexSaveConfig, value=2)
         @File(config.ini, type='ini')
        "
::= { apexConfAlarmEnable 8060 }

apexEnableRdsCommFault OBJECT-TYPE
    SYNTAX EnableDisableTYPE
    MAX-ACCESS read-write
    STATUS current
    DESCRIPTION
        "This setting enables or disables apexAlarmRdsCommFault.

         When set to 'enabled' the alarm will operate as described.

         When set to 'disabled' the alarm will not be reported or wrapped
         into unitAlarmStatus and the alarm condition will remain 'ok'.
         If the alarm condition is not 'ok' when it is 'disabled', the
         alarm will be cleared.

         Once written, the change to this parameter will take immediate
         effect.  However, in order for the change to persist through
         subsequent reboots or power cycles, the change must be saved via
         the apexSaveConfig parameter.

         @Config(config=yes, reboot=no)
         @Save(apexSaveConfig, value=2)
         @File(config.ini, type='ini')
        "
::= { apexConfAlarmEnable 8070 }

apexEnableHostModuleRedundFailover OBJECT-TYPE
    SYNTAX EnableDisableTYPE
    MAX-ACCESS read-write
    STATUS current
    DESCRIPTION
        "This setting enables or disables apexAlarmHostModuleRedundFailover.

         When set to 'enabled' the alarm will operate as described.

         When set to 'disabled' the alarm will not be reported or wrapped
         into unitAlarmStatus and the alarm condition will remain 'ok'.
         If the alarm condition is not 'ok' when it is 'disabled', the
         alarm will be cleared.

         Once written, the change to this parameter will take immediate
         effect.  However, in order for the change to persist through
         subsequent reboots or power cycles, the change must be saved via
         the apexSaveConfig parameter.

         @Config(config=yes, reboot=no)
         @Save(apexSaveConfig, value=2)
         @File(config.ini, type='ini')
        "
::= { apexConfAlarmEnable 8080 }

apexEnableHostModuleRedundFault OBJECT-TYPE
    SYNTAX EnableDisableTYPE
    MAX-ACCESS read-write
    STATUS current
    DESCRIPTION
        "This setting enables or disables apexAlarmHostModuleRedundFault.

         When set to 'enabled' the alarm will operate as described.

         When set to 'disabled' the alarm will not be reported or wrapped
         into unitAlarmStatus and the alarm condition will remain 'ok'.
         If the alarm condition is not 'ok' when it is 'disabled', the
         alarm will be cleared.

         Once written, the change to this parameter will take immediate
         effect.  However, in order for the change to persist through
         subsequent reboots or power cycles, the change must be saved via
         the apexSaveConfig parameter.

         @Config(config=yes, reboot=no)
         @Save(apexSaveConfig, value=2)
         @File(config.ini, type='ini')
        "
::= { apexConfAlarmEnable 8081 }

apexEnableDtiSyncLossFault OBJECT-TYPE
    SYNTAX EnableDisableTYPE
    MAX-ACCESS read-write
    STATUS current
    DESCRIPTION
        "This setting enables or disables apexAlarmDtiSyncLossFault.
         When set to 'enabled' the alarm will operate as described.

         When set to 'disabled' the alarm will not be reported or wrapped
         into unitAlarmStatus and the alarm condition will remain 'ok'.
         If the alarm condition is not 'ok' when it is 'disabled', the
         alarm will be cleared.

         Once written, the change to this parameter will take immediate
         effect.  However, in order for the change to persist through
         subsequent reboots or power cycles, the change must be saved via
         the apexSaveConfig parameter.

         @Config(config=yes, reboot=no)
         @Save(apexSaveConfig, value=2)
         @File(config.ini, type='ini')
        "
::= { apexConfAlarmEnable 8090 }

apexEnableDepiControlConnectionFault OBJECT-TYPE
    SYNTAX EnableDisableTYPE
    MAX-ACCESS read-write
    STATUS current
    DESCRIPTION
        "This setting enables or disables apexAlarmDepiControlConnectionFault.

         When set to 'enabled' the alarm will operate as described.

         When set to 'disabled' the alarm will not be reported or wrapped
         into unitAlarmStatus and the alarm condition will remain 'ok'.
         If the alarm condition is not 'ok' when it is 'disabled', the
         alarm will be cleared.

         Once written, the change to this parameter will take immediate
         effect.  However, in order for the change to persist through
         subsequent reboots or power cycles, the change must be saved via
         the apexSaveConfig parameter.

         @Config(config=yes, reboot=no)
         @Save(apexSaveConfig, value=2)
         @File(config.ini, type='ini')
        "
::= { apexConfAlarmEnable 8091 }


-- ------------------------------------------------------------------------------
--
-- apexConfAlarmClear
--

apexClearInvalidConfigData OBJECT-TYPE
    SYNTAX ClearAlarmTYPE
    MAX-ACCESS read-write
    STATUS current
    DESCRIPTION
        "Setting to 'clearAlarm' clears the apexAlarmInvalidConfigData.

         The APEX will set this parameter back to 'clearAlarmNotInProgress'
         after clearing the alarm.

         Once written, the change to this parameter will take immediate effect.

         @Config(config=no, reboot=no)
        "
::= { apexConfAlarmClear 8001 }

apexClearDepiControlConnectionFault OBJECT-TYPE
    SYNTAX ClearAlarmTYPE
    MAX-ACCESS read-write
    STATUS current
    DESCRIPTION
        "Setting to 'clearAlarm' clears the apexAlarmDepiControlConnectionFault.

         The APEX will set this parameter back to 'clearAlarmNotInProgress'
         after clearing the alarm.

         Once written, the change to this parameter will take immediate effect.

         @Config(config=no, reboot=no)
        "
::= { apexConfAlarmClear 8002 }


-- ------------------------------------------------------------------------------
--
-- apexLogs
--

-- ------------------------------------------------------------------------------
--
-- apexHwEventTable
--

apexHwEventTable OBJECT-TYPE
    SYNTAX SEQUENCE OF ApexHwEventEntry
    MAX-ACCESS not-accessible
    STATUS current
    DESCRIPTION
        "Table of Hardware Events that have occurred.
         Maximum of 300 events will be recorded.
        "
::= { apexLogs 1 }

apexHwEventEntry OBJECT-TYPE
    SYNTAX ApexHwEventEntry
    MAX-ACCESS not-accessible
    STATUS current
    DESCRIPTION
        "Hardware Event Table Entry."
    INDEX { apexHwEventIndex }
::= { apexHwEventTable 1 }

ApexHwEventEntry ::= SEQUENCE
    {
     apexHwEventIndex          Integer32,
     apexHwEventTimeLogged     Integer32,
     apexHwEventAlarmCode      Integer32,
     apexHwEventAlarmSeverity  INTEGER,     
     apexHwEventDescription    DisplayString
    }

apexHwEventIndex OBJECT-TYPE
    SYNTAX Integer32(0..300)
    MAX-ACCESS not-accessible
    STATUS current
    DESCRIPTION
        "Index to HW Event table entry."
::= { apexHwEventEntry 1 }

apexHwEventTimeLogged OBJECT-TYPE
    SYNTAX Integer32
    MAX-ACCESS read-only
    STATUS current
    DESCRIPTION
        "Time in GPS seconds (apexSystemTime) that this event was logged.
        "
::= { apexHwEventEntry 2 }

apexHwEventAlarmCode OBJECT-TYPE
    SYNTAX Integer32
    MAX-ACCESS read-only
    STATUS current
    DESCRIPTION
        "Last number of alarm OID.  Can be one of the following:
               0 Indicates event is informational and may or may not cause an alarm.
            8000 apexAlarmHardwareFault
            8002 apexAlarmTemperatureFault
            8003 apexAlarmFanFault
            8004 apexAlarmPowerSupplyFault
            8005 apexAlarmFanModuleFault
            8006 apexAlarmHostModuleFault
            8007 apexAlarmFrontPanelModuleFault
            8008 apexAlarmRfSwitchModuleFault
            8009 apexAlarm10GbeModuleFault
            8010 apexAlarmDtiModuleFault
            8025 apexAlarmGbeLossOfInputStream
            8042 apexAlarmQamBladeFault
            8043 apexAlarmQamRfPortFault
            8044 apexAlarmQamChannelFault
            8045 apexAlarmQamBladeRedundFailover
            8046 apexAlarmQamBladeRedundMismatch

         More details about the error can be found in apexHwEventDescription.
        "
::= { apexHwEventEntry 3 }

apexHwEventAlarmSeverity OBJECT-TYPE
    SYNTAX INTEGER
        {
         ok(1),
         indeterminate(2),
         warning(3),
         minor(4),
         major(5),
         critical(6)
        }
    MAX-ACCESS read-only
    STATUS current
    DESCRIPTION
        "Alarm severity level of this event.
        "
::= { apexHwEventEntry 4 }

apexHwEventDescription OBJECT-TYPE
    SYNTAX DisplayString
    MAX-ACCESS read-only
    STATUS current
    DESCRIPTION
        "Text description of the event."
::= { apexHwEventEntry 5 }


-- ------------------------------------------------------------------------------
--
-- apexInvalidConfigDataTable
--

apexInvalidConfigDataTable OBJECT-TYPE
    SYNTAX SEQUENCE OF ApexInvalidConfigDataEntry
    MAX-ACCESS not-accessible
    STATUS current
    DESCRIPTION
        "Table of Invalid Initialization Data Errors.
         Maximum of 300 errors will be recorded.
        "
::= { apexLogs 2 }

apexInvalidConfigDataEntry OBJECT-TYPE
    SYNTAX ApexInvalidConfigDataEntry
    MAX-ACCESS not-accessible
    STATUS current
    DESCRIPTION
        "Invalid Initialization Data Table Entry."
    INDEX { apexInvalidConfigDataIndex }
::= { apexInvalidConfigDataTable 1 }

ApexInvalidConfigDataEntry ::= SEQUENCE
    {
     apexInvalidConfigDataIndex       Integer32,
     apexInvalidConfigDataTimeLogged  Integer32,
     apexInvalidConfigDataDescription DisplayString
    }

apexInvalidConfigDataIndex OBJECT-TYPE
    SYNTAX Integer32(0..300)
    MAX-ACCESS not-accessible
    STATUS current
    DESCRIPTION
        "Index to Invalid Initialization Data table entry."
::= { apexInvalidConfigDataEntry 1 }

apexInvalidConfigDataTimeLogged OBJECT-TYPE
    SYNTAX Integer32
    MAX-ACCESS read-only
    STATUS current
    DESCRIPTION
        "Time in GPS seconds (apexSystemTime) that this event was logged."
::= { apexInvalidConfigDataEntry 2 }

apexInvalidConfigDataDescription OBJECT-TYPE
    SYNTAX DisplayString
    MAX-ACCESS read-only
    STATUS current
    DESCRIPTION
        "Text string describing the data error."
::= { apexInvalidConfigDataEntry 3 }


-- ------------------------------------------------------------------------------
--
-- apexOutputTsEventTable
--

apexOutputTsEventTable OBJECT-TYPE
    SYNTAX SEQUENCE OF ApexOutputTsEventEntry
    MAX-ACCESS not-accessible
    STATUS current
    DESCRIPTION
        "Table of Output Stream events that have occurred.

         Maximum of 300 events will be recorded for each slot.
        "
::= { apexLogs 3 }

apexOutputTsEventEntry OBJECT-TYPE
    SYNTAX ApexOutputTsEventEntry
    MAX-ACCESS not-accessible
    STATUS current
    DESCRIPTION
        "Output Stream Error Table Entry."
    INDEX { apexOutputTsEventBladeNum, apexOutputTsEventIndex }
::= { apexOutputTsEventTable 1 }

ApexOutputTsEventEntry ::= SEQUENCE
    {
     apexOutputTsEventBladeNum          Integer32,
     apexOutputTsEventIndex             Integer32,
     apexOutputTsEventTimeLogged        Integer32,
     apexOutputTsEventAlarmCode         Integer32,
     apexOutputTsEventAlarmSeverity     INTEGER,
     apexOutputTsEventOutputTsNum       Integer32,
     apexOutputTsEventCurRate           Integer32,
     apexOutputTsEventAvgRate           Integer32,
     apexOutputTsEventMinRate           Integer32,
     apexOutputTsEventPeakRate          Integer32,
     apexOutputTsEventDescription       DisplayString
    }

apexOutputTsEventBladeNum OBJECT-TYPE
    SYNTAX Integer32(1..8)
    MAX-ACCESS not-accessible
    STATUS current
    DESCRIPTION
        "Blade Number."
::= { apexOutputTsEventEntry 1 }

apexOutputTsEventIndex OBJECT-TYPE
    SYNTAX Integer32(1..300)
    MAX-ACCESS not-accessible
    STATUS current
    DESCRIPTION
        "Index to Output Stream Error table.
        "
::= { apexOutputTsEventEntry 2 }

apexOutputTsEventTimeLogged OBJECT-TYPE
    SYNTAX Integer32
    MAX-ACCESS read-only
    STATUS current
    DESCRIPTION
        "Time in GPS seconds (apexSystemTime) that this event was logged.
        "
::= { apexOutputTsEventEntry 3 }

apexOutputTsEventAlarmCode OBJECT-TYPE
    SYNTAX Integer32
    MAX-ACCESS read-only
    STATUS current
    DESCRIPTION
        "Last number of alarm OID.  Can be one of the following:
               0 Indicates event is informational and may or may not cause an alarm.
            8040 apexAlarmOutputUtilizationFault
            8041 apexAlarmOutputOverflow

         More details about the error can be found in apexOutputTsEventDescription.
        "
::= { apexOutputTsEventEntry 4 }

apexOutputTsEventAlarmSeverity OBJECT-TYPE
    SYNTAX INTEGER
        {
         ok(1),
         indeterminate(2),
         warning(3),
         minor(4),
         major(5),
         critical(6)
        }
    MAX-ACCESS read-only
    STATUS current
    DESCRIPTION
        "Alarm severity level of this event.
        "
::= { apexOutputTsEventEntry 5 }

apexOutputTsEventOutputTsNum OBJECT-TYPE
    SYNTAX Integer32 (0..256)
    MAX-ACCESS read-only
    STATUS current
    DESCRIPTION
        "The number of the output transport stream for this event.
        "
::= { apexOutputTsEventEntry 6 }

apexOutputTsEventCurRate OBJECT-TYPE
    SYNTAX Integer32
    MAX-ACCESS read-only
    STATUS current
    DESCRIPTION
        "Value of apexOutputTsUtilizCurRate when event occurred.
        "
::= { apexOutputTsEventEntry 7 }

apexOutputTsEventAvgRate OBJECT-TYPE
    SYNTAX Integer32
    MAX-ACCESS read-only
    STATUS current
    DESCRIPTION
        "Value of apexOutputTsUtilizAvgRate when event occurred.
        "
::= { apexOutputTsEventEntry 8 }

apexOutputTsEventMinRate OBJECT-TYPE
    SYNTAX Integer32
    MAX-ACCESS read-only
    STATUS current
    DESCRIPTION
        "Value of apexOutputTsUtilizMinRate when event occurred.
        "
::= { apexOutputTsEventEntry 9 }

apexOutputTsEventPeakRate OBJECT-TYPE
    SYNTAX Integer32
    MAX-ACCESS read-only
    STATUS current
    DESCRIPTION
        "Value of apexOutputTsUtilizPeakRate when event occurred.
        "
::= { apexOutputTsEventEntry 10 }

apexOutputTsEventDescription OBJECT-TYPE
    SYNTAX DisplayString
    MAX-ACCESS read-only
    STATUS current
    DESCRIPTION
        "Text description of the event.
         Maximum length is 128 characters.
        "
::= { apexOutputTsEventEntry 11 }


-- ------------------------------------------------------------------------------
--
-- apexGbeInputTsEventTable
--

apexGbeInputTsEventTable OBJECT-TYPE
    SYNTAX SEQUENCE OF ApexGbeInputTsEventEntry
    MAX-ACCESS not-accessible
    STATUS current
    DESCRIPTION
        "Table of Gigabit Ethernet Input Transport Stream Events that have occurred.
         Maximum of 300 events will be recorded.
        "
::= { apexLogs 4 }

apexGbeInputTsEventEntry OBJECT-TYPE
    SYNTAX ApexGbeInputTsEventEntry
    MAX-ACCESS not-accessible
    STATUS current
    DESCRIPTION
        "Gigabit Ethernet Input Transport Stream Event Table Entry."
    INDEX { apexGbeInputTsEventIndex }
::= { apexGbeInputTsEventTable 1 }

ApexGbeInputTsEventEntry ::= SEQUENCE
    {
     apexGbeInputTsEventIndex               Integer32,
     apexGbeInputTsEventTimeLogged          Integer32,
     apexGbeInputTsEventAlarmCode           Integer32,
     apexGbeInputTsEventAlarmSeverity       INTEGER,
     apexGbeInputTsEventRedundantConfig     INTEGER,
     apexGbeInputTsEventGbeInterface        Integer32,
     apexGbeInputTsEventUdpPort             Integer32,
     apexGbeInputTsEventDestinationIp       IpAddress,
     apexGbeInputTsEventSourceIp            IpAddress,
     apexGbeInputTsEventInputTsState        InputTsStateTYPE,     
     apexGbeInputTsEventCurStreamCount      Counter32,
     apexGbeInputTsEventCurDataCount        Counter32,    
     apexGbeInputTsEventDescription         DisplayString
    }

apexGbeInputTsEventIndex OBJECT-TYPE
    SYNTAX Integer32(0..300)
    MAX-ACCESS not-accessible
    STATUS current
    DESCRIPTION
        "Index to Gigabit Ethernet Input Transport Stream Event table.
        "
::= { apexGbeInputTsEventEntry 1 }

apexGbeInputTsEventTimeLogged OBJECT-TYPE
    SYNTAX Integer32
    MAX-ACCESS read-only
    STATUS current
    DESCRIPTION
        "Time in GPS seconds (apexSystemTime) that this event was logged.
        "
::= { apexGbeInputTsEventEntry 2 }

apexGbeInputTsEventAlarmCode OBJECT-TYPE
    SYNTAX Integer32
    MAX-ACCESS read-only
    STATUS current
    DESCRIPTION
        "Last number of alarm OID.  Can be one of the following:
               0 Indicates event is informational and may or may not cause an alarm.
            8022 apexAlarmGbeInputStreamHighBitRate
            8023 apexAlarmGbeInputTsRedundFailover
            8025 apexAlarmGbeLossOfInputStream

         More details about the error may be found in apexGbeInputTsEventDescription.
        "
::= { apexGbeInputTsEventEntry 3 }

apexGbeInputTsEventAlarmSeverity OBJECT-TYPE
    SYNTAX INTEGER
        {
         ok(1),
         indeterminate(2),
         warning(3),
         minor(4),
         major(5),
         critical(6)
        }
    MAX-ACCESS read-only
    STATUS current
    DESCRIPTION
        "Alarm severity level of this event.
        "
::= { apexGbeInputTsEventEntry 4 }

apexGbeInputTsEventRedundantConfig OBJECT-TYPE
    SYNTAX INTEGER
        {
         notApplicable (0),
         primary       (1),
         secondary     (2)
        }
    MAX-ACCESS read-only
    STATUS current
    DESCRIPTION
        "Indicates whether this input transport stream was
         configured as a primary or secondary at the time of the event.
        "
::= { apexGbeInputTsEventEntry 5 }

apexGbeInputTsEventGbeInterface OBJECT-TYPE
    SYNTAX Integer32
    MAX-ACCESS read-only
    STATUS current
    DESCRIPTION
        "Value of apexInputTsStatPriInputInterface or apexInputTsStatSecInputInterface
         at the time of the event.
        "
::= { apexGbeInputTsEventEntry 6 }

apexGbeInputTsEventUdpPort OBJECT-TYPE
    SYNTAX Integer32
    MAX-ACCESS read-only
    STATUS current
    DESCRIPTION
        "Value of apexInputTsStatPriInputUdp or apexInputTsStatSecInputUdp
         at the time of the event.
        "
::= { apexGbeInputTsEventEntry 7 }

apexGbeInputTsEventDestinationIp OBJECT-TYPE
    SYNTAX IpAddress
    MAX-ACCESS read-only
    STATUS current
    DESCRIPTION
        "Value of apexGbeStatusInputTsStatPriInputDestinationIp or
         apexGbeStatusInputTsStatSecInputDestinationIp
         at the time of the event.
        "
::= { apexGbeInputTsEventEntry 8 }

apexGbeInputTsEventSourceIp OBJECT-TYPE
    SYNTAX IpAddress
    MAX-ACCESS read-only
    STATUS current
    DESCRIPTION
        "Value of apexInputTsStatPriInputSourceIp or apexInputTsStatSecInputSourceIp
         at the time of the event.
        "
::= { apexGbeInputTsEventEntry 9 }

apexGbeInputTsEventInputTsState OBJECT-TYPE
    SYNTAX InputTsStateTYPE
    MAX-ACCESS read-only
    STATUS current
    DESCRIPTION
        "Value of apexInputTsStatPriState or apexInputTsStatSecState
         at the time of the event. For threshold or fail over events, the
         state reported is always the Primary input stream state.
        "
::= { apexGbeInputTsEventEntry 10 }

apexGbeInputTsEventCurStreamCount OBJECT-TYPE
    SYNTAX Counter32
    MAX-ACCESS read-only
    STATUS current
    DESCRIPTION
        "Current in use stream input stream Packet Count at the time of the event.
         This is the number of packets received, including Nulls, during the
         sample period defined in apexGbeInputTsEventSamplingPeriod.
        "
::= { apexGbeInputTsEventEntry 11 }

apexGbeInputTsEventCurDataCount OBJECT-TYPE
    SYNTAX Counter32
    MAX-ACCESS read-only
    STATUS current
    DESCRIPTION
        "Current in use stream input data Packet Count at the time of the event.
         This is the number of data packets received (non-Nulls), during the
         sample period defined in apexGbeInputTsEventSamplingPeriod.
        "
::= { apexGbeInputTsEventEntry 12 }

apexGbeInputTsEventDescription OBJECT-TYPE
    SYNTAX DisplayString
    MAX-ACCESS read-only
    STATUS current
    DESCRIPTION
        "Text description of the event.
         Maximum length is 128 characters.
        "
::= { apexGbeInputTsEventEntry 13 }


-- ------------------------------------------------------------------------------
--
-- apexRtspEventTable
--

apexRtspEventTable OBJECT-TYPE
    SYNTAX SEQUENCE OF ApexRtspEventEntry
    MAX-ACCESS not-accessible
    STATUS current
    DESCRIPTION
        "Table of RTSP Events that have occurred.
         Maximum of 300 events will be recorded.
        "
::= { apexLogs 5 }

apexRtspEventEntry OBJECT-TYPE
    SYNTAX ApexRtspEventEntry
    MAX-ACCESS not-accessible
    STATUS current
    DESCRIPTION
        "RTSP Event Table Entry."
    INDEX { apexRtspEventIndex }
::= { apexRtspEventTable 1 }

ApexRtspEventEntry ::= SEQUENCE
    {
     apexRtspEventIndex             Integer32,
     apexRtspEventTimeLogged        Integer32,
     apexRtspEventControllerIp      IpAddress,
     apexRtspEventSessionCount      Integer32,
     apexRtspEventSourceDescription DisplayString,
     apexRtspEventDescription       DisplayString
    }

apexRtspEventIndex OBJECT-TYPE
    SYNTAX Integer32(0..300)
    MAX-ACCESS not-accessible
    STATUS current
    DESCRIPTION
        "Index to RTSP Event table entry."
::= { apexRtspEventEntry 1 }

apexRtspEventTimeLogged OBJECT-TYPE
    SYNTAX Integer32
    MAX-ACCESS read-only
    STATUS current
    DESCRIPTION
        "Time in GPS seconds (apexSystemTime) that this event was logged.
        "
::= { apexRtspEventEntry 2 }

apexRtspEventControllerIp OBJECT-TYPE
    SYNTAX IpAddress
    MAX-ACCESS read-only
    STATUS current
    DESCRIPTION
        "IP address of the RTSP Controller associated with this event.  Value
         will be zero if the event is not associated with a specific controller.
         Refer to apexRtspEventSourceDescription for the source of the event.
        "
::= { apexRtspEventEntry 3 }

apexRtspEventSessionCount OBJECT-TYPE
    SYNTAX Integer32
    MAX-ACCESS read-only
    STATUS current
    DESCRIPTION
        "Number of active sessions for the RTSP Controller associated with this
         event.  Value will be total count of all sessions for all controllers
         if the event is not associated with a specific controller.  Refer
         to apexRtspEventSourceDescription for the source of the event.
        "
::= { apexRtspEventEntry 4 }

apexRtspEventSourceDescription OBJECT-TYPE
    SYNTAX DisplayString
    MAX-ACCESS read-only
    STATUS current
    DESCRIPTION
        "Text description of the source of the event.  May indicate a controller
         identifier or an APEX application process.
        "
::= { apexRtspEventEntry 5 }

apexRtspEventDescription OBJECT-TYPE
    SYNTAX DisplayString
    MAX-ACCESS read-only
    STATUS current
    DESCRIPTION
        "Text description of the event.
        "
::= { apexRtspEventEntry 6 }


-- ------------------------------------------------------------------------------
--
--  apexMappingErrorTable
--

apexMappingErrorTable OBJECT-TYPE
    SYNTAX SEQUENCE OF ApexMappingErrorEntry
    MAX-ACCESS not-accessible
    STATUS current
    DESCRIPTION
        "Table of program, ancillary PID, and stream pass through mapping errors
         that have occurred. 
         Maximum of 300 error events will be recorded for each slot.
        "
::= { apexLogs 6 }

apexMappingErrorEntry OBJECT-TYPE
    SYNTAX ApexMappingErrorEntry
    MAX-ACCESS not-accessible
    STATUS current
    DESCRIPTION
        "Program, PID, Stream Pass Through Error Table Entry."
    INDEX { apexMappingErrorIndex }
::= { apexMappingErrorTable 1 }

ApexMappingErrorEntry ::= SEQUENCE
    {
     apexMappingErrorIndex              Integer32,
     apexMappingErrorTimeLogged         Integer32,
     apexMappingErrorCode               Integer32,
     apexMappingErrorMappingType        INTEGER,
     apexMappingErrorInputInterface     Integer32,
     apexMappingErrorUdpPort            Integer32,
     apexMappingErrorMulticastIp        IpAddress,
     apexMappingErrorSourceIp           IpAddress,
     apexMappingErrorInputProgramPid    Integer32,
     apexMappingErrorOutputProgramPid   Integer32,
     apexMappingErrorOutputOpMode       INTEGER,
     apexMappingErrorOutputTsNum        Integer32,
     apexMappingErrorBladeNum           Integer32,
     apexMappingErrorSecInputInterface  Integer32,
     apexMappingErrorSecUdpPort         Integer32,
     apexMappingErrorSecMulticastIp     IpAddress,
     apexMappingErrorSecSourceIp        IpAddress
    }

apexMappingErrorIndex OBJECT-TYPE
    SYNTAX Integer32(1..300)
    MAX-ACCESS not-accessible
    STATUS current
    DESCRIPTION
        "Index to Program, PID, Stream Pass Through Error table.
        "
::= { apexMappingErrorEntry 1 }

apexMappingErrorTimeLogged OBJECT-TYPE
    SYNTAX Integer32
    MAX-ACCESS read-only
    STATUS current
    DESCRIPTION
        "Time in GPS seconds (apexSystemTime) that this error was logged.
        "
::= { apexMappingErrorEntry 2 }

apexMappingErrorCode OBJECT-TYPE
    SYNTAX Integer32
    MAX-ACCESS read-only
    STATUS current
    DESCRIPTION
        "Error code for this mapping error. 0 indicates no error.
        "
::= { apexMappingErrorEntry 3 }

apexMappingErrorMappingType OBJECT-TYPE
    SYNTAX INTEGER
        {
         notApplicable  (0),
         program        (1),
         ancillaryPid   (2),
         streamPassthru (3),
         docsis         (4)
        }
    MAX-ACCESS read-only
    STATUS current
    DESCRIPTION
        "Type of mapping (program, ancillary PID, DOCSIS or stream pass through).
        "
::= { apexMappingErrorEntry 4 }

apexMappingErrorInputInterface OBJECT-TYPE
    SYNTAX Integer32
    MAX-ACCESS read-only
    STATUS current
    DESCRIPTION
        "Interface port number of the primary input interface.
        "
::= { apexMappingErrorEntry 5 }

apexMappingErrorUdpPort OBJECT-TYPE
    SYNTAX Integer32
    MAX-ACCESS read-only
    STATUS current
    DESCRIPTION
        "Input UDP Port for primary input.
        "
::= { apexMappingErrorEntry 6 }

apexMappingErrorMulticastIp OBJECT-TYPE
    SYNTAX IpAddress
    MAX-ACCESS read-only
    STATUS current
    DESCRIPTION
        "The Multicast receive IP address for primary input.
        "
::= { apexMappingErrorEntry 7 }

apexMappingErrorSourceIp OBJECT-TYPE
    SYNTAX IpAddress
    MAX-ACCESS read-only
    STATUS current
    DESCRIPTION
        "This is the IGMP v3 Source IP address of the source device for the primary input.
        "
::= { apexMappingErrorEntry 8 }

apexMappingErrorInputProgramPid OBJECT-TYPE
    SYNTAX Integer32
    MAX-ACCESS read-only
    STATUS current
    DESCRIPTION
        "For program mappings, this is the input program number of the program being mapped.
         For ancillary PID mappings, this is the input PID number being mapped.
         For stream pass through mappings, this field is not used and is set to 0.
        "
::= { apexMappingErrorEntry 9 }

apexMappingErrorOutputProgramPid OBJECT-TYPE
    SYNTAX Integer32
    MAX-ACCESS read-only
    STATUS current
    DESCRIPTION
        "For program mappings, this is the output program number of the program being mapped.
         For ancillary PID mappings, this is the output PID number being mapped.
         For stream pass through mappings, this field is not used and is set to 0.
        "
::= { apexMappingErrorEntry 10 }

apexMappingErrorOutputOpMode OBJECT-TYPE
    SYNTAX INTEGER
        {
         notInUse       (0),
         sessionControl (1),
         manualRouting  (2)
        }
    MAX-ACCESS read-only
    STATUS current
    DESCRIPTION
        "Operating mode of the output transport stream for this mapping.
        "
::= { apexMappingErrorEntry 11 }

apexMappingErrorOutputTsNum OBJECT-TYPE
    SYNTAX Integer32 (0..256)
    MAX-ACCESS read-only
    STATUS current
    DESCRIPTION
        "The number of the output transport stream for this mapping error.
        "
::= { apexMappingErrorEntry 12 }

apexMappingErrorBladeNum OBJECT-TYPE
    SYNTAX Integer32(1..8)
    MAX-ACCESS read-only
    STATUS current
    DESCRIPTION
        "Blade number for this mapping error."
::= { apexMappingErrorEntry 13 }

apexMappingErrorSecInputInterface OBJECT-TYPE
    SYNTAX Integer32
    MAX-ACCESS read-only
    STATUS current
    DESCRIPTION
        "Interface port number of the secondary input interface.
         An interface number of 0 indicates no secondary input.
        "
::= { apexMappingErrorEntry 14 }

apexMappingErrorSecUdpPort OBJECT-TYPE
    SYNTAX Integer32
    MAX-ACCESS read-only
    STATUS current
    DESCRIPTION
        "Input UDP Port for secondary input.
        "
::= { apexMappingErrorEntry 15 }

apexMappingErrorSecMulticastIp OBJECT-TYPE
    SYNTAX IpAddress
    MAX-ACCESS read-only
    STATUS current
    DESCRIPTION
        "The Multicast receive IP address for secondary input.
        "
::= { apexMappingErrorEntry 16 }

apexMappingErrorSecSourceIp OBJECT-TYPE
    SYNTAX IpAddress
    MAX-ACCESS read-only
    STATUS current
    DESCRIPTION
        "This is the IGMP v3 Source IP address of the source device for the secondary input.
        "
::= { apexMappingErrorEntry 17 }


-- ------------------------------------------------------------------------------
--
--  apexHostModuleRedundEventTable
--

apexHostModuleRedundEventTable OBJECT-TYPE
    SYNTAX SEQUENCE OF ApexHostModuleRedundEventEntry
    MAX-ACCESS not-accessible
    STATUS current
    DESCRIPTION
        "Table of Host Module Redundancy Events that have occurred.
         Maximum of 300 events will be recorded.
        "
::= { apexLogs 7 }

apexHostModuleRedundEventEntry OBJECT-TYPE
    SYNTAX ApexHostModuleRedundEventEntry
    MAX-ACCESS not-accessible
    STATUS current
    DESCRIPTION
        "Host Module Redundancy Event Entry.
        "
    INDEX { apexHostModuleRedundEventIndex }
::= { apexHostModuleRedundEventTable 1 }

ApexHostModuleRedundEventEntry ::= SEQUENCE
    {
     apexHostModuleRedundEventIndex        Integer32,
     apexHostModuleRedundEventTimeLogged   Integer32,
     apexHostModuleRedundEventSeverity     INTEGER,
     apexHostModuleRedundEventCode         Integer32,
     apexHostModuleRedundEventData         Integer32,
     apexHostModuleRedundEventDescription  DisplayString
    }

apexHostModuleRedundEventIndex OBJECT-TYPE
    SYNTAX Integer32(1..300)
    MAX-ACCESS not-accessible
    STATUS current
    DESCRIPTION
        "Index to Host Module Redundancy table.
        "
::= { apexHostModuleRedundEventEntry 1 }

apexHostModuleRedundEventTimeLogged OBJECT-TYPE
    SYNTAX Integer32
    MAX-ACCESS read-only
    STATUS current
    DESCRIPTION
        "Time in GPS seconds (apexSystemTime) that this event was logged.
        "
::= { apexHostModuleRedundEventEntry 2 }

apexHostModuleRedundEventSeverity OBJECT-TYPE
    SYNTAX INTEGER
        {
         ok(1),
         indeterminate(2),
         warning(3),
         minor(4),
         major(5),
         critical(6)
        }
    MAX-ACCESS read-only
    STATUS current
    DESCRIPTION
        "Severity level of this event.
        "
::= { apexHostModuleRedundEventEntry 3 }

apexHostModuleRedundEventCode OBJECT-TYPE
    SYNTAX Integer32
    MAX-ACCESS read-only
    STATUS current
    DESCRIPTION
        "Code for this event.
        "
::= { apexHostModuleRedundEventEntry 4 }

apexHostModuleRedundEventData OBJECT-TYPE
    SYNTAX Integer32
    MAX-ACCESS read-only
    STATUS current
    DESCRIPTION
        "Additional integer data for this event:
        
        Byte 0 (LSB): Slot ID (1 or 2)
        Byte 1: Redundancy Role. 0 Unknown, 1 Active, 2 Standby
        "
::= { apexHostModuleRedundEventEntry 5 }

apexHostModuleRedundEventDescription OBJECT-TYPE
    SYNTAX DisplayString
    MAX-ACCESS read-only
    STATUS current
    DESCRIPTION
        "Text description of the event
        "
::= { apexHostModuleRedundEventEntry 6 }


-- ------------------------------------------------------------------------------
--
--  apexDepiEventTable
--

apexDepiEventTable OBJECT-TYPE
    SYNTAX SEQUENCE OF ApexDepiEventEntry
    MAX-ACCESS not-accessible
    STATUS current
    DESCRIPTION
        "Table of Depi Events that have occurred.
         Maximum of 300 events will be recorded.
        "
::= { apexLogs 8 }

apexDepiEventEntry OBJECT-TYPE
    SYNTAX ApexDepiEventEntry
    MAX-ACCESS not-accessible
    STATUS current
    DESCRIPTION
        "Depi Event Entry.
        "
    INDEX { apexDepiEventIndex }
::= { apexDepiEventTable 1 }

ApexDepiEventEntry ::= SEQUENCE
    {
     apexDepiEventIndex        Integer32,
     apexDepiEventTimeLogged   Integer32,
     apexDepiEventCode         Integer32,
     apexDepiEventConnId       Integer32,
     apexDepiEventSessionId    Integer32,
     apexDepiEventDescription  DisplayString
    }

apexDepiEventIndex OBJECT-TYPE
    SYNTAX Integer32(1..300)
    MAX-ACCESS not-accessible
    STATUS current
    DESCRIPTION
        "Index to Host Module Redundancy table.
        "
::= { apexDepiEventEntry 1 }

apexDepiEventTimeLogged OBJECT-TYPE
    SYNTAX Integer32
    MAX-ACCESS read-only
    STATUS current
    DESCRIPTION
        "Time in GPS seconds (apexSystemTime) that this event was logged.
        "
::= { apexDepiEventEntry 2 }

apexDepiEventCode OBJECT-TYPE
    SYNTAX Integer32
    MAX-ACCESS read-only
    STATUS current
    DESCRIPTION
        "Code for this event.
        "
::= { apexDepiEventEntry 3 }

apexDepiEventConnId OBJECT-TYPE
    SYNTAX Integer32
    MAX-ACCESS read-only
    STATUS current
    DESCRIPTION
        "Depi connection affected (if applicable)
        "
::= { apexDepiEventEntry 4 }

apexDepiEventSessionId OBJECT-TYPE
    SYNTAX Integer32
    MAX-ACCESS read-only
    STATUS current
    DESCRIPTION
        "Depi session affected (if applicable)
        "
::= { apexDepiEventEntry 5 }

apexDepiEventDescription OBJECT-TYPE
    SYNTAX DisplayString
    MAX-ACCESS read-only
    STATUS current
    DESCRIPTION
        "Text description of the event
        "
::= { apexDepiEventEntry 6 }


-- ------------------------------------------------------------------------------
--
-- apexTraps
--

-- ------------------------------------------------------------------------------
--
-- BCS Traps
--
-- Objects are commonly defined but ENTERPRISE is APEX specific.
-- Trap ID starts at 1.  Trap ID 1 and 2 are not issued by the APEX.
--

trapConfigurationChangeInteger NOTIFICATION-TYPE
    OBJECTS
    {
    trapIdentifier,
    trapSequenceId,
    trapNetworkElemModelNumber,
    trapNetworkElemSerialNum,
    trapPerceivedSeverity,
    trapNetworkElemOperState,
    trapNetworkElemAlarmStatus,
    trapNetworkElemAdminState,
    trapNetworkElemAvailStatus,
    trapText,
    trapNETrapLastTrapTimeStamp,
    trapChangedObjectId,
    trapChangedValueInteger
    }
    STATUS current
    DESCRIPTION
        "This trap is issued if configuration of a single variable
         with integer type was changed (via ANY interface).
         TrapChangedValueInteger variable may contain current reading
         of that variable.
         trapPerceivedSeverity - 'indeterminate'"
::= { apexTraps 3 }


trapConfigurationChangeDisplayString NOTIFICATION-TYPE
    OBJECTS
    {
    trapIdentifier,
    trapSequenceId,
    trapNetworkElemModelNumber,
    trapNetworkElemSerialNum,
    trapPerceivedSeverity,
    trapNetworkElemOperState,
    trapNetworkElemAlarmStatus,
    trapNetworkElemAdminState,
    trapNetworkElemAvailStatus,
    trapText,
    trapNETrapLastTrapTimeStamp,
    trapChangedObjectId,
    trapChangedValueDisplayString
    }
    STATUS current
    DESCRIPTION
        "This trap is issued if configuration of a single variable
         with DisplayString type was changed (via ANY interface).
         TrapChangedValueDisplayString variable may contain current
         reading of that variable.
         trapPerceivedSeverity - 'indeterminate'"
::= { apexTraps 4 }


trapConfigurationChangeOID NOTIFICATION-TYPE
    OBJECTS
    {
    trapIdentifier,
    trapSequenceId,
    trapNetworkElemModelNumber,
    trapNetworkElemSerialNum,
    trapPerceivedSeverity,
    trapNetworkElemOperState,
    trapNetworkElemAlarmStatus,
    trapNetworkElemAdminState,
    trapNetworkElemAvailStatus,
    trapText,
    trapNETrapLastTrapTimeStamp,
    trapChangedObjectId,
    trapChangedValueOID
    }
    STATUS current
    DESCRIPTION
        "This trap is issued if configuration of a single variable
         with OID type was changed (via ANY interface).
         TrapChangedValueOID variable may contain current reading
         of that variable.
         trapPerceivedSeverity - 'indeterminate'"
::= { apexTraps 5 }

trapConfigurationChangeIpAddress NOTIFICATION-TYPE
    OBJECTS
    {
    trapIdentifier,
    trapSequenceId,
    trapNetworkElemModelNumber,
    trapNetworkElemSerialNum,
    trapPerceivedSeverity,
    trapNetworkElemOperState,
    trapNetworkElemAlarmStatus,
    trapNetworkElemAdminState,
    trapNetworkElemAvailStatus,
    trapText,
    trapNETrapLastTrapTimeStamp,
    trapChangedObjectId,
    trapChangedValueIpAddress
    }
    STATUS current
    DESCRIPTION
        "This trap is issued if configuration of a single variable
         with IpAddress type was changed (via ANY interface).
         TrapChangedValueIpAddress variable may contain current reading
         of that variable.
         trapPerceivedSeverity - 'indeterminate'"
::= { apexTraps 6 }


-- ------------------------------------------------------------------------------
--
-- DNS Traps
--
-- Objects are commonly defined but ENTERPRISE is APEX specific.
-- Trap ID starts at 20.
--

trapConditionNotInList NOTIFICATION-TYPE
    OBJECTS
    {
    trapIdentifier,
    trapSequenceId,
    trapNetworkElemModelNumber,
    trapNetworkElemSerialNum,
    trapPerceivedSeverity,
    trapNetworkElemOperState,
    trapNetworkElemAlarmStatus,
    trapNetworkElemAdminState,
    trapNetworkElemAvailStatus,
    trapText,
    trapNETrapLastTrapTimeStamp,
    trapChangedObjectId,
    trapChangedValueInteger,
    trapAdditionalInfoInteger1,
    trapAdditionalInfoInteger2,
    trapAdditionalInfoInteger3
    }
    STATUS current
    DESCRIPTION
        "This trap is issued if a condition is being cleared and
         it is not in the condition list.
         trapAdditionalInfoInteger1 : Task and Function ID (task
                          and function generates the
                          error condition)
         trapAdditionalInfoInteger2 : Condition number
         trapAdditionalInfoInteger3 : Condition severity"
::= { apexTraps 20 }

trapConditionAlreadyInList NOTIFICATION-TYPE
    OBJECTS
    {
    trapIdentifier,
    trapSequenceId,
    trapNetworkElemModelNumber,
    trapNetworkElemSerialNum,
    trapPerceivedSeverity,
    trapNetworkElemOperState,
    trapNetworkElemAlarmStatus,
    trapNetworkElemAdminState,
    trapNetworkElemAvailStatus,
    trapText,
    trapNETrapLastTrapTimeStamp,
    trapChangedObjectId,
    trapChangedValueInteger,
    trapAdditionalInfoInteger1,
    trapAdditionalInfoInteger2,
    trapAdditionalInfoInteger3
    }
    STATUS current
    DESCRIPTION
        "This trap is issued if a condition is being set and
         it is already in the condition list.
         trapAdditionalInfoInteger1 : Task and Function ID (task
                          and function generates the
                          error condition)
         trapAdditionalInfoInteger2 : Condition number
         trapAdditionalInfoInteger3 : Condition severity"
::= { apexTraps 21 }

trapConditionListFull NOTIFICATION-TYPE
    OBJECTS
    {
    trapIdentifier,
    trapSequenceId,
    trapNetworkElemModelNumber,
    trapNetworkElemSerialNum,
    trapPerceivedSeverity,
    trapNetworkElemOperState,
    trapNetworkElemAlarmStatus,
    trapNetworkElemAdminState,
    trapNetworkElemAvailStatus,
    trapText,
    trapNETrapLastTrapTimeStamp,
    trapChangedObjectId,
    trapChangedValueInteger,
    trapAdditionalInfoInteger1,
    trapAdditionalInfoInteger2,
    trapAdditionalInfoInteger3
    }
    STATUS current
    DESCRIPTION
        "This trap is issued if a condition is being set and
         the condition list is full.
         trapAdditionalInfoInteger1 : Task and Function ID (task
                          and function generates the
                          error condition)
         trapAdditionalInfoInteger2 : Condition number
         trapAdditionalInfoInteger3 : Condition severity"
::= { apexTraps 22 }

trapInvalidCaseInSwitch NOTIFICATION-TYPE
    OBJECTS
    {
    trapIdentifier,
    trapSequenceId,
    trapNetworkElemModelNumber,
    trapNetworkElemSerialNum,
    trapPerceivedSeverity,
    trapNetworkElemOperState,
    trapNetworkElemAlarmStatus,
    trapNetworkElemAdminState,
    trapNetworkElemAvailStatus,
    trapText,
    trapNETrapLastTrapTimeStamp,
    trapChangedObjectId,
    trapChangedValueInteger,
    trapAdditionalInfoInteger1,
    trapAdditionalInfoInteger2,
    trapAdditionalInfoInteger3
    }
    STATUS current
    DESCRIPTION
        "This trap is issued when in a switch statement the
         default case is reached.  The trapAdditionalInfoInteger1
         will contain the task and Function ID.  The
         trapAdditionalInfoInteger2 will contain value of the switch.
         The trapAdditionalInfoInteger3 is not used."
::= { apexTraps 23 }

trapCannotCreateSemaphore NOTIFICATION-TYPE
    OBJECTS
    {
    trapIdentifier,
    trapSequenceId,
    trapNetworkElemModelNumber,
    trapNetworkElemSerialNum,
    trapPerceivedSeverity,
    trapNetworkElemOperState,
    trapNetworkElemAlarmStatus,
    trapNetworkElemAdminState,
    trapNetworkElemAvailStatus,
    trapText,
    trapNETrapLastTrapTimeStamp,
    trapChangedObjectId,
    trapChangedValueInteger,
    trapAdditionalInfoInteger1,
    trapAdditionalInfoInteger2,
    trapAdditionalInfoInteger3
    }
    STATUS current
    DESCRIPTION
        "This trap is issued when a semaphore cannot
         be created. The trapAdditionalInfoInteger1 will contain the
         task and Function ID, the trapAdditionalInfoInteger2 and
         trapAdditionalInfoInteger3 will not be used."
::= { apexTraps 24 }

trapCannotOpenSocket NOTIFICATION-TYPE
    OBJECTS
    {
    trapIdentifier,
    trapSequenceId,
    trapNetworkElemModelNumber,
    trapNetworkElemSerialNum,
    trapPerceivedSeverity,
    trapNetworkElemOperState,
    trapNetworkElemAlarmStatus,
    trapNetworkElemAdminState,
    trapNetworkElemAvailStatus,
    trapText,
    trapNETrapLastTrapTimeStamp,
    trapChangedObjectId,
    trapChangedValueInteger,
    trapAdditionalInfoInteger1,
    trapAdditionalInfoInteger2,
    trapAdditionalInfoInteger3
    }
    STATUS current
    DESCRIPTION
        "This trap is issued when a socket cannot
         be opened. The trapAdditionalInfoInteger1 will contain the
         task and Function ID. The trapAdditionalInfoInteger2 will
         contain the errno returned by the call to socket(). The
         trapAdditionalInfoInteger3 is not used."
::= { apexTraps 25 }

trapUnknownMessageReceived NOTIFICATION-TYPE
    OBJECTS
    {
    trapIdentifier,
    trapSequenceId,
    trapNetworkElemModelNumber,
    trapNetworkElemSerialNum,
    trapPerceivedSeverity,
    trapNetworkElemOperState,
    trapNetworkElemAlarmStatus,
    trapNetworkElemAdminState,
    trapNetworkElemAvailStatus,
    trapText,
    trapNETrapLastTrapTimeStamp,
    trapChangedObjectId,
    trapChangedValueInteger,
    trapAdditionalInfoInteger1,
    trapAdditionalInfoInteger2,
    trapAdditionalInfoInteger3
    }
    STATUS current
    DESCRIPTION
        "This trap is issued when an unknown message
         is received.  The trapAdditionalInfoInteger1 will contain the
         task and Function ID. The trapAdditionalInfoInteger2 will
         contain the message ID and the trapAdditionalInfoInteger3 is
         not used."
::= { apexTraps 26 }

trapInvalidMessageReceived NOTIFICATION-TYPE
    OBJECTS
    {
    trapIdentifier,
    trapSequenceId,
    trapNetworkElemModelNumber,
    trapNetworkElemSerialNum,
    trapPerceivedSeverity,
    trapNetworkElemOperState,
    trapNetworkElemAlarmStatus,
    trapNetworkElemAdminState,
    trapNetworkElemAvailStatus,
    trapText,
    trapNETrapLastTrapTimeStamp,
    trapChangedObjectId,
    trapChangedValueInteger,
    trapAdditionalInfoInteger1,
    trapAdditionalInfoInteger2,
    trapAdditionalInfoInteger3
    }
    STATUS current
    DESCRIPTION
        "This trap is issued when an invalid message
         is received.  The trapAdditionalInfoInteger1 will contain the
         task and Function ID. The trapAdditionalInfoInteger2 will
         contain the message ID and the trapAdditionalInfoInteger3 is
         not used."
::= { apexTraps 27 }


-- ------------------------------------------------------------------------------
--
-- APEX Alarm Traps
--
-- Trap ID starts at 8000.
--

trapHardwareFault NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmHardwareFault.

         This trap is sent on a summary basis.

         Additional Info 1 carries HW Error Code (refer to HW Event Log for details).
         Additional Info 2 is not used.
         Additional Info 3 is not used.
        "
::= { apexTraps 8000 }

trapInvalidConfigData NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmInvalidConfigData.

         This trap is sent on a summary basis.

         Additional Info 1 is not used.
         Additional Info 2 is not used.
         Additional Info 3 is not used.
        "
::= { apexTraps 8001 }

trapTemperatureFault NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmTemperatureFault.

         This trap is sent on a summary basis.

         Additional Info 1 is not used.
         Additional Info 2 is not used.
         Additional Info 3 is not used.
        "
::= { apexTraps 8002 }

trapFanFault NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmFanFault.

         This trap is sent on a QAM Blade fan basis.

         Additional Info 1 carries the QAM Blade number (1..8).
         Additional Info 2 carries the fan number (1..2).
         Additional Info 3 is not used.
        "
::= { apexTraps 8003 }

trapPowerSupplyFault NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmPowerSupplyFault.

         This trap is sent on a Power Supply Module basis.

         Additional Info 1 carries the Power Supply module number (1 to 2).
         Additional Info 2 is not used.
         Additional Info 3 is not used.
        "
::= { apexTraps 8004 }

trapFanModuleFault NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmFanModuleFault.

         This trap is sent on a Fan Module basis.

         Additional Info 1 carries the blade slot number (1 to 8).
         Additional Info 2 is not used.
         Additional Info 3 is not used.
        "
::= { apexTraps 8005 }

trapHostModuleFault NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmHostModuleFault.

         This trap is sent on a Host Module basis.

         Additional Info 1 carries the Host Module number (1 to 2).
         Additional Info 2 is not used.
         Additional Info 3 is not used.
        "
::= { apexTraps 8006 }

trapFrontPanelModuleFault NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmFrontPanelModuleFault.

         Additional Info 1 is not used.
         Additional Info 2 is not used.
         Additional Info 3 is not used.
        "
::= { apexTraps 8007 }

trapRfSwitchModuleFault NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmRfSwitchModuleFault.

         This trap is sent on a RF Switch Module basis.

         Additional Info 1 carries the RF Switch Module number (1..4).
         Additional Info 2 is not used.
         Additional Info 3 is not used.
        "
::= { apexTraps 8008 }

trap10GbeModuleFault NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarm10GbeModuleFault.

         This trap is sent on a 10GigE Module basis.

         Additional Info 1 carries the 10GigE Module number (1..3).
         Additional Info 2 is not used.
         Additional Info 3 is not used.
        "
::= { apexTraps 8009 }

trapDtiModuleFault NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmDtiModuleFault.

         Additional Info 1 is not used.
         Additional Info 2 is not used.
         Additional Info 3 is not used.
        "
::= { apexTraps 8010 }

trapGbeLossOfPhysicalInput NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmGbeLossOfPhysicalInput.

         This trap is sent on a GigE Interface basis.

         Additional Info 1 carries the GigE Interface Number (1 to 12).
         Additional Info 2 is not used.
         Additional Info 3 is not used.
        "
::= { apexTraps 8020 }

trapGbeBufferFullness NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmGbeBufferFullness.

         This trap is sent on a QAM Blade (NPU Processor) basis.

         Additional Info 1 carries the QAM Blade Number (1 to 8).
         Additional Info 2 is not used.
         Additional Info 3 is not used.
        "
::= { apexTraps 8021 }

trapGbeInputStreamHighBitRate NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmGbeInputStreamHighBitRate.

         This trap is sent on a summary basis.

         Additional Info 1 is not used.
         Additional Info 2 is not used.
         Additional Info 3 is not used.
        "
::= { apexTraps 8022 }

trapGbeInputTsRedundFailover NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmGbeInputTsRedundFailover.

         This trap is sent on a summary basis.

         Additional Info 1 is not used.
         Additional Info 2 is not used.
         Additional Info 3 is not used.
        "
::= { apexTraps 8023 }

trapServiceInError NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmServiceInError.

         This trap is sent on an RF Port summary basis.

         Additional Info 1 carries the QAM Blade number (1..8).
         Additional Info 2 carries the RF Port number (1..4).
         Additional Info 3 is not used.
        "
::= { apexTraps 8024 }

trapGbeLossOfInputStream NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmGbeLossOfInputStream.

         This trap is sent on a summary basis.

         Additional Info 1 is not used.
         Additional Info 2 is not used.
         Additional Info 3 is not used.
        "
::= { apexTraps 8025 }

trapNpuToHostCommFault NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmNpuToHostCommFault.

         This trap is sent on a QAM Blade (NPU Processor) basis.

         Additional Info 1 carries the QAM Blade Number (1 to 8).
         Additional Info 2 is not used.
         Additional Info 3 is not used.
        "
::= { apexTraps 8026 }

trapGbeInterfaceRedundFailover NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmGbeInterfaceRedundFailover.

         This trap is sent on a GigE Interface basis.

         Additional Info 1 carries the GigE Interface Number (1 to 12).
         Additional Info 2 is not used.
         Additional Info 3 is not used.
        "
::= { apexTraps 8027 }

trapServiceInactiveError NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmServiceInactiveError.

         This trap is sent on a QAM Blade basis.

         Additional Info 1 carries the QAM Blade Number (1 to 8).
         Additional Info 2 is not used.
         Additional Info 3 is not used.
        "
::= { apexTraps 8028 }

trapOutputUtilizationFault NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmOutputUtilizationFault.

         This trap is sent on an RF Port summary basis.

         Additional Info 1 carries the QAM Blade number (1..8).
         Additional Info 2 carries the RF Port number (1..4).
         Additional Info 3 is not used.
        "
::= { apexTraps 8040 }

trapOutputOverflow NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmOutputOverflow.

         This trap is sent on an RF Port summary basis.

         Additional Info 1 carries the QAM Blade number (1..8).
         Additional Info 2 carries the RF Port number (1..4).
         Additional Info 3 is not used.
        "
::= { apexTraps 8041 }

trapQamBladeFault NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmQamBladeFault.

         This trap is sent on a QAM Blade basis.

         Additional Info 1 carries the QAM Blade number (1 to 8).
         Additional Info 2 is not used.
         Additional Info 3 is not used.
        "
::= { apexTraps 8042 }

trapQamRfPortFault NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmQamRfPortFault.

         This trap is sent on a RF Port basis.

         Additional Info 1 carries the QAM Blade number (1..8).
         Additional Info 2 carries the RF Port number (1..4).
         Additional Info 3 is not used.
        "
::= { apexTraps 8043 }

trapQamChannelFault NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmQamChannelFault.

         This trap is sent on an RF Port summary basis.

         Additional Info 1 carries the QAM Blade number (1..8).
         Additional Info 2 carries the RF Port number (1..4).
         Additional Info 3 is not used.
        "
::= { apexTraps 8044 }

trapQamBladeRedundFailover NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmQamBladeRedundFailover.

         This trap is sent on a QAM Blade basis.
         
         Additional Info 1 carries the QAM Blade number (1..8).
         Additional Info 2 is not used.
         Additional Info 3 is not used.
        "
::= { apexTraps 8045 }

trapQamBladeRedundMismatch NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmQamBladeRedundMismatch.

         This trap is sent on a summary basis.

         Additional Info is not used.
        "
::= { apexTraps 8046 }

trapQamBladePhysicalLatchFault NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmQamBladePhysicalLatchFault.

         This trap is sent on a QAM Blade basis.

         Additional Info 1 carries the QAM Blade number (1 to 8).
         Additional Info 2 is not used.
         Additional Info 3 is not used.
        "
::= { apexTraps 8047 }

trapRtspControllerCommFault NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmRtspControllerCommFault.

         This trap is sent on a controller basis.

         Additional Info 1 carries the controller number.
         Additional Info 2 is not used.
         Additional Info 3 is not used.
        "
::= { apexTraps 8060 }

trapRdsCommFault NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmRdsCommFault.

         Additional Info is not used.
        "
::= { apexTraps 8070 }

trapHostModuleRedundFailover NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmHostModuleRedundFailover.

         This trap is sent on a summary basis.

         Additional Info 1 carries the Original Active Host Module number (1 to 2).
         Additional Info 2 is not used.
         Additional Info 3 is not used.
        "
::= { apexTraps 8080 }

trapHostModuleRedundFault NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmHostModuleRedundFault.

         This trap is sent on a summary basis.

         Additional Info 1 is not used.
         Additional Info 2 is not used.
         Additional Info 3 is not used.
        "
::= { apexTraps 8081 }

trapDtiSyncLossFault NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmDtiSyncLossFault.

         This trap is sent on a summary basis.

         Additional Info 1 is not used.
         Additional Info 2 is not used.
         Additional Info 3 is not used.
        "
::= { apexTraps 8090 }


trapDepiControlConnectionFault NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding alarm apexAlarmDepiControlConnectionFault.

         This trap is sent on a summary basis.

         Additional Info 1 is not used.
         Additional Info 2 is not used.
         Additional Info 3 is not used.
        "
::= { apexTraps 8091 }


-- ------------------------------------------------------------------------------
--
-- APEX Event Traps
--
-- Trap ID starts at 8500.
--

trapEmUserLoginFailed NOTIFICATION-TYPE
    OBJECTS
    {
     trapIdentifier,
     trapSequenceId,
     trapNetworkElemModelNumber,
     trapNetworkElemSerialNum,
     trapPerceivedSeverity,
     trapNetworkElemOperState,
     trapNetworkElemAlarmStatus,
     trapNetworkElemAdminState,
     trapNetworkElemAvailStatus,
     trapText,
     trapNETrapLastTrapTimeStamp,
     trapChangedObjectId,
     trapChangedValueInteger,
     trapAdditionalInfoInteger1,
     trapAdditionalInfoInteger2,
     trapAdditionalInfoInteger3
    }
    STATUS current
    DESCRIPTION
        "See corresponding event apexEventEmUserLoginFailed.

         Additional Info is not used."
::= { apexTraps 8500 }


-- ------------------------------------------------------------------------------
END
