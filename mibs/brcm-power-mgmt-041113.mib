--****************************************************************************
--
-- Copyright (c) 2012-2013 Broadcom Corporation
--
-- This program is the proprietary software of Broadcom Corporation and/or
-- its licensors, and may only be used, duplicated, modified or distributed
-- pursuant to the terms and conditions of a separate, written license
-- agreement executed between you and Broadcom (an "Authorized License").
-- Except as set forth in an Authorized License, Broadcom grants no license
-- (express or implied), right to use, or waiver of any kind with respect to
-- the Software, and Broadcom expressly reserves all rights in and to the
-- Software and all intellectual property rights therein.  IF YOU HAVE NO
-- AUTHORIZED LICENSE, THEN YOU HAVE NO RIGHT TO USE THIS SOFTWARE IN ANY WAY,
-- AND SHOULD IMMEDIATELY NOTIFY BROADCOM AND DISCONTINUE ALL USE OF THE
-- SOFTWARE.  
--
-- Except as expressly set forth in the Authorized License,
--
-- 1.     This program, including its structure, sequence and organization,
-- constitutes the valuable trade secrets of Broadcom, and you shall use all
-- reasonable efforts to protect the confidentiality thereof, and to use this
-- information only in connection with your use of Broadcom integrated circuit
-- products.
--
-- 2.     TO THE MAXIMUM EXTENT PERMITTED BY LAW, THE SOFTWARE IS PROVIDED
-- "AS IS" AND WITH ALL FAULTS AND BROADCOM MAKES NO PROMISES, REPRESENTATIONS
-- OR WARRANTIES, EITHER EXPRESS, IMPLIED, STATUTORY, OR OTHERWISE, WITH
-- RESPECT TO THE SOFTWARE.  BROADCOM SPECIFICALLY DISCLAIMS ANY AND ALL
-- IMPLIED WARRANTIES OF TITLE, MERCHANTABILITY, NONINFRINGEMENT, FITNESS FOR
-- A PARTICULAR PURPOSE, LACK OF VIRUSES, ACCURACY OR COMPLETENESS, QUIET
-- ENJOYMENT, QUIET POSSESSION OR CORRESPONDENCE TO DESCRIPTION. YOU ASSUME
-- THE ENTIRE RISK ARISING OUT OF USE OR PERFORMANCE OF THE SOFTWARE.
--
-- 3.     TO THE MAXIMUM EXTENT PERMITTED BY LAW, IN NO EVENT SHALL BROADCOM
-- OR ITS LICENSORS BE LIABLE FOR (i) CONSEQUENTIAL, INCIDENTAL, SPECIAL,
-- INDIRECT, OR EXEMPLARY DAMAGES WHATSOEVER ARISING OUT OF OR IN ANY WAY
-- RELATING TO YOUR USE OF OR INABILITY TO USE THE SOFTWARE EVEN IF BROADCOM
-- HAS BEEN ADVISED OF THE POSSIBILITY OF SUCH DAMAGES; OR (ii) ANY AMOUNT IN
-- EXCESS OF THE AMOUNT ACTUALLY PAID FOR THE SOFTWARE ITSELF OR U.S. $1,
-- WHICHEVER IS GREATER. THESE LIMITATIONS SHALL APPLY NOTWITHSTANDING ANY
-- FAILURE OF ESSENTIAL PURPOSE OF ANY LIMITED REMEDY.
--
--****************************************************************************
--    Filename: brcm-power-mgmt.mib
--    Author:   Kevin O'Neal
--    Creation Date: August 14, 2012
--
--**************************************************************************
--    Description:
--
--    MIB for runtime management of BFC power management features
--		
--**************************************************************************
--    Revision History:
--
--**************************************************************************

BRCM-POWER-MGMT-MIB DEFINITIONS ::= BEGIN

IMPORTS
    MODULE-IDENTITY,
    OBJECT-TYPE,
    Integer32
        FROM SNMPv2-SMI
    TruthValue
        FROM SNMPv2-TC
    MODULE-COMPLIANCE,
    OBJECT-GROUP
        FROM SNMPv2-CONF
    ifIndex
        FROM IF-MIB
    cableDataMgmtMIBObjects
        FROM BRCM-CABLEDATA-MGMT-MIB;
                
powerMgmt MODULE-IDENTITY
    LAST-UPDATED "201304110000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadcom proprietary MIB for runtime management and configuration
         of objects related to power management features."
    REVISION      "201304110000Z"
    DESCRIPTION
        "Added types MODULE-COMPLIANCE, OBJECT-GROUP, and ifIndex to IMPORTS
        section."
    REVISION      "201211090000Z"
    DESCRIPTION
        "Deprecated object powerMgmtIfDelay."
    REVISION      "201208140000Z"
    DESCRIPTION
        "Initial version of this MIB module."
    ::= { cableDataMgmtMIBObjects 20 }
    
--
-- Textual Conventions
--

--
-- Object Definitions
--

powerMgmtNotifications  OBJECT IDENTIFIER ::= { powerMgmt 0 }

powerMgmtMIBObjects OBJECT IDENTIFIER ::= { powerMgmt 1 }

powerMgmtConformance OBJECT IDENTIFIER ::= { powerMgmt 2 }

--
-- MIB objects
--

powerMgmtBase OBJECT IDENTIFIER ::= { powerMgmtMIBObjects 1 }

powerMgmtInterfaceTable  OBJECT-TYPE
    SYNTAX      SEQUENCE OF PowerMgmtInterfaceEntry
    MAX-ACCESS  not-accessible
    STATUS      current
    DESCRIPTION
        "This table is used to characterize the power management properties of
         the device on a per-interface basis.  An entry exists in this table 
         for each entry in the ifTable which has power management capability."
    ::= { powerMgmtBase 1 }

powerMgmtInterfaceEntry OBJECT-TYPE
    SYNTAX      PowerMgmtInterfaceEntry
    MAX-ACCESS  not-accessible
    STATUS      current
    DESCRIPTION
        "An entry containing power management information applicable to a
         particular interface."
    INDEX   { ifIndex }
    ::= { powerMgmtInterfaceTable 1 }

PowerMgmtInterfaceEntry ::= 
    SEQUENCE    {
        powerMgmtIfDelay    Integer32
    }

powerMgmtIfDelay OBJECT-TYPE
    SYNTAX      Integer32 (-1..2147483647)
    UNITS       "seconds"
    MAX-ACCESS  read-write
    STATUS      deprecated
    DESCRIPTION
        "This object has been deprecated and may not be supported on some
         devices.  If this object is not supported, then the 
         powerMgmtInterfaceTable will also not be supported since this is the
         only column in the table.
         
         Specifies the number of seconds following a battery or thermal event
         before the interface will enter reduced power mode.  If set to -1, 
         the interface will never enter reduced power mode and will remain at 
         full power until the trigger event is cleared.

         Trigger events may include, but are not limited to, transition to 
         battery power or temperature which exceeds thermal threshold limits.

         Reaction to reduced power mode is interface and device dependent.
         Some interfaces may be disabled completely in reduced power mode,
         others may have capabilities restricted in order to conserve power."
    DEFVAL { 0 }
    ::= { powerMgmtInterfaceEntry 1 }

powerMgmtCableModem OBJECT IDENTIFIER ::= { powerMgmtMIBObjects 2 }

powerMgmtCmChannelBondingStrategy OBJECT-TYPE
    SYNTAX      INTEGER {
                noChange(0),
                docsis3(1),
                macReset1x1(2),
                docsis3WithMacResetFallback(3)
    }
    MAX-ACCESS  read-write
    STATUS      current
    DESCRIPTION
        "Determines the channel bonding transition strategy used when the CM
         enters reduced power mode due to transition to battery power or thermal 
         event.

         For the purposes of this MIB description, 'reduced power mode' means a 
         mode of operation in which modem features are intentionally disabled as 
         a response to a trigger event.  It is not related to measures which 
         may be employed during normal operation with the goal of improving 
         overall energy efficiency.
         
         When set to a value of noChange(0), the modem will not change the 
         channel bonding configuration in response to a transition to reduced
         power mode.  The device will continue to operate in the bonding 
         configuration that was in effect at the time the modem entered 
         reduced power mode.
         
         When set to docsis3(1), the CM will conform to DOCSIS 3.0 requirements 
         by dispatching a CM-STATUS message to the CMTS with a type code of 9, 
         'CM operating on battery backup', indicating a transition to battery 
         mode.  The CMTS is then expected to initiate a DBC transaction which 
         will reduce the number of channels used by the CM.  

         Note that the 'battery backup' event code is used for either type of 
         trigger, because the CM-STATUS event set does not include message codes
         for other reduced power events.
         
         The value of macReset1x1(2) is used when the CM is operating in an 
         environment in which the CMTS does not respond to CM-STATUS messaging 
         for type code 9.

         In this mode, upon transition to reduced power mode, the CM will 
         re-initialize the MAC and re-register, reporting a value of 0 for 
         the Multiple Transmit Channel Support modem capability and a value of 0 
         for the Multiple Receive Channel Support modem capability. This disables 
         both downstream channel bonding and Multiple Transmit Channel Mode.  
         The CM will then register in DOCSIS 2.0 1x1 mode, resulting in reduced 
         power consumption.

         Note that if a critical data service (such as a telephone call in the 
         case of a device which includes an eMTA) is in progress, the MAC 
         re-init will be deferred until the critical operation completes.  Upon 
         transition back to full power mode, the CM will again re-init the MAC, 
         this time advertising Multiple Transmit Channel support and Multiple 
         Receive Channel Support to the extent that the device is capable.  
         Again, the re-init may be deferred if necessary to avoid interruption 
         of a critical data service.

         The default value of cmStatusWith1x1Fallback(3) combines the docsis3
         mode with a fallback to macReset1x1 mode.  Upon transition to reduced
         power mode, the CM will dispatch a CM-STATUS message to the CMTS in an
         attempt to change to 1x1 mode according to standard DOCSIS mechanisms.  
         If, after 30 seconds, the CM has not transitioned to 1x1 mode then the 
         CM will re-initialize the MAC and re-register in 1x1 mode as described 
         above."
    DEFVAL { docsis3WithMacResetFallback }
    ::= { powerMgmtCableModem 1 }

powerMgmtEthernet OBJECT IDENTIFIER ::= { powerMgmtMIBObjects 3 }

powerMgmtEthDefaultAutoPowerDownEnable OBJECT-TYPE
    SYNTAX      TruthValue
    MAX-ACCESS  read-write
    STATUS      current
    DESCRIPTION
        "Enables or disables the Ethernet automatic powerdown feature.  If 
         enabled, the analog portion of the Ethernet PHY circuitry will be shut 
         off when the cable is not connected or the link partner power is off.

         If the device has multiple ethernet ports, the value of this setting
         will be applied to all ports.

         The value of this object is only applied at system initialization.  If
         the value is modified, the new value will be stored to non-volatile
         storage but will not take effect until the next reboot."
    DEFVAL { true }
    ::= { powerMgmtEthernet 1 }

powerMgmtEthDefaultAutoPowerDownSleepTimer OBJECT-TYPE
    SYNTAX      Integer32 (0..15000)
    UNITS       "milliseconds"
    MAX-ACCESS  read-write
    STATUS      current
    DESCRIPTION
        "When powerMgmtEthAutoPowerDownEnable is set to true(1), the value of
         this object controls the length of time after the Ethernet link drops
         before the PHY circuitry is disabled.

         If the device has multiple ethernet ports, the value of this setting
         will be applied to all ports.

         The acceptable values for this object are device-specific.  If the 
         object is set to a value which is within the allowable range but does
         not match a discrete acceptable value for the specific device, the
         value will automatically be set to the nearest acceptable value.

         The value of this object is only applied at system initialization.  If
         the value is modified, the new value will be stored to non-volatile
         storage but will not take effect until the next reboot."
    DEFVAL { 2700 }
    ::= { powerMgmtEthernet 2 }

powerMgmtEthDefaultAutoPowerDownWakeTimer OBJECT-TYPE
    SYNTAX      Integer32 (0..15000)
    UNITS       "milliseconds"
    MAX-ACCESS  read-write
    STATUS      current
    DESCRIPTION
        "When powerMgmtEthAutoPowerDownEnable is set to true(1), and the 
         Ethernet PHY has been disabled due to the link being down, the PHY
         will be re-enabled upon restoration of link.  The value of this object
         controls the frequency at which a check for link restoration is made.

         If the device has multiple ethernet ports, the value of this setting
         will be applied to all ports.

         The acceptable values for this object are device-specific.  If the 
         object is set to a value which is within the allowable range but does
         not match a discrete acceptable value for the specific device, the
         value will automatically be set to the nearest acceptable value.

         The value of this object is only applied at system initialization.  If
         the value is modified, the new value will be stored to non-volatile
         storage but will not take effect until the next reboot."
    DEFVAL { 84 }
    ::= { powerMgmtEthernet 3 }

--
-- Conformance definitions
--

--
-- Compliance Statements
--

powerMgmtCompliances  OBJECT IDENTIFIER ::= { powerMgmtConformance 1 }

powerMgmtGroups       OBJECT IDENTIFIER ::= { powerMgmtConformance 2 }

powerMgmtCompliance  MODULE-COMPLIANCE
    STATUS      current
    DESCRIPTION
        "The compliance statement for devices which support the power management 
         feature."
    MODULE
    MANDATORY-GROUPS {
               powerMgmtBaseGroup
    }
    ::= { powerMgmtCompliances 1 }


powerMgmtBaseGroup OBJECT-GROUP
    OBJECTS {
        powerMgmtIfDelay,
        powerMgmtCmChannelBondingStrategy,
        powerMgmtEthDefaultAutoPowerDownEnable,
        powerMgmtEthDefaultAutoPowerDownSleepTimer,
        powerMgmtEthDefaultAutoPowerDownWakeTimer
    }
    STATUS      current
    DESCRIPTION
        "A set of objects supported by all agents which implement this MIB."
    ::= { powerMgmtGroups 1 }       
END
