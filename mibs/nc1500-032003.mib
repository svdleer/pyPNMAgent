NC1500-MIB DEFINITIONS ::= BEGIN
--
--  FILE INFO:
--    $Workfile:   nc1500.mib  $
--    $Revision:   1.37  $
--    $Date:   23 Mar 2006 18:19:34  $
--
--IMPORTS
--    MODULE-IDENTITY, OBJECT-TYPE, NOTIFICATION-TYPE,
--    ObjectName, Integer32, Counter32 
--        FROM SNMPv2-SMI
--    DisplayString, TestAndIncr, TimeStamp
--      FROM SNMPv2-TC
--  MODULE-COMPLIANCE, OBJECT-GROUP
--      FROM SNMPv2-CONF
--  system, ifIndex
--      FROM RFC1213-MIB
--
--  NC1500-MIB MODULE-IDENTITY
--      LAST-UPDATED "0303200000Z"
--      ORGANIZATION "Motorola Corporation"
--      CONTACT-INFO "Jiun-Li Jang
--                    Motorola Corporation
--                    Digital Media Systems
--                    101 Tournament Dr.
--                    Horsham, PA  19044
--
--                    Tel: +1 215 323 1454
--                    Fax: +1 215 323 0364
--                    E-mail: jjang@motorola.com"
--
--      DESCRIPTION  "This MIB module is for the NC1500.
--                    The objects in this MIB are organized
--                    as follows:"
--
-- ncSystem {nc1500 1}
--     ncSystemConf { ncSystem 1 }
--         ncNetCards
--             ncOampNetCard
--                 ncOampIpAddress
--                 ncOampSubnet
--                 ncOampMacAddress
--                 ncOampEthernetConfig
--                 ncOampEthernetActual
--             ncAppNetCard
--                 ncAppIpAddress
--                 ncAppSubnet
--                 ncAppMacAddress
--                 ncAppEthernetConfig
--                 ncAppEthernetActual
--         ncDacInterface
--             ncDacHostName
--             ncDacDataServiceName
--             ncDacIpAddress
--         ncSystemConfMisc
--             ncSaveConfiguration
--             ncBackgroundPurgeEnable
--             ncSoftwareVersion
--             ncUploadFiles
--             ncBackgroundPathTestEnable
--             ncSystemStatusOne
--             ncSettopHostIp
--             ncSettopSubnetMask
--             ncSettopNetworkBcIp
--             ncSettopNetworkBcIpEnable
--             ncSettopSinglecastBcIp
--             ncSettopSinglecastBcIpEnable
--             ncSettopMulticastIp1
--             ncSettopMulticastIp1Enable
--             ncSettopMulticastIp2
--             ncSettopMulticastIp2Enable
--             ncSettopMulticastIp3
--             ncSettopMulticastIp3Enable
--             ncSettopMulticastIp4
--             ncSettopMulticastIp4Enable
--             ncSettopActualSupported
--             ncBroadcastMessageInterval
--             ncTaskMonitoringRebootEnable
--         ncDateAndTimeConf
--             ncDateAndTime
--         ncDNSServerConf
--             ncDNSServerIP
--             ncDNSDomainName
--     ncRpdConf { ncSystem 2 }
--         ncRpdConfTable
--             ncRpdConfRpdIndex
--             ncRpdIpAddress
--             ncRpdUdpPortNumber
--         ncRpdDemodConfTable
--             ncDemodConfRpdIndex
--             ncDemodConfDemodIndex
--             ncDemodReturnPathId
--             ncDemodDownStreamPathId
--             ncDemodTunedFrequency
--             ncDemodChannelType
--     ncOmConf {ncSystem 3 }
--         ncOmConfTable
--             ncOmConfOmIndex
--             ncOmIpAddress
--             ncOmUdpPortNumber
--             ncOmDownStreamPathId
--             ncOmTransportType
--             ncOmMacSignalingPid
--             ncOmDataPid
--             ncOmBandWidth
--     ncPeriodicBrdcastConf { ncSystem 4 }
--         ncBroadcastTaskConf
--             ncDefaultConfigMsgRate
--             ncContChannelMsgRate
--         ncDefaultConfigMsg
--             ncPowerRetryCount
--             ncMaximumPowerLevel
--             ncMinimumPowerLevel
--             ncPowerIncrement
--             ncIdleInterval
--             ncNetworkEntryDelay
--             ncInitTimeout
--         ncContChannelMsg
--             ncBackoffTimeUnit
--             ncBackoffMax
--             ncCellAbortCount
--             ncMacAbortCount
--             ncBackoffOffset
--             ncAckTimeout
--     ncDiagnostics { ncSystem 5 }
--         ncDiagConnectTest
--             ncDiagConnStart
--             ncDiagConnResultTable
--                 ncDiagConnResultIndex
--                 ncDiagConnResultDac
--                 ncDiagConnResultOmOne
--                 ncDiagConnResultOmTwo
--                 ncDiagConnResultOmThree 
--                 ncDiagConnResultOmFour
--                 ncDiagConnResultOmFive
--                 ncDiagConnResultOmSix
--                 ncDiagConnResultOmSeven
--                 ncDiagConnResultOmEight
--                 ncDiagConnResultOmNine
--                 ncDiagConnResultOmTen
--                 ncDiagConnResultRpdOne
--                 ncDiagConnResultRpdTwo
--                 ncDiagConnResultRpdThree
--                 ncDiagConnResultRpdFour
--                 ncDiagConnResultRpdFive
--                 ncDiagConnResultRpdSix
--                 ncDiagConnResultRpdSeven
--                 ncDiagConnResultRpdEight
--                 ncDiagConnResultRpdNine
--                 ncDiagConnResultRpdTen
--                 ncDiagConnResultRpdEleven
--                 ncDiagConnResultRpdTwelve
--                 ncDiagConnResultRpdThirteen
--                 ncDiagConnResultRpdFourteen
--                 ncDiagConnResultRpdFifteen
--                 ncDiagConnResultRpdSixteen
--                 ncDiagConnResultRpdSeventeen
--                 ncDiagConnResultRpdEighteen
--                 ncDiagConnResultRpdNineteen
--                 ncDiagConnResultRpdTwenty
--                 ncDiagConnResultRpdTwentyone
--                 ncDiagConnResultRpdTwentytwo
--                 ncDiagConnResultRpdTwentythree
--                 ncDiagConnResultRpdTwentyfour
--                 ncDiagConnResultRpdTwentyfive
--                 ncDiagConnResultRpdTwentysix
--                 ncDiagConnResultRpdTwentyseven
--                 ncDiagConnResultRpdTwentyeight
--                 ncDiagConnResultRpdTwentynine
--                 ncDiagConnResultRpdThirty
--                 ncDiagConnResultRpdThirtyone
--                 ncDiagConnResultRpdThirtytwo
--         ncMaintenance
--             ncPurgeSettop
--             ncBackgroundQuestionSettop
--             ncAutoRecoveryFlag
--             ncOpenAppPortsFlag
--             ncClearRetryStats
--             ncUpTimeDays
--             ncUpTimeHours
--             ncUpTimeMinutes
--             ncUpTimeSeconds
--             ncReduceIdleTime
--             ncStealthSignOn
--             ncXmitMcast40
--             ncTempSettopKey
--             ncSettopKeyVerify
--         ncSettopStatusTest
--             ncSettopStatusStart
--             ncSettopStatusIP
--             ncSettopStatusResult
--         ncSettopStatusSummary
--             ncSettopTotal
--             ncSettopGood
--             ncSettopQuestionable
--             ncSettopDatabaseSize
--           ncAlarmThresholds               
--             ncRPDFramesDropThreshold
--             ncRPDFramesDropCountPeriod
--             ncDMBandwidthThreshold
--             ncSettopDatabaseThreshold
--             ncUpstreamRetryThreshold
--             ncQuestionableSettopThreshold
--             ncPurgedSettopThreshold
--             ncExcessDropDsMsgThreshold
--             ncExcessDropDsMsgCountPeriod
--             ncExcessDropDsMsgClearThreshold
--             ncUpstreamBandwidthThreshold
--             ncSettopDbThresholdSeverity
--         ncGateNDestTest
--             ncGateNDestNumEntries
--             ncGateNDestOverallStatus
--             ncGateNDestTestStart
--             ncGateNDestPingRate
--         ncGateNDestTestResults
--             ncGateNDestTestResultsIndex
--             ncGateNDestIPAddrs
--             ncGateNDestTestResultsBitFields
-- ncUpStream {nc1500 2}
--     ncUpStreamStatTable
--         ncUpStreamStatRpdIndex
--         ncUpStreamStatDemodIndex
--         ncUpStatLastSecUncorrCells
--         ncUpStatLastSecCorrectCells
--         ncUpStatLastSecPerfectCells
--         ncUpStatLastSecCells
--         ncUpStatLoWinUncorrCells
--         ncUpStatLoWinCorrectCells
--         ncUpStatLoWinPerfectCells
--         ncUpStatLoWinCells
--         ncUpStatMinLoWinUncorrCells
--         ncUpStatMinLoWinCorrectCells
--         ncUpStatMinLoWinPerfectCells
--         ncUpStatMaxLoWinUncorrCells
--         ncUpStatMaxLoWinCorrectCells
--         ncUpStatMaxLoWinPerfectCells
--         ncUpStatAveLoWinUncorrCells
--         ncUpStatAveLoWinCorrectCells
--         ncUpStatAveLoWinPerfectCells
--         ncUpStatShWinUncorrCells
--         ncUpStatShWinCorrectCells
--         ncUpStatShWinPerfectCells
--         ncUpStatShWinCells
--         ncUpStatShWinMinUncorrCells
--         ncUpStatShWinMinCorrectCells
--         ncUpStatShWinMinPerfectCells
--         ncUpStatShWinMaxUncorrCells
--         ncUpStatShWinMaxCorrectCells
--         ncUpStatShWinMaxPerfectCells
--         ncUpStatShWinAveUncorrCells
--         ncUpStatShWinAveCorrectCells
--         ncUpStatShWinAvePerfectCells
--         ncUpStatUncorrCellsCntr
--         ncUpStatCorrectCellsCntr
--         ncUpStatPerfectCellsCntr
--         ncUpStatCellsCntr
--         ncUpStatLostRpdFrames
--         ncUpStatRpdFrames
--         ncUpStatLostRpdFramesCntr
--         ncUpStatRpdFramesCntr
--     ncUpStreamStatClear
--     ncUpStreamPathStatTable
--         ncUpStreamPathIdIndex
--         ncUpStreamRetryZero
--         ncUpStreamRetryOne
--         ncUpStreamRetryTwo
--         ncUpStreamRetryThree
--         ncUpStreamRetryFourOrMore
--         ncUpStreamRetryCountClear
--         ncUpStreamRetryEfficiency
--     ncUpStreamPathStatClear
--     ncPathTest
--         ncPathTestNumberOfPathPairs
--         ncPathTestMasterAlarm
--         ncPathPairTestBitFieldTable
--             ncPathPairTestBitFieldIndex
--             ncPathPairTestBitFieldData
--         ncPathConfigTable
--             ncPathConfigIndex
--             ncPathConfigDownStreamPathId
--             ncPathConfigOmChassisNumber
--             ncPathConfigUpStreamPathId
--             ncPathConfigRpdChassisOne
--             ncPathConfigRpdChassisTwo
--             ncPathConfigRpdChassisThree
--             ncPathConfigRpdChassisFour
--             ncPathConfigRpdChassisFive
--             ncPathConfigRpdChassisSix
--             ncPathConfigRpdChassisSeven
--             ncPathConfigRpdChassisEight
--             ncPathConfigRpdChassisNine
--             ncPathConfigRpdChassisTen
--             ncPathConfigRpdChassisEleven
--             ncPathConfigRpdChassisTwelve
--             ncPathConfigRpdChassisThirteen
--             ncPathConfigRpdChassisFourteen
--             ncPathConfigRpdChassisFifteen
--             ncPathConfigRpdChassisSixteen
--             ncPathConfigRpdChassisSeventeen
--             ncPathConfigRpdChassisEighteen
--             ncPathConfigRpdChassisNineteen
--             ncPathConfigRpdChassisTwenty
--     ncDemodStatusTable
--         ncDemodStatusIndex
--         ncDemodStatus
--     ncRpdChassisStatusTable
--         ncRpdChassisStatusIndex
--         ncRpdChassisStatus
-- ncSettopBox {nc1500 3}
--     ncSettopBoxAdd
--         ncSettopAddedMac
--     ncSettopBoxDelete
--         ncSettopDeletedMac
--     ncSettopIpRange
--         ncSettopStartIp
--         ncSettopEndIp
--     ncSettopBoxTable
--         ncSettopBoxMacIndex
--         ncSettopBoxIpAddress
--         ncSettopBoxUpmAddress
--         ncSettopBoxMacAddress
--         ncSettopBoxDownStreamPathId
--         ncSettopBoxReturnPathId
--         ncSettopBoxNumDownStreamPdu
--         ncSettopBoxNumUpStreamPdu
--         ncSettopBoxNumUpStreamCrcErr
--         ncSettopBoxRetryCount
--         ncSettopBoxReceivedPwrLevel
--         ncSettopBoxNumberOfEntries
--         ncSettopBoxLastIdleTime
--         ncSettopBoxLastMessageTime
--         ncSettopBoxStatus
-- ncAlarms {nc1500 4}
-- ncDownStream {nc1500 5}
--     ncOmChassisStatus
--
    IMPORTS
        Counter, 
        Gauge, 
        IpAddress, 
        TimeTicks                      FROM RFC1155-SMI
        DisplayString                  FROM RFC1213-MIB
        OBJECT-TYPE                    FROM RFC-1212
        TRAP-TYPE                      FROM RFC-1215
        dnsAlarms                      FROM DNS-TRAPS-MIB
        trapIdentifier,     
        trapNetworkElemModelNumber,
        trapNetworkElemSerialNum,
        trapPerceivedSeverity,
        trapNetworkElemOperState,
        trapNetworkElemAlarmStatus,
        trapNetworkElemAdminState,
        trapNetworkElemAvailStatus, 
        trapText,
        trapNETrapLastTrapTimeStamp,
        trapChangedObjectId,
        trapAdditionalInfoInteger1, 
        trapAdditionalInfoInteger2, 
        trapAdditionalInfoInteger3,     
        trapChangedValueDisplayString,  
        trapChangedValueOID, 
        trapChangedValueIpAddress,                     
        trapChangedValueInteger        FROM NLSBBN-TRAPS-MIB
        nc1500                         FROM NLS-BBNIDENT-MIB;
        
-- All representations of MAC addresses in this MIB Module
-- use, as a textual convention (i.e. this convention does
-- not affect their encoding), the data type:

        MacAddress ::= OCTET STRING (SIZE (6))    -- a 6 octet address in the
                                                  -- "canonical" order
-- groups in the NC1500 MIB

        ncSystem              OBJECT IDENTIFIER  ::= {nc1500 1} 
        ncSystemConf          OBJECT IDENTIFIER  ::= {ncSystem 1}
        ncNetCards            OBJECT IDENTIFIER  ::= {ncSystemConf 1}
        ncOampNetCard         OBJECT IDENTIFIER  ::= {ncNetCards 1}
        ncAppNetCard          OBJECT IDENTIFIER  ::= {ncNetCards 2}
        ncDacInterface        OBJECT IDENTIFIER  ::= {ncSystemConf 2}
        ncSystemConfMisc      OBJECT IDENTIFIER  ::= {ncSystemConf 3}
        ncDateAndTimeConf     OBJECT IDENTIFIER  ::= {ncSystemConf 4}
        ncDNSServerConf       OBJECT IDENTIFIER  ::= {ncSystemConf 5}
        ncRpdConf             OBJECT IDENTIFIER  ::= {ncSystem 2}
        ncOmConf              OBJECT IDENTIFIER  ::= {ncSystem 3}
        ncPeriodicBrdcastConf OBJECT IDENTIFIER  ::= {ncSystem 4}
        ncBroadcastTaskConf   OBJECT IDENTIFIER  ::= {ncPeriodicBrdcastConf 1}
        ncDefaultConfigMsg    OBJECT IDENTIFIER  ::= {ncPeriodicBrdcastConf 2}
        ncContChannelMsg      OBJECT IDENTIFIER  ::= {ncPeriodicBrdcastConf 3}
        ncDiagnostics         OBJECT IDENTIFIER  ::= {ncSystem 5}
        ncDiagConnectTest     OBJECT IDENTIFIER  ::= {ncDiagnostics 1}
        ncMaintenance         OBJECT IDENTIFIER  ::= {ncDiagnostics 2}
        ncSettopStatusTest    OBJECT IDENTIFIER  ::= {ncDiagnostics 3}
        ncSettopStatusSummary OBJECT IDENTIFIER  ::= {ncDiagnostics 4}
        ncAlarmThresholds     OBJECT IDENTIFIER  ::= {ncDiagnostics 5}
        ncGateNDestTest         OBJECT IDENTIFIER  ::= {ncDiagnostics 6}
        ncUpStream            OBJECT IDENTIFIER  ::= {nc1500 2}
        ncPathTest            OBJECT IDENTIFIER  ::= {ncUpStream 5}
        ncSettopBox           OBJECT IDENTIFIER  ::= {nc1500 3}
        ncAlarms              OBJECT IDENTIFIER  ::= {nc1500 4}
        ncDownStream          OBJECT IDENTIFIER  ::= {nc1500 5}
        ncSettopBoxAdd        OBJECT IDENTIFIER  ::= {ncSettopBox 1}
        ncSettopBoxDelete     OBJECT IDENTIFIER  ::= {ncSettopBox 2}
        ncSettopIpRange       OBJECT IDENTIFIER  ::= {ncSettopBox 3}
       
--*****************************************
--
-- NC System Group
--   NC System Configuration Group
--     NC Network Cards Group
--       NC OAM&P Network Card Group
--
--*****************************************

ncOampIpAddress OBJECT-TYPE
                SYNTAX  IpAddress
                ACCESS  read-write
                STATUS  mandatory

                DESCRIPTION "OAM&P Ethernet card IP address.  A reboot is 
                             required for a change to the parameter to 
                             take affect."
                REFERENCE   " -- "
        ::= { ncOampNetCard 1 }

ncOampSubnet OBJECT-TYPE
                SYNTAX  IpAddress
                ACCESS  read-write
                STATUS  mandatory

                DESCRIPTION "OAM&P Ethernet card subnet mask.  A reboot is 
                             required for a change to the parameter to 
                             take affect."
                REFERENCE   " -- "
        ::= { ncOampNetCard 2 }

ncOampMacAddress OBJECT-TYPE
                SYNTAX  DisplayString
                ACCESS  read-only
                STATUS  mandatory  

                DESCRIPTION "OAM&P Ethernet card MAC address."
                REFERENCE   " -- "
        ::= { ncOampNetCard 3 }
        
ncOampEthernetConfig OBJECT-TYPE
                SYNTAX  INTEGER
                ACCESS  read-write
                STATUS  mandatory  

                DESCRIPTION "OAM&P Ethernet Bit Rate/Duplex setting 1=10/Half, 
                             2=10/Full, 3=100/Half, 4=100/Full, 5=Auto/Auto.
                             Incorrectly setting this value may cause impaired
                             network connectivity or loss of network 
                             connectivity. Refer to the Port Lockdown section
                             of the NC1500 Operator Manual."
                REFERENCE   " -- "
        ::= { ncOampNetCard 4 }
        
ncOampEthernetActual OBJECT-TYPE
                SYNTAX  INTEGER
                ACCESS  read-only
                STATUS  mandatory  

                DESCRIPTION "OAM&P Ethernet Bit Rate/Duplex actual negotiated 
                             setting 1=10/Half, 2=10/Full, 3=100/Half, 
                             4=100/Full."
                REFERENCE   " -- "
        ::= { ncOampNetCard 5 }

--*****************************************
--
-- NC System Group
--   NC System Configuration Group
--     NC Network Cards Group
--       NC Application Server Network Card Group
--
--*****************************************

ncAppIpAddress OBJECT-TYPE
                SYNTAX  IpAddress
                ACCESS  read-write
                STATUS  mandatory

                DESCRIPTION "Application Server Ethernet card IP address.  
                             A reboot is required for a change to the 
                             parameter to take affect."
                REFERENCE   " -- "
        ::= { ncAppNetCard 1 }

ncAppSubnet OBJECT-TYPE
                SYNTAX  IpAddress
                ACCESS  read-write
                STATUS  mandatory

                DESCRIPTION "Application Server Ethernet card subnet mask.
                             A reboot is required for a change to the 
                             parameter to take affect."
                REFERENCE   " -- "
        ::= { ncAppNetCard 2 }

ncAppMacAddress OBJECT-TYPE
                SYNTAX  DisplayString
                ACCESS  read-only
                STATUS  mandatory  

                DESCRIPTION "Application Server Ethernet card MAC address."
                REFERENCE   " -- "
        ::= { ncAppNetCard 3 }
        
ncAppEthernetConfig OBJECT-TYPE
                SYNTAX  INTEGER
                ACCESS  read-write
                STATUS  mandatory  

                DESCRIPTION "Application Network Ethernet Bit Rate/Duplex setting 1=10/Half, 
                             2=10/Full, 3=100/Half, 4=100/Full, 5=Auto/Auto.
                             Incorrectly setting this value may cause impaired network 
                             connectivity or loss of network connectivity. Refer to the Port
                             Lockdown section of the NC1500 Operator Manual."
                REFERENCE   " -- "
        ::= { ncAppNetCard 4 }
        
ncAppEthernetActual OBJECT-TYPE
                SYNTAX  INTEGER
                ACCESS  read-only
                STATUS  mandatory  

                DESCRIPTION "Application Network Ethernet Bit Rate/Duplex 
                             actual negotiated setting 1=10/Half, 2=10/Full, 
                             3=100/Half, 4=100/Full."
                REFERENCE   " -- "
        ::= { ncAppNetCard 5 }

--*****************************************
--
-- NC System Group
--   NC System Configuration Group
--     NC DAC Interface Group
--
--*****************************************

ncDacHostName OBJECT-TYPE
                SYNTAX  DisplayString
                ACCESS  read-write
                STATUS  mandatory  

                DESCRIPTION "DAC, RADD, or HMS host name."
                REFERENCE   " -- "
        ::= { ncDacInterface 1 }

ncDacDataServiceName OBJECT-TYPE
                SYNTAX  DisplayString
                ACCESS  read-write
                STATUS  mandatory  

                DESCRIPTION "DAC, RADD, or HMS service name corresponding to the
                             UDP port on the DAC which receives data from the 
                             NC1500."
                REFERENCE   " -- "
        ::= { ncDacInterface 2 }

ncDacIpAddress OBJECT-TYPE
                SYNTAX  IpAddress
                ACCESS  read-only
                STATUS  mandatory

                DESCRIPTION "DAC, RADD, or HMS IP address."
                REFERENCE   " -- "
        ::= { ncDacInterface 3 }

--*****************************************
--
-- NC System Group
--   NC System Configuration Group
--     NC System Configuration Miscelaneous Group
--
--*****************************************

ncSaveConfiguration OBJECT-TYPE
                SYNTAX  INTEGER
                        {
                         saveNotInProgress     (1),
                         startSaveToFile       (2),
                         savingConfigToFile    (3)
                        }
                ACCESS  read-write
                STATUS  mandatory
                DESCRIPTION "Writing the value startSaveToFile to this object 
                     will commit the current configuration to the config.ini 
                     file on the hard drive or CompactFlash. If a read returns 
                     the value savingConfigToFile, the files are being saved; 
                     the save may not have been initiated by an SNMP set."
                REFERENCE   " -- "
        ::= { ncSystemConfMisc 1}

ncBackgroundPurgeEnable OBJECT-TYPE
                SYNTAX  INTEGER
                        {
                         disable     (1),
                         enable      (2)
                        }
                ACCESS  read-write
                STATUS  mandatory
                DESCRIPTION "Writing to this object will enable or disable the 
                             background purging of questionable settops from 
                             the settop database."
                REFERENCE   " -- "
        ::= { ncSystemConfMisc 2}

ncSoftwareVersion OBJECT-TYPE
                SYNTAX  DisplayString
                ACCESS  read-only
                STATUS  mandatory
                DESCRIPTION "This string object contains the NC1500 core 
                             software version."
                REFERENCE   " -- "
        ::= { ncSystemConfMisc 3}

ncUploadFiles OBJECT-TYPE
                SYNTAX  INTEGER
                        {
                         notSending                   (1),
                         preparingFiles               (2),
                         sending                      (3),
                         sendDatabaseFiles            (4),
                         sendLogFiles                 (5),
                         sendDatabaseAndLogFiles      (6),
                         sendTrapLogFiles             (7)
                        }
                ACCESS  read-write
                STATUS  mandatory
                DESCRIPTION "This object provides the application level 
                             handshaking needed to prepare and transfer 
                             various files from the NC 1500 to an FTP client."
                REFERENCE   " -- "
        ::= { ncSystemConfMisc 4}

ncBackgroundPathTestEnable OBJECT-TYPE
                SYNTAX  INTEGER
                        {
                         disable     (1),
                         enable      (2)
                        }
                ACCESS  read-write
                STATUS  mandatory
                DESCRIPTION "Writing to this object will enable or disable the 
			     the Path Test logic."
                REFERENCE   " -- "
        ::= { ncSystemConfMisc 5}

ncSystemStatusOne OBJECT-TYPE
                SYNTAX  INTEGER
                ACCESS  read-only
                STATUS  mandatory
                DESCRIPTION "Reading this will provide status for some of the tabs on the JC"
                REFERENCE   " -- "
        ::= { ncSystemConfMisc 6}
        
ncSettopHostIp OBJECT-TYPE
                SYNTAX  IpAddress
                ACCESS  read-write
                STATUS  mandatory
                DESCRIPTION "This value, along with the Settop Subnet Mask will
                             define the range of IP addressesthe NC1500 is 
                             allowed to assign to settops."
                REFERENCE   " -- "
        ::= { ncSystemConfMisc 7 }
        
ncSettopSubnetMask OBJECT-TYPE
                SYNTAX  IpAddress
                ACCESS  read-write
                STATUS  mandatory
                DESCRIPTION "This value, along with the Settop Host IP will
                             define the range of IP addressesthe NC1500 is 
                             allowed to assign to settops."
                REFERENCE   " -- "
        ::= { ncSystemConfMisc 8 }

ncSettopNetworkBcIp OBJECT-TYPE
                SYNTAX  IpAddress
                ACCESS  read-only
                STATUS  mandatory
                DESCRIPTION "This value will be a Broadcast receipt IP
                             for the application interface.  This value will be
                             calculated by the NC1500."
                REFERENCE   " -- "
        ::= { ncSystemConfMisc 9 }
        
ncSettopNetworkBcIpEnable OBJECT-TYPE
                SYNTAX  INTEGER
                        {
                         disable     (1),
                         enable      (2)
                        }
                ACCESS  read-write
                STATUS  mandatory
                DESCRIPTION "Writing to this object will enable or disable the 
                             Network Broadcast IP for receipt of data."
                REFERENCE   " -- "
        ::= { ncSystemConfMisc 10 }

ncSettopSinglecastBcIp OBJECT-TYPE
                SYNTAX  IpAddress
                ACCESS  read-only
                STATUS  mandatory
                DESCRIPTION "This value will be a Singlecast ABA receipt IP
                             for the application interface.  This value will be
                             set by the user, being ANY singlecast IP address."
                REFERENCE   " -- "
        ::= { ncSystemConfMisc 11 }
        
ncSettopSinglecastBcIpEnable OBJECT-TYPE
                SYNTAX  INTEGER
                        {
                         disable     (1),
                         enable      (2)
                        }
                ACCESS  read-write
                STATUS  mandatory
                DESCRIPTION "Writing to this object will enable or disable the 
                             Singlecast ABA IP for receipt of data."
                REFERENCE   " -- "
        ::= { ncSystemConfMisc 12 }

ncSettopMulticastIp1 OBJECT-TYPE
                SYNTAX  IpAddress
                ACCESS  read-write
                STATUS  mandatory
                DESCRIPTION "This value will be a Singlecast ABA receipt IP
                             for the application interface.  This value will be
                             set by the user, being ANY singlecast IP address."
                REFERENCE   " -- "
        ::= { ncSystemConfMisc 13 }
        
ncSettopMulticastIp1Enable OBJECT-TYPE
                SYNTAX  INTEGER
                        {
                         disable     (1),
                         enable      (2)
                        }
                ACCESS  read-write
                STATUS  mandatory
                DESCRIPTION "Writing to this object will enable or disable the 
                             Singlecast ABA IP for receipt of data."
                REFERENCE   " -- "
        ::= { ncSystemConfMisc 14 }

ncSettopMulticastIp2 OBJECT-TYPE
                SYNTAX  IpAddress
                ACCESS  read-write
                STATUS  mandatory
                DESCRIPTION "This value will be a Singlecast ABA receipt IP
                             for the application interface.  This value will be
                             set by the user, being ANY singlecast IP address."
                REFERENCE   " -- "
        ::= { ncSystemConfMisc 15 }
        
ncSettopMulticastIp2Enable OBJECT-TYPE
                SYNTAX  INTEGER
                        {
                         disable     (1),
                         enable      (2)
                        }
                ACCESS  read-write
                STATUS  mandatory
                DESCRIPTION "Writing to this object will enable or disable the 
                             Singlecast ABA IP for receipt of data."
                REFERENCE   " -- "
        ::= { ncSystemConfMisc 16 }

ncSettopMulticastIp3 OBJECT-TYPE
                SYNTAX  IpAddress
                ACCESS  read-write
                STATUS  mandatory
                DESCRIPTION "This value will be a Singlecast ABA receipt IP
                             for the application interface.  This value will be
                             set by the user, being ANY singlecast IP address."
                REFERENCE   " -- "
        ::= { ncSystemConfMisc 17 }
        
ncSettopMulticastIp3Enable OBJECT-TYPE
                SYNTAX  INTEGER
                        {
                         disable     (1),
                         enable      (2)
                        }
                ACCESS  read-write
                STATUS  mandatory
                DESCRIPTION "Writing to this object will enable or disable the 
                             Singlecast ABA IP for receipt of data."
                REFERENCE   " -- "
        ::= { ncSystemConfMisc 18 }

ncSettopMulticastIp4 OBJECT-TYPE
                SYNTAX  IpAddress
                ACCESS  read-write
                STATUS  mandatory
                DESCRIPTION "This value will be a Singlecast ABA receipt IP
                             for the application interface.  This value will be
                             set by the user, being ANY singlecast IP address."
                REFERENCE   " -- "
        ::= { ncSystemConfMisc 19 }
        
ncSettopMulticastIp4Enable OBJECT-TYPE
                SYNTAX  INTEGER
                        {
                         disable     (1),
                         enable      (2)
                        }
                ACCESS  read-write
                STATUS  mandatory
                DESCRIPTION "Writing to this object will enable or disable the 
                             Singlecast ABA IP for receipt of data."
                REFERENCE   " -- "
        ::= { ncSystemConfMisc 20 }
        
ncSettopActualSupported OBJECT-TYPE
                SYNTAX  INTEGER
                ACCESS  read-only
                STATUS  mandatory
                DESCRIPTION "This will be calculated by the NC & will be the 
                             number of settops that the Settop IP range
                             is capable of supporting before running out of IPs"
                REFERENCE   " -- "
        ::= { ncSystemConfMisc 21 }
        
ncBroadcastMessageInterval OBJECT-TYPE
                SYNTAX  INTEGER
                ACCESS  read-write
                STATUS  mandatory
                DESCRIPTION "This will determine the interval between messages
                             that are transmitted to the settops after they are
                             received on any of the application broadcast ports"
                REFERENCE   " -- "
        ::= { ncSystemConfMisc 22 }

ncTaskMonitoringRebootEnable OBJECT-TYPE
                SYNTAX  INTEGER
                        {
                         disable     (1),
                         enable      (2)
                        }
                ACCESS  read-write
                STATUS  mandatory
                DESCRIPTION "Writing to this object will enable or disable the 
                             reboot operation of the Task Monitoring feature.
                             Task Monitoring reports to the shell and issues
                             traps but doesn't reboot if this is disabled."
                REFERENCE   " -- "
        ::= { ncSystemConfMisc 23 }
        

--*****************************************
--
-- NC System Group
--   NC System Configuration Group
--     NC System Configuration Date and Time Group
--
--*****************************************

ncDateAndTime OBJECT-TYPE
                SYNTAX  DisplayString
                ACCESS  read-write
                STATUS  mandatory
                DESCRIPTION "NC 1500 date and time."
                REFERENCE   " -- "
        ::= { ncDateAndTimeConf 1}

--*****************************************
--
-- NC System Group
--   NC System Configuration Group
--     NC System Configuration DNS Server Config
--
--*****************************************

ncDNSServerIP OBJECT-TYPE
                SYNTAX  IpAddress
                ACCESS  read-write
                STATUS  mandatory
                DESCRIPTION "IP Address of the DNS Server.  A 
                             reboot is required for a change to 
                             the parameter to take affect."
                REFERENCE   " -- "
        ::= { ncDNSServerConf 1}

ncDNSDomainName OBJECT-TYPE
                SYNTAX  DisplayString
                ACCESS  read-write
                STATUS  mandatory
                DESCRIPTION "Domain Name of the DNS Server.  A 
                             reboot is required for a change to 
                             the parameter to take affect."
                REFERENCE   " -- "
        ::= { ncDNSServerConf 2}

--*****************************************
--
-- NC System Group
--   NC RPD Configuration Group
--     NC RPD Configuration Table Group
--
--*****************************************

ncRpdConfTable OBJECT-TYPE
                SYNTAX  SEQUENCE OF NcRpdConfTableEntry
                ACCESS  not-accessible
                STATUS  mandatory
                DESCRIPTION "This table is used to configure the RPD chassis
                             connected to NC1500."
                REFERENCE   " -- "
        ::= { ncRpdConf 1 }

ncRpdConfTableEntry OBJECT-TYPE
                SYNTAX  NcRpdConfTableEntry
                ACCESS  not-accessible
                STATUS  mandatory
                DESCRIPTION "A row in the NC1500 RPD configuration table."
                REFERENCE   " -- "
                INDEX  { ncRpdConfRpdIndex }
        ::= { ncRpdConfTable 1}
 
NcRpdConfTableEntry ::= SEQUENCE 
       {
       ncRpdConfRpdIndex    INTEGER,
       ncRpdIpAddress       IpAddress,
       ncRpdUdpPortNumber   INTEGER
       }

ncRpdConfRpdIndex OBJECT-TYPE
                SYNTAX  INTEGER(1..32)
                ACCESS  not-accessible
                STATUS  mandatory
                DESCRIPTION "Table index: RPD reference number (1 - 32)."
                REFERENCE   " -- "
        ::= { ncRpdConfTableEntry 1 }

ncRpdIpAddress OBJECT-TYPE
                SYNTAX  IpAddress
                ACCESS  read-write
                STATUS  mandatory
                DESCRIPTION "The IP address for this RPD.  A reboot is required 
                             for a change to the parameter to take affect."
                REFERENCE   " -- "
        ::= { ncRpdConfTableEntry 2 }

ncRpdUdpPortNumber OBJECT-TYPE
                SYNTAX  INTEGER
                ACCESS  read-write
                STATUS  mandatory
                DESCRIPTION "The NC1500's UDP port number used to receive data 
                             from this RPD.  A reboot is required for a change 
                             to the parameter to take affect."
                REFERENCE   " -- "
        ::= { ncRpdConfTableEntry 3 }

--*****************************************
--
-- NC System Group
--   NC RPD Configuration Group
--     NC RPD Demod Configuration Table Group
--
--*****************************************

ncRpdDemodConfTable OBJECT-TYPE
                SYNTAX  SEQUENCE OF NcRpdDemodConfTableEntry
                ACCESS  not-accessible
                STATUS  mandatory
                DESCRIPTION "This table is used to configure the RPD 
                             demodulators. Each RPD has up to 6 demodulators."
                REFERENCE   " -- "
        ::= { ncRpdConf 2 }

ncRpdDemodConfTableEntry OBJECT-TYPE
                SYNTAX  NcRpdDemodConfTableEntry
                ACCESS  not-accessible
                STATUS  mandatory
                DESCRIPTION "A row in the NC1500 RPD demod configuration table."
                REFERENCE   " -- "
                INDEX  { ncDemodConfRpdIndex, ncDemodConfDemodIndex }
        ::= { ncRpdDemodConfTable 1}
 
NcRpdDemodConfTableEntry ::= SEQUENCE 
       {
       ncDemodConfRpdIndex           INTEGER,
       ncDemodConfDemodIndex         INTEGER,
       ncDemodReturnPathId           INTEGER,
       ncDemodDownStreamPathId       INTEGER,
       ncDemodTunedFrequency         INTEGER,
       ncDemodChannelType            INTEGER
       }

ncDemodConfRpdIndex OBJECT-TYPE
                SYNTAX  INTEGER(1..32)
                ACCESS  not-accessible
                STATUS  mandatory
                DESCRIPTION "The first index is the RPD reference number."
                REFERENCE   " -- "
        ::= { ncRpdDemodConfTableEntry 1 }

ncDemodConfDemodIndex OBJECT-TYPE
                SYNTAX  INTEGER(1..6)
                ACCESS  not-accessible
                STATUS  mandatory
                DESCRIPTION "The second index is the demod number within 
                             the RPD indexed above."
                REFERENCE   " -- "
        ::= { ncRpdDemodConfTableEntry 2 }

ncDemodReturnPathId OBJECT-TYPE
                SYNTAX  INTEGER
                ACCESS  read-write
                STATUS  mandatory
                DESCRIPTION "The return path associated with this demod 
                             channel."
                REFERENCE   " -- "
        ::= { ncRpdDemodConfTableEntry 3 }

ncDemodDownStreamPathId OBJECT-TYPE
                SYNTAX  INTEGER
                ACCESS  read-write
                STATUS  mandatory
                DESCRIPTION "The downstream path ID associated with this demod
                             channel."
                REFERENCE   " -- "
        ::= { ncRpdDemodConfTableEntry 4 }

ncDemodTunedFrequency OBJECT-TYPE
                SYNTAX  INTEGER
                ACCESS  read-write
                STATUS  mandatory
                DESCRIPTION "The frequency (in Hz) assigned to this demod 
                             channel."
                REFERENCE   " -- "
        ::= { ncRpdDemodConfTableEntry 5 }

ncDemodChannelType OBJECT-TYPE
                SYNTAX  INTEGER
                        {
                         demodNotInUse                 (1),
                         serviceOnlyChannel            (2),
                         dataChannel                   (3),
                         combinedServiceDataChannel    (4),
                         dedicatedPollingChannel       (5)
                        }
                ACCESS  read-write
                STATUS  mandatory
                DESCRIPTION "The type (use) of this demod channel."
                REFERENCE   " -- "
        ::= { ncRpdDemodConfTableEntry 6 }

--*****************************************
--
-- NC System Group
--   NC OM Configuration Group
--     NC OM Configuration Table Group
--
--*****************************************

ncOmConfTable OBJECT-TYPE
                SYNTAX  SEQUENCE OF NcOmConfTableEntry
                ACCESS  not-accessible
                STATUS  mandatory
                DESCRIPTION "This table is used to configure the OM chassis
                             connected to NC1500."
                REFERENCE   " -- "
        ::= { ncOmConf 1 }

ncOmConfTableEntry OBJECT-TYPE
                SYNTAX  NcOmConfTableEntry
                ACCESS  not-accessible
                STATUS  mandatory
                DESCRIPTION "A row in the NC1500 OM configuration table."
                REFERENCE   " -- "
                INDEX  { ncOmConfOmIndex }
        ::= { ncOmConfTable 1}
 
NcOmConfTableEntry ::= SEQUENCE 
       {
       ncOmConfOmIndex        INTEGER,
       ncOmIpAddress          IpAddress,
       ncOmUdpPortNumber      INTEGER,
       ncOmDownStreamPathId   INTEGER,
       ncOmTransportType      INTEGER,
       ncOmMacSignalingPid    INTEGER,
       ncOmDataPid            INTEGER,
       ncOmBandWidth          INTEGER
       }

ncOmConfOmIndex OBJECT-TYPE
                SYNTAX  INTEGER(1..10)
                ACCESS  not-accessible
                STATUS  mandatory
                DESCRIPTION "The OM reference number (1 - 10)."
                REFERENCE   " -- "
        ::= { ncOmConfTableEntry 1 }

ncOmIpAddress OBJECT-TYPE
                SYNTAX  IpAddress
                ACCESS  read-write
                STATUS  mandatory
                DESCRIPTION "The IP address of the OM.  A reboot is required 
                             for a change to the parameter to take affect."
                REFERENCE   " -- "
        ::= { ncOmConfTableEntry 2 }

ncOmUdpPortNumber OBJECT-TYPE
                SYNTAX  INTEGER
                ACCESS  read-write
                STATUS  mandatory
                DESCRIPTION "The UDP input port number of the OM.  A reboot 
                             is required for a change to the parameter to 
                             take affect."
                REFERENCE   " -- "
        ::= { ncOmConfTableEntry 3 }

ncOmDownStreamPathId OBJECT-TYPE
                SYNTAX  INTEGER
                ACCESS  read-write
                STATUS  mandatory
                DESCRIPTION "The downstream path ID associated with this OM."
                REFERENCE   " -- "
        ::= { ncOmConfTableEntry 4 }

ncOmTransportType OBJECT-TYPE
                SYNTAX  INTEGER
                        {
                         outOfBand    (1),
                         inBand       (2)
                        }
                ACCESS  read-write
                STATUS  mandatory
                DESCRIPTION "The downstream transport type for this OM."
                REFERENCE   " -- "
        ::= { ncOmConfTableEntry 5 }

ncOmMacSignalingPid OBJECT-TYPE
                SYNTAX  INTEGER
                ACCESS  read-write
                STATUS  mandatory
                DESCRIPTION "The downstream MAC layer signaling PID associated 
                             with this OM."
                REFERENCE   " -- "
        ::= { ncOmConfTableEntry 6 }

ncOmDataPid OBJECT-TYPE
                SYNTAX  INTEGER
                ACCESS  read-write
                STATUS  mandatory
                DESCRIPTION "The downstream application server data PID
                             associated with this OM."
                REFERENCE   " -- "
        ::= { ncOmConfTableEntry 7 }

ncOmBandWidth OBJECT-TYPE
                SYNTAX  INTEGER
                ACCESS  read-write
                STATUS  mandatory
                DESCRIPTION "The downstream bandwidth that the NC can use with
                             this OM. This sets the NC throttling rate for this
                             OM."
                REFERENCE   " -- "
        ::= { ncOmConfTableEntry 8 }

--*****************************************
--
-- NC System Group
--   NC Periodic Broadcast Conf Group
--     NC Broadcast Task Conf Group
--
--*****************************************

ncDefaultConfigMsgRate OBJECT-TYPE
                SYNTAX  INTEGER
                ACCESS  read-write
                STATUS  mandatory
                DESCRIPTION "The rate of tranmission for the Default 
                             Configuration Message (in seconds)."
                REFERENCE   " -- "
        ::= { ncBroadcastTaskConf 1 }

ncContChannelMsgRate OBJECT-TYPE
                SYNTAX  INTEGER
                ACCESS  read-write
                STATUS  mandatory
                DESCRIPTION "The rate of transmission for the Contention 
                             Channel List Message (in seconds)."
                REFERENCE   " -- "
        ::= { ncBroadcastTaskConf 2 }

--*****************************************
--
-- NC System Group
--   NC Periodic Broadcast Conf Group
--     NC Default Config Message Group
--
--*****************************************

ncPowerRetryCount OBJECT-TYPE
                SYNTAX  INTEGER
                ACCESS  read-write
                STATUS  mandatory
                DESCRIPTION "This object specifies the maximum number of times 
                             a settop will try to enter the network at a given
                             power level before automatically changing power 
                             levels."
                REFERENCE   " -- "
        ::= { ncDefaultConfigMsg 1 }

ncMaximumPowerLevel OBJECT-TYPE
                SYNTAX  INTEGER
                ACCESS  read-write
                STATUS  mandatory
                DESCRIPTION "Maximum transmit power level of a settop (in
                             dBmV).  When adjusting its power level, a settop
                             will not transmit more this power level."
                REFERENCE   " -- "
        ::= { ncDefaultConfigMsg 2 }

ncMinimumPowerLevel OBJECT-TYPE
                SYNTAX  INTEGER
                ACCESS  read-write
                STATUS  mandatory
                DESCRIPTION "Minimum transmit power level of a settop (in
                             dBmV).  When adjusting its power level, a settop
                             will not transmit less than this power level."
                             
                REFERENCE   " -- "
        ::= { ncDefaultConfigMsg 3 }

ncPowerIncrement OBJECT-TYPE
                SYNTAX  INTEGER
                ACCESS  read-write
                STATUS  mandatory
                DESCRIPTION "The amount by which a settop will increase its
                             power when it reaches PowerRetryCount (in 0.5dB 
                             steps)."
                REFERENCE   " -- "
        ::= { ncDefaultConfigMsg 4 }

ncIdleInterval OBJECT-TYPE
                SYNTAX  INTEGER
                ACCESS  read-write
                STATUS  mandatory
                DESCRIPTION "The rate (in seconds) at which a setop will send 
                             MAC Idle Messages when it has not sent anything 
                             else within the Idle Interval period. A value of 0 
                             signifies that Idle Messages should not be sent."
                REFERENCE   " -- "
        ::= { ncDefaultConfigMsg 5 }

ncNetworkEntryDelay OBJECT-TYPE
                SYNTAX  INTEGER
                ACCESS  read-write
                STATUS  mandatory
                DESCRIPTION "A settop will wait a random time interval 
                             between 0 and this number (in seconds) before 
                             attempting to enter the interactive network."
                REFERENCE   " -- "
        ::= { ncDefaultConfigMsg 6 }

ncInitTimeout OBJECT-TYPE
                SYNTAX  INTEGER
                ACCESS  read-write
                STATUS  mandatory
                DESCRIPTION "A settop will wait this time (in seconds) for 
                             either a MAC Sign On Request or a MAC Logical 
                             Address message before restarting initialization."
                REFERENCE   " -- "
        ::= { ncDefaultConfigMsg 7 }

--*****************************************
--
-- NC System Group
--   NC Periodic Broadcast Conf Group
--     NC Contention Channel Message Group
--
--*****************************************

ncBackoffTimeUnit OBJECT-TYPE
                SYNTAX  INTEGER
                ACCESS  read-write
                STATUS  mandatory
                DESCRIPTION "This is the base back-off time used in the ALOHA 
                             backoff algorithm.  Expressed in microseconds."
                REFERENCE   " -- "
        ::= { ncContChannelMsg 1 }

ncBackoffMax OBJECT-TYPE
                SYNTAX  INTEGER
                ACCESS  read-write
                STATUS  mandatory
                DESCRIPTION "This is the largest upper limit for the exponent
                             in the ALOHA backoff algorithm."
                REFERENCE   " -- "
        ::= { ncContChannelMsg 2 }

ncCellAbortCount OBJECT-TYPE
                SYNTAX  INTEGER
                ACCESS  read-write
                STATUS  mandatory
                DESCRIPTION "This is the maximum number of times a settop will 
                             attempt to send a MAC cell upstream before aborting
                             and reporting an error."
                REFERENCE   " -- "
        ::= { ncContChannelMsg 3 }

ncMacAbortCount OBJECT-TYPE
                SYNTAX  INTEGER
                ACCESS  read-write
                STATUS  mandatory
                DESCRIPTION "This is the number of consecutive times
                             ncCellAbortCount may be reached before the settop
                             declares the MAC layer unavailable."
                REFERENCE   " -- "
        ::= { ncContChannelMsg 4 }

ncBackoffOffset OBJECT-TYPE
                SYNTAX  INTEGER
                ACCESS  read-write
                STATUS  mandatory
                DESCRIPTION "This is an offset which is added to the exponent 
                             in the ALOHA backoff algorithm."
                REFERENCE   " -- "
        ::= { ncContChannelMsg 5 }

ncAckTimeout OBJECT-TYPE
                SYNTAX  INTEGER
                ACCESS  read-write
                STATUS  mandatory
                DESCRIPTION "This is the time window (in 10's of milliseconds) during 
                             which the setop can expect to receive an 
                             acknowledgment for a cell transmitted upstream.  A
                             value of 10 represents 100 milliseconds."
                REFERENCE   " -- "
        ::= { ncContChannelMsg 6 }

--*****************************************
--
-- NC System Group
--   NC Diagnostics Group
--     NC Connection Test Group
--
--*****************************************

ncDiagConnStart OBJECT-TYPE
                SYNTAX  INTEGER
                        {
                         pingTestStart          (1),
                         pingTestInProgress     (2),
                         pingTestComplete       (3)
                        }
                ACCESS  read-write
                STATUS  mandatory
                DESCRIPTION "Writing pingTestStart to this object starts the 
                             NC 1500 connectivity test.  Reading the value 
                             pingTestInProgress indicates that the ping test is 
                             currently in progress.  Reading the value 
                             pingTestComplete indicates that the ping test is 
                             not active and has been completed if it was 
                             previously started."
                REFERENCE   " -- "
        ::= { ncDiagConnectTest 1 }

ncDiagConnResultTable OBJECT-TYPE
                SYNTAX  SEQUENCE OF NcDiagConnResultTableEntry
                ACCESS  not-accessible
                STATUS  mandatory
                DESCRIPTION "This table is used to report the connection status
                             of OMs and RPDs associated with this NC1500."
                REFERENCE   " -- "
        ::= { ncDiagConnectTest 2 }

ncDiagConnResultTableEntry OBJECT-TYPE
                SYNTAX  NcDiagConnResultTableEntry
                ACCESS  not-accessible
                STATUS  mandatory
                DESCRIPTION "A row in the NC1500 Connection test result table."
                REFERENCE   " -- "
                INDEX  { ncDiagConnResultIndex }
        ::= { ncDiagConnResultTable 1}
 
NcDiagConnResultTableEntry ::= SEQUENCE 
       {
       ncDiagConnResultIndex            INTEGER,
       ncDiagConnResultDac              INTEGER,
       ncDiagConnResultOmOne            INTEGER,
       ncDiagConnResultOmTwo            INTEGER,
       ncDiagConnResultOmThree          INTEGER,
       ncDiagConnResultOmFour           INTEGER,
       ncDiagConnResultOmFive           INTEGER,
       ncDiagConnResultOmSix            INTEGER,
       ncDiagConnResultOmSeven          INTEGER,
       ncDiagConnResultOmEight          INTEGER,
       ncDiagConnResultOmNine           INTEGER,
       ncDiagConnResultOmTen            INTEGER,
       ncDiagConnResultRpdOne           INTEGER,
       ncDiagConnResultRpdTwo           INTEGER,
       ncDiagConnResultRpdThree         INTEGER,
       ncDiagConnResultRpdFour          INTEGER,
       ncDiagConnResultRpdFive          INTEGER,
       ncDiagConnResultRpdSix           INTEGER,
       ncDiagConnResultRpdSeven         INTEGER,
       ncDiagConnResultRpdEight         INTEGER,
       ncDiagConnResultRpdNine          INTEGER,
       ncDiagConnResultRpdTen           INTEGER,
       ncDiagConnResultRpdEleven        INTEGER,
       ncDiagConnResultRpdTwelve        INTEGER,
       ncDiagConnResultRpdThirteen      INTEGER,
       ncDiagConnResultRpdFourteen      INTEGER,
       ncDiagConnResultRpdFifteen       INTEGER,
       ncDiagConnResultRpdSixteen       INTEGER,
       ncDiagConnResultRpdSeventeen     INTEGER,
       ncDiagConnResultRpdEighteen      INTEGER,
       ncDiagConnResultRpdNineteen      INTEGER,
       ncDiagConnResultRpdTwenty        INTEGER,
       ncDiagConnResultRpdTwentyone     INTEGER,
       ncDiagConnResultRpdTwentytwo     INTEGER,
       ncDiagConnResultRpdTwentythree   INTEGER,
       ncDiagConnResultRpdTwentyfour    INTEGER,
       ncDiagConnResultRpdTwentyfive    INTEGER,
       ncDiagConnResultRpdTwentysix     INTEGER,
       ncDiagConnResultRpdTwentyseven   INTEGER,
       ncDiagConnResultRpdTwentyeight   INTEGER,
       ncDiagConnResultRpdTwentynine    INTEGER,
       ncDiagConnResultRpdThirty        INTEGER,
       ncDiagConnResultRpdThirtyone     INTEGER,
       ncDiagConnResultRpdThirtytwo     INTEGER
       }

ncDiagConnResultIndex OBJECT-TYPE
                SYNTAX  INTEGER(1..44)
                ACCESS  not-accessible
                STATUS  mandatory
                DESCRIPTION "The row index number."
                REFERENCE   " -- "
        ::= { ncDiagConnResultTableEntry 1 }

ncDiagConnResultDac OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "This NC1500 connectivity test result for DAC, 
                             RADD, or HMS."
                REFERENCE   " -- "
        ::= { ncDiagConnResultTableEntry 2 }

ncDiagConnResultOmOne OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for OM #1."
                REFERENCE   " -- "
        ::= { ncDiagConnResultTableEntry 3 }

ncDiagConnResultOmTwo OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for OM #2."
                REFERENCE   " -- "
        ::= { ncDiagConnResultTableEntry 4 }

ncDiagConnResultOmThree OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for OM #3."
                REFERENCE   " -- "
        ::= { ncDiagConnResultTableEntry 5 }

ncDiagConnResultOmFour OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for OM #4."
                REFERENCE   " -- "
        ::= { ncDiagConnResultTableEntry 6 }

ncDiagConnResultOmFive OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for OM #5."
                REFERENCE   " -- "
        ::= { ncDiagConnResultTableEntry 7 }

ncDiagConnResultOmSix OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for OM #6."
                REFERENCE   " -- "
        ::= { ncDiagConnResultTableEntry 8 }

ncDiagConnResultOmSeven OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for OM #7."
                REFERENCE   " -- "
        ::= { ncDiagConnResultTableEntry 9 }

ncDiagConnResultOmEight OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for OM #8."
                REFERENCE   " -- "
        ::= { ncDiagConnResultTableEntry 10 }

ncDiagConnResultOmNine OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for OM #9."
                REFERENCE   " -- "
        ::= { ncDiagConnResultTableEntry 11 }

ncDiagConnResultOmTen OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for OM #10."
                REFERENCE   " -- "
        ::= { ncDiagConnResultTableEntry 12 }

ncDiagConnResultRpdOne OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #1."
                REFERENCE   " -- "
        ::= { ncDiagConnResultTableEntry 13 }

ncDiagConnResultRpdTwo OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #2."
                REFERENCE   " -- "
        ::= { ncDiagConnResultTableEntry 14 }

ncDiagConnResultRpdThree OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #3."
                REFERENCE   " -- "
        ::= { ncDiagConnResultTableEntry 15 }

ncDiagConnResultRpdFour OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #4."
                REFERENCE   " -- "
        ::= { ncDiagConnResultTableEntry 16 }

ncDiagConnResultRpdFive OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #5."
                REFERENCE   " -- "
        ::= { ncDiagConnResultTableEntry 17 }

ncDiagConnResultRpdSix OBJECT-TYPE
                SYNTAX  INTEGER
                        {
                         pingResultUnconfigured        (1),
                         pingResultNoAnswer            (2),
                         
                         pingResultOk                  (3),
                         pingResultIncomplete          (4)
                        }
                ACCESS  read-only
                STATUS  mandatory
                DESCRIPTION "The NC1500 connectivity test result for RPD #6."
                REFERENCE   " -- "
        ::= { ncDiagConnResultTableEntry 18 }

ncDiagConnResultRpdSeven OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #7."
                REFERENCE   " -- "
        ::= { ncDiagConnResultTableEntry 19 }

ncDiagConnResultRpdEight OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #8."
                REFERENCE   " -- "
        ::= { ncDiagConnResultTableEntry 20 }

ncDiagConnResultRpdNine OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #9."
                REFERENCE   " -- "
        ::= { ncDiagConnResultTableEntry 21 }

ncDiagConnResultRpdTen OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #10."
                REFERENCE   " -- "
        ::= { ncDiagConnResultTableEntry 22 }

ncDiagConnResultRpdEleven OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #11."
                REFERENCE   " -- "
        ::= { ncDiagConnResultTableEntry 23 }

ncDiagConnResultRpdTwelve OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #12."
                REFERENCE   " -- "
        ::= { ncDiagConnResultTableEntry 24 }

ncDiagConnResultRpdThirteen OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #13."
                REFERENCE   " -- "
        ::= { ncDiagConnResultTableEntry 25 }

ncDiagConnResultRpdFourteen OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #14."
                REFERENCE   " -- "
        ::= { ncDiagConnResultTableEntry 26 }

ncDiagConnResultRpdFifteen OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #15."
                REFERENCE   " -- "
        ::= { ncDiagConnResultTableEntry 27 }

ncDiagConnResultRpdSixteen OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #16."
                REFERENCE   " -- "
        ::= { ncDiagConnResultTableEntry 28 }

ncDiagConnResultRpdSeventeen OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #17."
                REFERENCE   " -- "
        ::= { ncDiagConnResultTableEntry 29 }

ncDiagConnResultRpdEighteen OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #18."
                REFERENCE   " -- "
        ::= { ncDiagConnResultTableEntry 30 }

ncDiagConnResultRpdNineteen OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #19."
                REFERENCE   " -- "
        ::= { ncDiagConnResultTableEntry 31 }

ncDiagConnResultRpdTwenty OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #20."
                REFERENCE   " -- "
        ::= { ncDiagConnResultTableEntry 32 }

ncDiagConnResultRpdTwentyone OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #21."
                REFERENCE   " -- "
        ::= { ncDiagConnResultTableEntry 33 }

ncDiagConnResultRpdTwentytwo OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #22."
                REFERENCE   " -- "
        ::= { ncDiagConnResultTableEntry 34 }

ncDiagConnResultRpdTwentythree OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #23."
                REFERENCE   " -- "
        ::= { ncDiagConnResultTableEntry 35 }

ncDiagConnResultRpdTwentyfour OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #24."
                REFERENCE   " -- "
        ::= { ncDiagConnResultTableEntry 36 }

ncDiagConnResultRpdTwentyfive OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #25."
                REFERENCE   " -- "
        ::= { ncDiagConnResultTableEntry 37 }

ncDiagConnResultRpdTwentysix OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #26."
                REFERENCE   " -- "
        ::= { ncDiagConnResultTableEntry 38 }

ncDiagConnResultRpdTwentyseven OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #27."
                REFERENCE   " -- "
        ::= { ncDiagConnResultTableEntry 39 }

ncDiagConnResultRpdTwentyeight OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #28."
                REFERENCE   " -- "
        ::= { ncDiagConnResultTableEntry 40 }

ncDiagConnResultRpdTwentynine OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #29."
                REFERENCE   " -- "
        ::= { ncDiagConnResultTableEntry 41 }

ncDiagConnResultRpdThirty OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #30."
                REFERENCE   " -- "
        ::= { ncDiagConnResultTableEntry 42 }

ncDiagConnResultRpdThirtyone OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #31."
                REFERENCE   " -- "
        ::= { ncDiagConnResultTableEntry 43 }

ncDiagConnResultRpdThirtytwo OBJECT-TYPE
                SYNTAX  INTEGER
                        {
                         pingResultUnconfigured        (1),
                         pingResultNoAnswer            (2),
                         pingResultOk                  (3),
                         pingResultIncomplete          (4)
                        }
                ACCESS  read-only
                STATUS  mandatory
                DESCRIPTION "The NC1500 connectivity test result for RPD #32."
                REFERENCE   " -- "
        ::= { ncDiagConnResultTableEntry 44 }

--*****************************************
--
-- NC System Group
--   NC Diagnostics Group
--     NC Maintenance Group
--
--*****************************************

ncPurgeSettop OBJECT-TYPE
                SYNTAX  INTEGER
                        {
                         purgeInactive   (1),
                         settopPurge     (2)
                        }
                ACCESS  read-write
                STATUS  mandatory
                DESCRIPTION "Writing settopPurge clears the NC1500's settop 
                             database."
                REFERENCE   " -- "
        ::= { ncMaintenance 1 }

ncBackgroundQuestionSettop OBJECT-TYPE
                SYNTAX  INTEGER
                        {
                         checkInactive   (1),
                         checkActive     (2)
                        }
                ACCESS  read-write
                STATUS  mandatory
                DESCRIPTION "Writing checkActive enables passive checking for 
                             questionable settops. A questionable settop is one
                             for which no messages have been received within a
                             pre-determined period."
                REFERENCE   " -- "
        ::= { ncMaintenance 2 }

ncAutoRecoveryFlag OBJECT-TYPE
                SYNTAX  INTEGER
                        {
                         disable   (1),
                         enable    (2)
                        }
                ACCESS  read-write
                STATUS  mandatory
                DESCRIPTION "Writing to this object enables or disables the
                             Auto-recovery feature.  Auto-recovery attempts to
                             correct settop upstream/downstream path IDs to 
                             reflect the actual path pair on which the settop 
                             resides."
                REFERENCE   " -- "
        ::= { ncMaintenance 3 }
        
ncOpenAppPortsFlag OBJECT-TYPE
                SYNTAX  INTEGER
                        {
                         disable   (1),
                         enable    (2)
                        }
                ACCESS  read-write
                STATUS  mandatory
                DESCRIPTION "Writing to this object enables or disables the
                             ability to TFTP, FTP, TELNET, RLOGIN, HTTP, and 
                             SNMP access to the application interface."
                REFERENCE   " -- "
        ::= { ncMaintenance 4 }
        
ncClearRetryStats OBJECT-TYPE
                SYNTAX  INTEGER
                        {
                         clearNotInProgress   (1),
                         readyToClear         (2),
                         clearInProgress      (3)
                        }
                ACCESS  read-write
                STATUS  mandatory
                DESCRIPTION "Writing readyToClear to this object clears the 
                             upstream retry count values for all upstreams.  
                             Reading the value clearInProgress indicates 
                             that a clear is currently in progress.  Reading 
                             the value clearNotInProgress indicates that a 
                             clear is not active and has been completed if 
                             it was previously started."
                REFERENCE   " -- "
        ::= { ncMaintenance 5 }

ncUpTimeDays OBJECT-TYPE
                SYNTAX  INTEGER
                ACCESS  read-only
                STATUS  mandatory
                DESCRIPTION "NC 1500 Operational Time Elapsed - Days"
                REFERENCE   " -- "
        ::= { ncMaintenance 6}
        
ncUpTimeHours OBJECT-TYPE
                SYNTAX  INTEGER
                ACCESS  read-only
                STATUS  mandatory
                DESCRIPTION "NC 1500 Operational Time Elapsed - Hours"
                REFERENCE   " -- "
        ::= { ncMaintenance 7}
        
ncUpTimeMinutes OBJECT-TYPE
                SYNTAX  INTEGER
                ACCESS  read-only
                STATUS  mandatory
                DESCRIPTION "NC 1500 Operational Time Elapsed - Minutes"
                REFERENCE   " -- "
        ::= { ncMaintenance 8}
        
ncUpTimeSeconds OBJECT-TYPE
                SYNTAX  INTEGER
                ACCESS  read-only
                STATUS  mandatory
                DESCRIPTION "NC 1500 Operational Time Elapsed - Seconds"
                REFERENCE   " -- "
        ::= { ncMaintenance 9}
        
ncReduceIdleTime OBJECT-TYPE
                SYNTAX  INTEGER
                        {
                         disable   (1),
                         enable    (2)
                        }
                ACCESS  read-write
                STATUS  mandatory
                DESCRIPTION "writing to this will cause the NC to automatically
                             reduce the idle time to 5 minutes for a period of 
                             30 minutes to cause all of the settops in the
                             population to log back in quickly"
                REFERENCE   " -- "
        ::= { ncMaintenance 10}
        
ncStealthSignOn OBJECT-TYPE
                SYNTAX  INTEGER
                        {
                         disable   (1),
                         enable    (2)
                        }
                ACCESS  read-write
                STATUS  mandatory
                DESCRIPTION "writing to this will cause the NC to enable or
                             disable the Stealth Sign On feature.
                             Requires a Save/Reboot to take affect within the NC."
                REFERENCE   " -- "
        ::= { ncMaintenance 11}
        
ncXmitMcast40 OBJECT-TYPE
                SYNTAX  INTEGER
                        {
                         disable   (1),
                         enable    (2)
                        }
                ACCESS  read-write
                STATUS  mandatory
                DESCRIPTION "writing to this will cause the NC to enable or
                             disable the transmission of the MCast40 address.
                             Requires a Save/Reboot to take affect within the NC."
                REFERENCE   " -- "
        ::= { ncMaintenance 12}
        
ncTempSettopKey OBJECT-TYPE
                SYNTAX  DisplayString
                ACCESS  read-write
                STATUS  mandatory
                DESCRIPTION "storage location for the 75K settop key for
                             verification by the NC software."
                REFERENCE   " -- "
        ::= { ncMaintenance 13}
        
ncSettopKeyVerify OBJECT-TYPE
                SYNTAX  INTEGER
                        {
                         inactive    (1),
                         verify      (2),
                         keyValid    (3),
                         keyInvalid  (4)
                        }
                ACCESS  read-write
                STATUS  mandatory
                DESCRIPTION "writing to this will cause the NC to verify the 
                             key entered into the  variable.  The
                             NC will set this variable when the process is
                             complete, with the appropriate result.  If
                             successful, the NC will save the key into the 
                             config.ini file, otherwise it will do nothing.  In
                             either case, the ncTempSettopKey will be cleared.
                             Once it has been successfully verified, a reboot
                             will be required before it is activated."
                REFERENCE   " -- "
        ::= { ncMaintenance 14}
        
        
--*****************************************
--
-- NC System Group
--   NC Diagnostics Group
--     NC Settop Status Test Group
--
--*****************************************

ncSettopStatusStart OBJECT-TYPE
                SYNTAX  INTEGER
                        {
                         settopStatusTestStart        (1),
                         settopStatusTestInprogress   (2),
                         settopStatusTestComplete     (3)
                        }
                ACCESS  read-write
                STATUS  mandatory
                DESCRIPTION "Writing settopStatusTestStart to this object starts
                             the Settop Status Test. Reading the value 
                             settopStatusTestInProgress indicates that the 
                             Settop Status Test is currently in progress.  
                             Reading the value sttopStstuaTestComplete indicates
                             that the Settop Status Test is not active and has
                             been completed if it was previously started."
                REFERENCE   " -- "
        ::= { ncSettopStatusTest 1 }

ncSettopStatusIP OBJECT-TYPE
                SYNTAX  IpAddress
                ACCESS  read-write
                STATUS  mandatory
                DESCRIPTION "The IP address of the settop to test."
                REFERENCE   " -- "
        ::= { ncSettopStatusTest 2 }

ncSettopStatusResult OBJECT-TYPE
                SYNTAX  INTEGER
                        {
                         settopStatusResultIncomplete        (1),
                         settopStatusResultNoAnswer          (2),
                         settopStatusResultOk                (3),
                         settopStatusResultNotFound          (4)
                        }
                ACCESS  read-only
                STATUS  mandatory
                DESCRIPTION "The result of the Settop Status Test for the 
                             requested settop."
                REFERENCE   " -- "
        ::= { ncSettopStatusTest 3 }

--*****************************************
--
-- NC System Group
--   NC Diagnostics Group
--     NC Settop Status Summary Group
--
--*****************************************

ncSettopTotal OBJECT-TYPE
                SYNTAX  INTEGER
                ACCESS  read-only
                STATUS  mandatory
                DESCRIPTION "The total number of settops."
                REFERENCE   " -- "
        ::= { ncSettopStatusSummary 1 }

ncSettopGood OBJECT-TYPE
                SYNTAX  INTEGER
                ACCESS  read-only
                STATUS  mandatory
                DESCRIPTION "The number of good settops."
                REFERENCE   " -- "
        ::= { ncSettopStatusSummary 2 }

ncSettopQuestionable OBJECT-TYPE
                SYNTAX  INTEGER
                ACCESS  read-only
                STATUS  mandatory
                DESCRIPTION "The number of questionable settops"
                REFERENCE   " -- "
        ::= { ncSettopStatusSummary 3 }
        
ncSettopDatabaseSize OBJECT-TYPE
                SYNTAX  INTEGER
                ACCESS  read-only
                STATUS  mandatory
                DESCRIPTION "The maximum number of settops that will fit in the database"
                REFERENCE   " -- "
        ::= { ncSettopStatusSummary 4 }
        
--*****************************************
--
-- NC System Group
--   NC Diagnostics Group
--     NC Alarm Thresholds Summary Group
--
--*****************************************

ncRPDFramesDropThreshold OBJECT-TYPE            
                SYNTAX  INTEGER (0..50)
                ACCESS  read-write
                STATUS  mandatory
                DESCRIPTION "The rate of dropped RPD frames per minute 
                             that will trigger an alarm. Value ranges 
                             from 0 to 50 frames."
                REFERENCE   " -- "
        ::= { ncAlarmThresholds 1 }
        
ncRPDFramesDropCountPeriod OBJECT-TYPE            
                SYNTAX  INTEGER (0..10)
                ACCESS  read-write
                STATUS  mandatory
                DESCRIPTION "The length of time that the number of RPD
                             frames that are dropped should be measured 
                             over. Value ranges from 0 to 10 minutes."
                REFERENCE   " -- "
        ::= { ncAlarmThresholds 2 }
        
ncDMBandwidthThreshold OBJECT-TYPE            
                SYNTAX  INTEGER (0..200)
                ACCESS  read-write
                STATUS  mandatory
                DESCRIPTION "The percentage of nominal capacity (50 cells/sec)
                             measured over a period of one minute that
                             will cause an alarm to be generated. Value 
                             ranges from 0 to 200 percent."
                REFERENCE   " -- "
        ::= { ncAlarmThresholds 3 }
        
ncSettopDatabaseThreshold OBJECT-TYPE            
                SYNTAX  INTEGER (0..100)
                ACCESS  read-write
                STATUS  mandatory
                DESCRIPTION "The percentage of the settop database limit, 
                             which when exceeded will produce an alarm. 
                             Value ranges from 0 to 100 percent."
                REFERENCE   " -- "
        ::= { ncAlarmThresholds 4 }
        
ncUpstreamRetryThreshold OBJECT-TYPE            
                SYNTAX  INTEGER (0..100)
                ACCESS  read-write
                STATUS  mandatory
                DESCRIPTION "The percentage of cells received during a one 
                             minute period on a particular upstream path 
                             that required at least one retry to get through.
                             Value ranges from 0 to 100 percent."
                REFERENCE   " -- "
        ::= { ncAlarmThresholds 5 }
        
ncQuestionableSettopThreshold OBJECT-TYPE            
                SYNTAX  INTEGER
                ACCESS  read-write
                STATUS  mandatory
                DESCRIPTION "The percentage of questionable settops in the settop
                             database required to trigger an alarm."
                REFERENCE   " -- "
        ::= { ncAlarmThresholds 6 }
        
ncPurgedSettopThreshold OBJECT-TYPE            
                SYNTAX  INTEGER
                ACCESS  read-write
                STATUS  mandatory
                DESCRIPTION "The number of purged settops required to 
                             trigger an alarm."
                REFERENCE   " -- "
        ::= { ncAlarmThresholds 7 }
        
ncExcessDropDsMsgThreshold OBJECT-TYPE            
                SYNTAX  INTEGER (0..50)
                ACCESS  read-write
                STATUS  mandatory
                DESCRIPTION "The number of dropped downstream messages required to 
                             trigger an alarm. Value ranges from 0 to 50 messages."
                REFERENCE   " -- "
        ::= { ncAlarmThresholds 8 }
        
ncExcessDropDsMsgCountPeriod OBJECT-TYPE            
                SYNTAX  INTEGER (0..10)
                ACCESS  read-write
                STATUS  mandatory
                DESCRIPTION "The length of time that the number of Downstream
                             messages that are dropped should be measured 
                             over. Value ranges from 0 to 10 minutes."
                REFERENCE   " -- "
        ::= { ncAlarmThresholds 9 }
        
ncExcessDropDsMsgClearThreshold OBJECT-TYPE            
                SYNTAX  INTEGER (0..50)
                ACCESS  read-write
                STATUS  mandatory
                DESCRIPTION "The number of dropped downstream messages required to 
                             trigger an alarm. Value ranges from 0 to 50 messages."
                REFERENCE   " -- "
        ::= { ncAlarmThresholds 10 }
        
ncUpstreamBandwidthThreshold OBJECT-TYPE            
                SYNTAX  INTEGER (0..200)
                ACCESS  read-write
                STATUS  mandatory
                DESCRIPTION "The percentage of nominal capacity (50 cells/sec per DM)
                             measured over a period of one minute that
                             will cause an alarm to be generated. Values range from
                             0 to 200 percent."
                REFERENCE   " -- "
        ::= { ncAlarmThresholds 11 }
        
ncSettopDbThresholdSeverity OBJECT-TYPE            
                SYNTAX  INTEGER (2..6)
                ACCESS  read-write
                STATUS  mandatory
                DESCRIPTION "The severity level for the Settop Database Threshold 
                             Reached trap.  Where 2=INDETERMINATE, 3=WARNING, 
                             4=MINOR, 5=MAJOR, 6=CRITITCAL"
                REFERENCE   " -- "
        ::= { ncAlarmThresholds 12 }

--*****************************************
--
-- NC System Group
--   NC Diagnostics Group
--     NC Gateway and Destination Test Group
--
--*****************************************

ncGateNDestNumEntries OBJECT-TYPE
                SYNTAX  INTEGER(0..150)
                ACCESS  read-only
                STATUS  mandatory
                DESCRIPTION "This value is the number of entries in 
                             ncGateNDestTestResults."
                REFERENCE   " -- "
        ::= { ncGateNDestTest 1 }

ncGateNDestOverallStatus OBJECT-TYPE
                SYNTAX  INTEGER
                        {
                         ncGateNDestNoOverallAlarm           (1),
                         ncGateNDestOverallAlarm             (2)
                        }
                ACCESS  read-only
                STATUS  mandatory
                DESCRIPTION "This is the master alarm for the Gateways and 
                             Destinations connectivity test. If any device is
                             not communicating this alarm is set."
                REFERENCE   " -- "
        ::= { ncGateNDestTest 2 }

ncGateNDestTestStart OBJECT-TYPE
                SYNTAX  INTEGER
                        {
                         ncGateNDestTestStart        (1),
                         ncGateNDestTestInprogress   (2),
                         ncGateNDestTestComplete     (3)
                        }
                ACCESS  read-write
                STATUS  mandatory
                DESCRIPTION "Writing GateNDestTestStart to this object starts
                             the Gateways and Destinations connectivity test. 
                             Reading the value GateNDestTestInprogress 
                             indicates that the Gateways and Destinations 
                             connectivity test is currently in progress.  
                             Reading the value GateNDestTestComplete indicates
                             that the Gateways and Destinations connectivity 
                             test is not active and has been completed if it 
                             was previously started."
                REFERENCE   " -- "
        ::= { ncGateNDestTest 3 }

ncGateNDestPingRate OBJECT-TYPE
                SYNTAX  INTEGER
                ACCESS  read-write
                STATUS  mandatory
                DESCRIPTION "The interval in seconds before the next device is
                             tested in the Gateways and Destinations 
                             connectivity test. The valid range is 5 to 300 
                             seconds and 0 for no ping."
                REFERENCE   " -- "
        ::= { ncGateNDestTest 4 }

--*****************************************
--
-- NC System Group
--   NC Diagnostics Group
--     NC Gateway and Destination Test Results Group
--
--*****************************************

ncGateNDestTestResults OBJECT-TYPE
                SYNTAX  SEQUENCE OF NcGateNDestTestResultsEntry
                ACCESS  not-accessible
                STATUS  mandatory
                DESCRIPTION "This table is used to report the connection status
                             of Gateways and Destinations (application server)."
                REFERENCE   " -- "
        ::= { ncDiagnostics 7 }

ncGateNDestTestResultsEntry OBJECT-TYPE
                SYNTAX  NcGateNDestTestResultsEntry
                ACCESS  not-accessible
                STATUS  mandatory
                DESCRIPTION "A row in the NC1500 Gateways and Destinations 
                             connection test result table."
                REFERENCE   " -- "
                INDEX  { ncGateNDestTestResultsIndex }
        ::= { ncGateNDestTestResults 1}
 
NcGateNDestTestResultsEntry ::= SEQUENCE 
       {
       ncGateNDestTestResultsIndex      INTEGER,
       ncGateNDestIPAddrs               IpAddress,
       ncGateNDestTestResultsBitFields  INTEGER
       }

ncGateNDestTestResultsIndex OBJECT-TYPE
                SYNTAX  INTEGER(1..150)
                ACCESS  not-accessible
                STATUS  mandatory
                DESCRIPTION "The row index number."
                REFERENCE   " -- "
        ::= { ncGateNDestTestResultsEntry 1 }

ncGateNDestIPAddrs OBJECT-TYPE
                SYNTAX  IpAddress
                ACCESS  read-only
                STATUS  mandatory
                DESCRIPTION "The IP address of the device to test."
                REFERENCE   " -- "
        ::= { ncGateNDestTestResultsEntry 2 }

ncGateNDestTestResultsBitFields OBJECT-TYPE
                SYNTAX  INTEGER
                ACCESS  read-only
                STATUS  mandatory
                DESCRIPTION "The NC1500 Gateways and Destinations connection 
                             test results compressed into 4 bit fields. Bits
                             3-0 indicate network type. Bits 7-4 indicate 
                             device type. Bits 11-8 indicate most recent test
                             results. Bits 15-12 indicate previous test 
                             results."
                REFERENCE   " -- "
        ::= { ncGateNDestTestResultsEntry 3 }

--*****************************************
--
-- NC Up Stream Group
--   NC Up Stream Statistics Table Group
--
--*****************************************

ncUpStreamStatTable OBJECT-TYPE
                SYNTAX  SEQUENCE OF NcUpStreamStatTableEntry
                ACCESS  not-accessible
                STATUS  mandatory
                DESCRIPTION "This table is used to report the statistics 
                             information for each demod board within each 
                             RPD unit."
                REFERENCE   " -- "
        ::= { ncUpStream 1 }

ncUpStreamStatTableEntry OBJECT-TYPE
                SYNTAX  NcUpStreamStatTableEntry
                ACCESS  not-accessible
                STATUS  mandatory
                DESCRIPTION "A row in the NC1500 RPD demod statistics 
                             information report table."
                REFERENCE   " -- "
                INDEX  { ncUpStreamStatRpdIndex, ncUpStreamStatDemodIndex }
        ::= { ncUpStreamStatTable 1}
 
NcUpStreamStatTableEntry ::= SEQUENCE 
       {
       ncUpStreamStatRpdIndex         INTEGER,
       ncUpStreamStatDemodIndex       INTEGER,
       ncUpStatLastSecUncorrCells     Counter,
       ncUpStatLastSecCorrectCells    Counter,
       ncUpStatLastSecPerfectCells    Counter,
       ncUpStatLastSecCells           Counter,
       ncUpStatLoWinUncorrCells       Counter,
       ncUpStatLoWinCorrectCells      Counter,
       ncUpStatLoWinPerfectCells      Counter,
       ncUpStatLoWinCells             Counter,
       ncUpStatMinLoWinUncorrCells    Counter,
       ncUpStatMinLoWinCorrectCells   Counter,
       ncUpStatMinLoWinPerfectCells   Counter,
       ncUpStatMaxLoWinUncorrCells    Counter,
       ncUpStatMaxLoWinCorrectCells   Counter,
       ncUpStatMaxLoWinPerfectCells   Counter,
       ncUpStatAveLoWinUncorrCells    Counter,
       ncUpStatAveLoWinCorrectCells   Counter,
       ncUpStatAveLoWinPerfectCells   Counter,
       ncUpStatShWinUncorrCells       Counter,
       ncUpStatShWinCorrectCells      Counter,
       ncUpStatShWinPerfectCells      Counter,
       ncUpStatShWinCells             Counter,
       ncUpStatShWinMinUncorrCells    Counter,
       ncUpStatShWinMinCorrectCells   Counter,
       ncUpStatShWinMinPerfectCells   Counter,
       ncUpStatShWinMaxUncorrCells    Counter,
       ncUpStatShWinMaxCorrectCells   Counter,
       ncUpStatShWinMaxPerfectCells   Counter,
       ncUpStatShWinAveUncorrCells    Counter,
       ncUpStatShWinAveCorrectCells   Counter,
       ncUpStatShWinAvePerfectCells   Counter,
       ncUpStatUncorrCellsCntr        Counter,
       ncUpStatCorrectCellsCntr       Counter,
       ncUpStatPerfectCellsCntr       Counter,
       ncUpStatCellsCntr              Counter,
       ncUpStatLostRpdFrames          Counter,
       ncUpStatRpdFrames              Counter,
       ncUpStatLostRpdFramesCntr      Counter,
       ncUpStatRpdFramesCntr          Counter
       }

ncUpStreamStatRpdIndex OBJECT-TYPE
                SYNTAX  INTEGER(1..32)
                ACCESS  not-accessible
                STATUS  mandatory
                DESCRIPTION "The first index is the RPD reference number."
                REFERENCE   " -- "
        ::= { ncUpStreamStatTableEntry 1 }

ncUpStreamStatDemodIndex OBJECT-TYPE
                SYNTAX  INTEGER(1..6)
                ACCESS  not-accessible
                STATUS  mandatory
                DESCRIPTION "The second index is the demod number within each
                             RPD."
                REFERENCE   " -- "
        ::= { ncUpStreamStatTableEntry 2 }

ncUpStatLastSecUncorrCells OBJECT-TYPE
                SYNTAX  Counter
                ACCESS  read-only
                STATUS  mandatory
                DESCRIPTION "The number of Uncorrected Cells in all of
                             the RPD Frames recorded in a 1 second period. The 
                             RPD attempts to correct errors detected in the 
                             upstream cells. Those that can't be corrected are
                             marked as Uncorrected Cells.
                             (max. = 24 cells/frame * 125 frames/sec)"
                REFERENCE   " -- "
        ::= { ncUpStreamStatTableEntry 3 }

ncUpStatLastSecCorrectCells OBJECT-TYPE
                SYNTAX  Counter
                ACCESS  read-only
                STATUS  mandatory
                DESCRIPTION "The number of Corrected Cells in all of the RPD 
                             Frames recorded in a 1 second period. The RPD 
                             attempts to correct errors detected in the upstream
                             cells. Those that can be corrected are marked as 
                             Corrected Cells.
                             (max. = 24 cells/frame * 125 frames/sec)"
                REFERENCE   " -- "
        ::= { ncUpStreamStatTableEntry 4 }

ncUpStatLastSecPerfectCells OBJECT-TYPE
                SYNTAX  Counter
                ACCESS  read-only
                STATUS  mandatory
                DESCRIPTION "The number of Perfect Cells in all of the RPD 
                             Frames recorded in a 1 second period. The RPD marks
                             upstream cells that require no correction as 
                             Perfect Cells.
                             (max. = 24 cells/frame * 125 frames/sec)"
                REFERENCE   " -- "
        ::= { ncUpStreamStatTableEntry 5 }

ncUpStatLastSecCells OBJECT-TYPE
                SYNTAX  Counter
                ACCESS  read-only
                STATUS  mandatory
                DESCRIPTION "The total number of cells in all of the RPD Frames
                             recorded in a 1 second period.
                             (max. = 24 cells/frame * 125 frames/sec)"
                REFERENCE   " -- "
        ::= { ncUpStreamStatTableEntry 6 }

ncUpStatLoWinUncorrCells OBJECT-TYPE
                SYNTAX  Counter
                ACCESS  read-only
                STATUS  mandatory
                DESCRIPTION "The number of Uncorrected Cells in all of the RPD 
                             Frames recorded in a period of time referred to as 
                             a long window. The period of the long window is 
                             hard-coded as 1 hour.  The number of Uncorrected 
                             Cells is adjusted with a new value 1 time per 
                             second. Measurements more than 1 hour old are 
                             removed from the calculations. The RPD attempts to 
                             correct errors detected in the upstream cells. 
                             Those that can't be corrected are marked as 
                             Uncorrected Cells.
                             (max. = 24 cells/frame * 125 frames/sec * 
                              60 seconds * 60 minutes )"
                REFERENCE   " -- "
        ::= { ncUpStreamStatTableEntry 7 }

ncUpStatLoWinCorrectCells OBJECT-TYPE
                SYNTAX  Counter
                ACCESS  read-only
                STATUS  mandatory
                DESCRIPTION "The number of Corrected Cells in all of the RPD 
                             Frames recorded in a period of time referred to as 
                             a long window. The period of the long window is 
                             hard-coded as 1 hour.  The number of Corrected 
                             Cells is adjusted with a new value 1 time per 
                             second. Measurements more than 1 hour old are 
                             removed from the calculations. The RPD attempts to
                             correct errors detected in the upstream cells. 
                             Those that can be corrected are marked as Corrected 
                             Cells.
                             (max. = 24 cells/frame * 125 frames/sec * 
                              60 seconds * 60 minutes )"
                REFERENCE   " -- "
        ::= { ncUpStreamStatTableEntry 8 }

ncUpStatLoWinPerfectCells OBJECT-TYPE
                SYNTAX  Counter
                ACCESS  read-only
                STATUS  mandatory
                DESCRIPTION "The number of Perfect Cells in all of the RPD 
                             Frames recorded in a period of time referred to as 
                             a long window. The period of the long window is 
                             hard-coded as 1 hour. The number of Perfect Cells 
                             is adjusted with a new value 1 time per second. 
                             Measurements more than 1 hour old are removed
                             from the calculations. The RPD marks upstream cells 
                             that require no correction as Perfect Cells.
                             (max. = 24 cells/frame * 125 frames/sec * 
                              60 seconds * 60 minutes )"
                REFERENCE   " -- "
        ::= { ncUpStreamStatTableEntry 9 }

ncUpStatLoWinCells OBJECT-TYPE
                SYNTAX  Counter
                ACCESS  read-only
                STATUS  mandatory
                DESCRIPTION "The total number of Cells in all of the RPD Frames 
                             recorded in a period of time referred to as a long
                             window. The period of the long window is hard-coded
                             as 1 hour. The number of Cells is adjusted with a 
                             new value 1 time per second. Measurements more than
                             1 hour old are removed from the calculations.
                             (max. = 24 cells/frame * 125 frames/sec * 
                              60 seconds * 60 minutes )"
                REFERENCE   " -- "
        ::= { ncUpStreamStatTableEntry 10 }

ncUpStatMinLoWinUncorrCells OBJECT-TYPE
                SYNTAX  Counter
                ACCESS  read-only
                STATUS  mandatory
                DESCRIPTION "A minimum based on the number of Uncorrected 
                             Cells in all of the RPD Frames recorded in a period
                             of time referred to as a long window. The period of
                             the long window is hard-coded as 1 hour. The number
                             of Uncorrected Cells is adjusted with a new value 1
                             time per second. Measurements more than 1 hour old
                             are removed from the calculations. Thus, there are
                             3600 values in the history. The minimum is the 
                             smallest of the 3600 values recorded.
                             (max. = 24 cells/frame * 125 frames/sec )"
                REFERENCE   " -- "
        ::= { ncUpStreamStatTableEntry 11 }

ncUpStatMinLoWinCorrectCells OBJECT-TYPE
                SYNTAX  Counter
                ACCESS  read-only
                STATUS  mandatory
                DESCRIPTION "A minimum based on the number of Corrected Cells in
                             all of the RPD1000 RPD Frames recorded in a period
                             of time referred to as a long window. The period of
                             the long window is hard-coded as 1 hour. The number
                             of Corrected Cells is adjusted with a new value 1 
                             time per second. Measurements more than 1 hour old
                             are removed from the calculations. Thus, there are
                             3600 values in the history. The minimum is the
                             smallest of the 3600 values recorded.
                             (max. = 24 cells/frame * 125 frames/sec )"
                REFERENCE   " -- "
        ::= { ncUpStreamStatTableEntry 12 }

ncUpStatMinLoWinPerfectCells OBJECT-TYPE
                SYNTAX  Counter
                ACCESS  read-only
                STATUS  mandatory
                DESCRIPTION "A minimum based on the number of Perfect Cells in
                             all of the RPD Frames recorded in a period of time
                             referred to as a long window. The period of the 
                             long window is hard-coded as 1 hour. The number of 
                             Perfect Cells is adjusted with a new value 1 time 
                             per second. Measurements more than 1 hour old are
                             removed from the calculations. Thus, there are 3600
                             values in the history. The minimum is the smallest
                             of the 3600 values recorded.
                             (max. = 24 cells/frame * 125 frames/sec )"
                REFERENCE   " -- "
        ::= { ncUpStreamStatTableEntry 13 }

ncUpStatMaxLoWinUncorrCells OBJECT-TYPE
                SYNTAX  Counter
                ACCESS  read-only
                STATUS  mandatory
                DESCRIPTION "A maximum based on the number of Uncorrected 
                             Cells in all of the RPD Frames recorded in a period
                             of time referred to as a long window. The period of
                             the long window is hard-coded as 1 hour. The number
                             of Uncorrected Cells is adjusted with a new value 1
                             time per second. Measurements more than 1 hour old
                             are removed from the calculations. Thus, there are
                             3600 values in the history. The maximum is the
                             largest of the 3600 values recorded.
                             (max. = 24 cells/frame * 125 frames/sec )"
                REFERENCE   " -- "
        ::= { ncUpStreamStatTableEntry 14 }

ncUpStatMaxLoWinCorrectCells OBJECT-TYPE
                SYNTAX  Counter
                ACCESS  read-only
                STATUS  mandatory
                DESCRIPTION "A maximum based on the number of Corrected Cells in
                             all of the RPD Frames recorded in a period of time
                             referred to as a long window. The period of the 
                             long window is hard-coded as 1 hour. The number of 
                             Corrected Cells is adjusted with a new value 1 time
                             per second. Measurements more than 1 hour old are
                             removed from the calculations. Thus, there are 3600
                             values in the history. The maximum is the largest
                             of the 3600 values recorded.
                             (max. = 24 cells/frame * 125 frames/sec )"
                REFERENCE   " -- "
        ::= { ncUpStreamStatTableEntry 15 }

ncUpStatMaxLoWinPerfectCells OBJECT-TYPE
                SYNTAX  Counter
                ACCESS  read-only
                STATUS  mandatory
                DESCRIPTION "A maximum based on the number of Perfect Cells in
                             all of the RPD1000 RPD Frames recorded in a period
                             of time referred to as a long window. The period of
                             the long window is hard-coded as 1 hour. The number
                             of Perfect Cells is adjusted with a new value 1 
                             time per second. Measurements more than 1 hour old
                             are removed from the calculations. Thus, there are
                             3600 values in the history. The maximum is the
                             largest of the 3600 values recorded.
                             (max. = 24 cells/frame * 125 frames/sec )"
                REFERENCE   " -- "
        ::= { ncUpStreamStatTableEntry 16 }

ncUpStatAveLoWinUncorrCells OBJECT-TYPE
                SYNTAX  Counter
                ACCESS  read-only
                STATUS  mandatory
                DESCRIPTION "An average based on the number of Uncorrected 
                             Cells in all of the RPD Frames recorded in a period
                             of time referred to as a long window. The period of
                             the long window is hard-coded as 1 hour. The number
                             of Uncorrected Cells is adjusted with a new value 1
                             time per second. Measurements more than 1 hour old
                             are removed from the calculations. Thus, there are
                             3600 values in the history. The average is the sum
                             of the 3600 Uncorrected Cell values recorded 
                             divided by 3600.
                             (max. = 24 cells/frame * 125 frames/sec )"
                REFERENCE   " -- "
        ::= { ncUpStreamStatTableEntry 17 }

ncUpStatAveLoWinCorrectCells OBJECT-TYPE
                SYNTAX  Counter
                ACCESS  read-only
                STATUS  mandatory
                DESCRIPTION "An average based on the number of Corrected 
                             Cells in all of the RPD Frames recorded in a period
                             of time referred to as a long window. The period of
                             the long window is hard-coded as 1 hour. The number
                             of Corrected Cells is adjusted with a new value 1
                             time per second. Measurements more than 1 hour old
                             are removed from the calculations. Thus, there are
                             3600 values in the history. The average is the sum
                             of the 3600 Corrected Cell values recorded divided
                             by 3600.
                             (max. = 24 cells/frame * 125 frames/sec )"
                REFERENCE   " -- "
        ::= { ncUpStreamStatTableEntry 18 }

ncUpStatAveLoWinPerfectCells OBJECT-TYPE
                SYNTAX  Counter
                ACCESS  read-only
                STATUS  mandatory
                DESCRIPTION "An average based on the number of Perfect Cells in
                             all of the RPD Frames recorded in a period of time
                             referred to as a long window. The period of the
                             long window is hard-coded as 1 hour. The number of 
                             Perfect Cells is adjusted with a new value 1 time
                             per second. Measurements more than 1 hour old are
                             removed from the calculations. Thus, there are 3600
                             values in the history. The average is the sum of 
                             the 3600 Perfect Cell values recorded divided by 
                             3600.
                             (max. = 24 cells/frame * 125 frames/sec )"
                REFERENCE   " -- "
        ::= { ncUpStreamStatTableEntry 19 }

ncUpStatShWinUncorrCells OBJECT-TYPE
                SYNTAX  Counter
                ACCESS  read-only
                STATUS  mandatory
                DESCRIPTION "The number of Uncorrected Cells in all of the RPD 
                             Frames recorded in a period of time referred to as
                             a short window. The period of the short window is
                             hard-coded as 1 minute. The number of Uncorrected
                             Cells is adjusted with a new value 1 time per 
                             second. Measurements more than 1 minute old are 
                             removed from the calculations. The RPD attempts to
                             correct errors detected in the upstream cells. 
                             Those that can't be corrected are marked as 
                             Uncorrected Cells.
                             (max. = 24 cells/frame * 125 frames/sec * 
                              60 seconds )"
                REFERENCE   " -- "
        ::= { ncUpStreamStatTableEntry 20 }

ncUpStatShWinCorrectCells OBJECT-TYPE
                SYNTAX  Counter
                ACCESS  read-only
                STATUS  mandatory
                DESCRIPTION "The number of Corrected Cells in all of the RPD 
                             Frames recorded in a period of time referred to as
                             a short window. The period of the short window is
                             hard-coded as 1 minute. The number of Corrected 
                             Cells is adjusted with a new value 1 time per 
                             second. Measurements more than 1 minute old are 
                             removed from the calculations. The RPD attempts to
                             correct errors detected in the upstream cells. 
                             Those that can be corrected are marked as Corrected 
                             Cells.
                             (max. = 24 cells/frame * 125 frames/sec * 
                              60 seconds )"
                REFERENCE   " -- "
        ::= { ncUpStreamStatTableEntry 21 }

ncUpStatShWinPerfectCells OBJECT-TYPE
                SYNTAX  Counter
                ACCESS  read-only
                STATUS  mandatory
                DESCRIPTION "The number of Perfect Cells in all of the RPD 
                             Frames recorded in a period of time referred to as
                             a short window. The period of the short window is
                             hard-coded as 1 minute. The number of Perfect Cells
                             is adjusted with a new value 1 time per second. 
                             Measurements more than 1 minute old are removed 
                             from the calculations. The RPD marks upstream cells
                             that require no correction as Perfect Cells.
                             (max. = 24 cells/frame * 125 frames/sec * 
                              60 seconds )"
                REFERENCE   " -- "
        ::= { ncUpStreamStatTableEntry 22 }

ncUpStatShWinCells OBJECT-TYPE
                SYNTAX  Counter
                ACCESS  read-only
                STATUS  mandatory
                DESCRIPTION "The total number of Cells in all of the RPD Frames
                             recorded in a period of time referred to as a short
                             window. The period of the short window is hard-
                             coded as 1 minute. The number of Cells is adjusted
                             with a new value 1 time per second. Measurements
                             more than 1 minute old are removed from the
                             calculations.
                             (max. = 24 cells/frame * 125 frames/sec * 
                              60 seconds )"
                REFERENCE   " -- "
        ::= { ncUpStreamStatTableEntry 23 }

ncUpStatShWinMinUncorrCells OBJECT-TYPE
                SYNTAX  Counter
                ACCESS  read-only
                STATUS  mandatory
                DESCRIPTION "A minimum based on the number of Uncorrected 
                             Cells in all of the RPD Frames recorded in a period
                             of time referred to as a short window. The period
                             of the short window is hard-coded as 1 minute. The
                             number of Uncorrected Cells is adjusted with a new 
                             value 1 time per second. Measurements more than 1
                             minute old are removed from the calculations. Thus,
                             there are 60 values in the history. The minimum is
                             the smallest of the 60 values recorded.
                             (max. = 24 cells/frame * 125 frames/sec )"
                REFERENCE   " -- "
        ::= { ncUpStreamStatTableEntry 24 }

ncUpStatShWinMinCorrectCells OBJECT-TYPE
                SYNTAX  Counter
                ACCESS  read-only
                STATUS  mandatory
                DESCRIPTION "A minimum based on the number of Corrected Cells in
                             all of the RPD1000 RPD Frames recorded in a period
                             of time referred to as a short window. The period
                             of the short window is hard-coded as 1 minute. The
                             number of Corrected Cells is adjusted with a new 
                             value 1 time per second. Measurements more than 1
                             minute old are removed from the calculations. Thus,
                             there are 60 values in the history. The minimum is
                             the smallest of the 60 values recorded.
                             (max. = 24 cells/frame * 125 frames/sec )"
                REFERENCE   " -- "
        ::= { ncUpStreamStatTableEntry 25 }

ncUpStatShWinMinPerfectCells OBJECT-TYPE
                SYNTAX  Counter
                ACCESS  read-only
                STATUS  mandatory
                DESCRIPTION "A minimum based on the number of Perfect Cells in
                             all of the RPD Frames recorded in a period of time
                             referred to as a short window. The period of the 
                             short window is hard-coded as 1 minute. The number
                             of Perfect Cells is adjusted with a new value 1 
                             time per second. Measurements more than 1 minute 
                             old are removed from the calculations. Thus, there
                             are 60 values in the history. The minimum is the 
                             smallest of the 60 values recorded.
                             (max. = 24 cells/frame * 125 frames/sec )"
                REFERENCE   " -- "
        ::= { ncUpStreamStatTableEntry 26 }

ncUpStatShWinMaxUncorrCells OBJECT-TYPE
                SYNTAX  Counter
                ACCESS  read-only
                STATUS  mandatory
                DESCRIPTION "A maximum based on the number of Uncorrected 
                             Cells in all of the RPD Frames recorded in a period
                             of time referred to as a short window. The period
                             of the short window is hard-coded as 1 minute. The
                             number of Uncorrected Cells is adjusted with a new 
                             value 1 time per second. Measurements more than 1
                             minute old are removed from the calculations. Thus,
                             there are 60 values in the history. The maximum is
                             the largest of the 60 values recorded.
                             (max. = 24 cells/frame * 125 frames/sec )"
                REFERENCE   " -- "
        ::= { ncUpStreamStatTableEntry 27 }

ncUpStatShWinMaxCorrectCells OBJECT-TYPE
                SYNTAX  Counter
                ACCESS  read-only
                STATUS  mandatory
                DESCRIPTION "A maximum based on the number of Corrected 
                             Cells in all of the RPD Frames recorded in a period
                             of time referred to as a short window. The period
                             of the short window is hard-coded as 1 minute.
                             The number of Corrected Cells is adjusted with a
                             new value 1 time per second. Measurements more 
                             than 1 minute old are removed from the 
                             calculations. Thus, there are 60 values in the 
                             history. The maximum is the largest of the 60 
                             values recorded.
                             (max. = 24 cells/frame * 125 frames/sec )"
                REFERENCE   " -- "
        ::= { ncUpStreamStatTableEntry 28 }

ncUpStatShWinMaxPerfectCells OBJECT-TYPE
                SYNTAX  Counter
                ACCESS  read-only
                STATUS  mandatory
                DESCRIPTION "A maximum based on the number of Perfect 
                             Cells in all of the RPD Frames recorded in a period
                             of time referred to as a short window. The period
                             of the short window is hard-coded as 1 minute. The
                             number of Perfect Cells is adjusted with a new 
                             value 1 time per second. Measurements more than 1
                             minute old are removed from the calculations. Thus,
                             there are 60 values in the history. The maximum is
                             the largest of the 60 values recorded.
                             (max. = 24 cells/frame * 125 frames/sec )"
                REFERENCE   " -- "
        ::= { ncUpStreamStatTableEntry 29 }

ncUpStatShWinAveUncorrCells OBJECT-TYPE
                SYNTAX  Counter
                ACCESS  read-only
                STATUS  mandatory
                DESCRIPTION "An average based on the number of Uncorrected 
                             Cells in all of the RPD Frames recorded in a period
                             of time referred to as a short window. The period
                             of the short window is hard-coded as 1 minute. The
                             number of Uncorrected Cells is adjusted with a new 
                             value 1 time per second. Measurements more than 1
                             minute old are removed from the calculations. Thus,
                             there are 60 values in the history. The average is
                             the sum of the 60 Uncorrected Cell values recorded
                             divided by 60.
                             (max. = 24 cells/frame * 125 frames/sec )"
                REFERENCE   " -- "
        ::= { ncUpStreamStatTableEntry 30 }

ncUpStatShWinAveCorrectCells OBJECT-TYPE
                SYNTAX  Counter
                ACCESS  read-only
                STATUS  mandatory
                DESCRIPTION "An average based on the number of Corrected Cells
                             in all of the RPD Frames recorded in a period of
                             time referred to as a short window. The period of
                             the short window is hard-coded as 1 minute. The
                             number of Corrected Cells is adjusted with a new 
                             value 1 time per second. Measurements more than 1
                             minute old are removed from the calculations. Thus,
                             there are 60 values in the history. The average is
                             the sum of the 60 Corrected Cell values recorded
                             divided by 60.
                             (max. = 24 cells/frame * 125 frames/sec )"
                REFERENCE   " -- "
        ::= { ncUpStreamStatTableEntry 31 }

ncUpStatShWinAvePerfectCells OBJECT-TYPE
                SYNTAX  Counter
                ACCESS  read-only
                STATUS  mandatory
                DESCRIPTION "An average based on the number of Perfect Cells in
                             all of the RPD Frames recorded in a period of time
                             referred to as a short window. The period of the
                             short window is hard-coded as 1 minute. The number
                             of Perfect Cells is adjusted with a new value 1 
                             time per second. Measurements more than 1 minute
                             old are removed from the calculations. Thus, there
                             are 60 values in the history. The average is the
                             sum of the 60 Perfect Cell values recorded divided
                             by 60.
                             (max. = 24 cells/frame * 125 frames/sec )"
                REFERENCE   " -- "
        ::= { ncUpStreamStatTableEntry 32 }

ncUpStatUncorrCellsCntr OBJECT-TYPE
                SYNTAX  Counter
                ACCESS  read-only
                STATUS  mandatory
                DESCRIPTION "The number of Uncorrected Cells in all of the RPD
                             Frames recorded. The number of Uncorrected Cells is
                             adjusted with a new value 1 time per second. This
                             counter increments until it overflows to 0. It is
                             an unsigned long.
                             (max. = (2^32)-1)"
                REFERENCE   " -- "
        ::= { ncUpStreamStatTableEntry 33 }

ncUpStatCorrectCellsCntr OBJECT-TYPE
                SYNTAX  Counter
                ACCESS  read-only
                STATUS  mandatory
                DESCRIPTION "The number of Corrected Cells in all of the RPD
                             Frames recorded. The number of Corrected Cells is
                             adjusted with a new value 1 time per second. This
                             counter increments until it overflows to 0. It is
                             an unsigned long.
                             (max. = (2^32)-1)"
                REFERENCE   " -- "
        ::= { ncUpStreamStatTableEntry 34 }

ncUpStatPerfectCellsCntr OBJECT-TYPE
                SYNTAX  Counter
                ACCESS  read-only
                STATUS  mandatory
                DESCRIPTION "The number of Perfect Cells in all of the RPD 
                             Frames recorded. The number of Perfect Cells is
                             adjusted with a new value 1 time per second. This
                             counter increments until it overflows to 0. It is
                             an unsigned long.
                             (max. = (2^32)-1)"
                REFERENCE   " -- "
        ::= { ncUpStreamStatTableEntry 35 }

ncUpStatCellsCntr OBJECT-TYPE
                SYNTAX  Counter
                ACCESS  read-only
                STATUS  mandatory
                DESCRIPTION "The total number of Cells in all of the RPD Frames
                             recorded. The number of Cells is adjusted with a
                             new value 1 time per second. This counter 
                             increments until it overflows to 0. It is an
                             unsigned long.
                             (max. = (2^32)-1)"
                REFERENCE   " -- "
        ::= { ncUpStreamStatTableEntry 36 }

ncUpStatLostRpdFrames OBJECT-TYPE
                SYNTAX  Counter
                ACCESS  read-only
                STATUS  mandatory
                DESCRIPTION "The number of Lost RPD Frames recorded in a period
                             of time referred to as a long window. The period of
                             the long window is hard-coded as 1 hour. The number
                             of Lost RPD Frames is adjusted with a new value 1
                             time per second. Measurements more than 1 hour old
                             are removed from the calculations. The RPD includes
                             a sequence number in each frame. This value is used
                             to determine if an RPD Frame is not received by the 
                             NC1500.
                             (max. = 125 frames/sec * 60 seconds * 
                             60 minutes )"
                REFERENCE   " -- "
        ::= { ncUpStreamStatTableEntry 37 }

ncUpStatRpdFrames OBJECT-TYPE
                SYNTAX  Counter
                ACCESS  read-only
                STATUS  mandatory
                DESCRIPTION "The number of RPD Frames recorded in a period of
                             time referred to as a long window. The period of
                             the long window is hard-coded as 1 hour. The number
                             of Lost RPD Frames is adjusted with a new value 1
                             time per second. Measurements more than 1 hour old
                             are removed from the calculations.
                             (max. = 125 frames/sec * 60 seconds * 
                             60 minutes )"
                REFERENCE   " -- "
        ::= { ncUpStreamStatTableEntry 38 }

ncUpStatLostRpdFramesCntr OBJECT-TYPE
                SYNTAX  Counter
                ACCESS  read-only
                STATUS  mandatory
                DESCRIPTION "The number of Lost RPD Frames recorded. The number
                             of Lost RPD Frames is adjusted with a new value 1
                             time per second. The RPD includes a sequence number
                             in each frame. This value is used to determine if 
                             an RPD Frame is not received by the NC1500. This
                             counter increments until it overflows to 0. It is
                             an unsigned long.
                             (max. = (2^32)-1)"
                REFERENCE   " -- "
        ::= { ncUpStreamStatTableEntry 39 }

ncUpStatRpdFramesCntr OBJECT-TYPE
                SYNTAX  Counter
                ACCESS  read-only
                STATUS  mandatory
                DESCRIPTION "The number of RPD Frames recorded. The number of
                             RPD Frames is adjusted with a new value 1 time per
                             second. This counter increments until it overflows
                             to 0. It is an unsigned long.
                             (max. = (2^32)-1)"
                REFERENCE   " -- "
        ::= { ncUpStreamStatTableEntry 40 }

--*****************************************
--
-- NC Up Stream Group
--
--*****************************************

ncUpStreamStatClear OBJECT-TYPE
                SYNTAX  INTEGER
                        {
                         clearNotInProgress   (1),
                         readyToClear         (2),
                         clearInProgress      (3)
                        }
                ACCESS  read-write
                STATUS  mandatory
                DESCRIPTION "Writing readyToClear to this object clears all 
                             upstream statistic values for all of the RPDs.  
                             Reading the value clearInProgress indicates 
                             that a clear is currently in progress.  
                             Reading the value clearNotInProgress indicates 
                             that a clear is not active and has been 
                             completed if it was previously started."
                REFERENCE   " -- "
        ::= { ncUpStream 2 }

--*****************************************
--
-- NC Up Stream Group
--   NC Up Stream Return Path Table Group
--
--*****************************************

ncUpStreamPathStatTable OBJECT-TYPE
                SYNTAX  SEQUENCE OF NcUpStreamPathStatTableEntry
                ACCESS  not-accessible
                STATUS  mandatory
                DESCRIPTION "This table is used to report the statistics 
                information based on return path id."
                REFERENCE   " -- "
        ::= { ncUpStream 3 }

ncUpStreamPathStatTableEntry OBJECT-TYPE
                SYNTAX  NcUpStreamPathStatTableEntry
                ACCESS  not-accessible
                STATUS  mandatory
                DESCRIPTION "A row in the Upstream Path Statistics Table."
                REFERENCE   " -- "
                INDEX  { ncUpStreamPathIdIndex }
        ::= { ncUpStreamPathStatTable 1}
 
NcUpStreamPathStatTableEntry ::= SEQUENCE 
       {
       ncUpStreamPathIdIndex          INTEGER,
       ncUpStreamRetryZero            Counter,
       ncUpStreamRetryOne             Counter,
       ncUpStreamRetryTwo             Counter,
       ncUpStreamRetryThree           Counter,
       ncUpStreamRetryFourOrMore      Counter,
       ncUpStreamRetryCountClear      INTEGER,
       ncUpStreamRetryEfficiency      INTEGER
       }

ncUpStreamPathIdIndex OBJECT-TYPE
                SYNTAX  INTEGER
                ACCESS  not-accessible
                STATUS  mandatory
                DESCRIPTION "The index is the return path id."
                REFERENCE   " -- "
        ::= { ncUpStreamPathStatTableEntry 1 }

ncUpStreamRetryZero OBJECT-TYPE
                SYNTAX  Counter
                ACCESS  read-only
                STATUS  mandatory
                DESCRIPTION "The number of packets for which the retry count is
                             zero."
                REFERENCE   " -- "
        ::= { ncUpStreamPathStatTableEntry 2 }

ncUpStreamRetryOne OBJECT-TYPE
                SYNTAX  Counter
                ACCESS  read-only
                STATUS  mandatory
                DESCRIPTION "The number of packets for which the retry count is
                             one."
                REFERENCE   " -- "
        ::= { ncUpStreamPathStatTableEntry 3 }

ncUpStreamRetryTwo OBJECT-TYPE
                SYNTAX  Counter
                ACCESS  read-only
                STATUS  mandatory
                DESCRIPTION "The number of packets for which the retry count is
                             two."
                REFERENCE   " -- "
        ::= { ncUpStreamPathStatTableEntry 4 }

ncUpStreamRetryThree OBJECT-TYPE
                SYNTAX  Counter
                ACCESS  read-only
                STATUS  mandatory
                DESCRIPTION "The number of packets for which the retry count is
                             three."
                REFERENCE   " -- "
        ::= { ncUpStreamPathStatTableEntry 5 }

ncUpStreamRetryFourOrMore OBJECT-TYPE
                SYNTAX  Counter
                ACCESS  read-only
                STATUS  mandatory
                DESCRIPTION "The number of packets for which the retry count is
                             four or more."
                REFERENCE   " -- "
        ::= { ncUpStreamPathStatTableEntry 6 }

ncUpStreamRetryCountClear OBJECT-TYPE
                SYNTAX  INTEGER
                        {
                         clearNotInProgress   (1),
                         readyToClear         (2),
                         clearInProgress      (3)
                        }
                ACCESS  read-write
                STATUS  mandatory
                DESCRIPTION "Writing readyToClear to this object clears the 
                             upstream retry count values for a specific 
                             upstream in ncUpStreamPathStatTable.  
                             Reading the value clearInProgress indicates 
                             that a clear is currently in progress.  Reading 
                             the value clearNotInProgress indicates that a 
                             clear is not active and has been completed if 
                             it was previously started."
                REFERENCE   " -- "
        ::= { ncUpStreamPathStatTableEntry 7 }

ncUpStreamRetryEfficiency OBJECT-TYPE
                SYNTAX  INTEGER
                ACCESS  read-only
                STATUS  mandatory
                DESCRIPTION "The calculated Upstream efficiency value 0-100 percent"
                REFERENCE   " -- "
        ::= { ncUpStreamPathStatTableEntry 8 }

--*****************************************
--
-- NC Up Stream Group
--
--*****************************************

ncUpStreamPathStatClear OBJECT-TYPE
                SYNTAX  INTEGER
                        {
                         clearNotInProgress   (1),
                         readyToClear         (2),
                         clearInProgress      (3)
                        }
                ACCESS  read-write
                STATUS  mandatory
                DESCRIPTION "Not implemented."
                REFERENCE   " -- "
        ::= { ncUpStream 4 }

--*****************************************
--
-- NC Up Stream Group
--   NC Up Stream Path Test Group
--
--*****************************************

ncPathTestNumberOfPathPairs OBJECT-TYPE
                SYNTAX  INTEGER
                ACCESS  read-only
                STATUS  mandatory
                DESCRIPTION "Number of configured upstream paths."
                REFERENCE   " -- "
        ::= { ncPathTest 1 }

ncPathTestMasterAlarm OBJECT-TYPE
                SYNTAX  INTEGER
                        {
                         green        (1),
                         yellow       (2),
                         red          (3),
                         grey         (4)
                        }
                ACCESS  read-only
                STATUS  mandatory
                DESCRIPTION "The Master Alarm set by Path Test results."
                REFERENCE   " -- "
        ::= { ncPathTest 2 }

--*****************************************
--
-- NC Up Stream Group
--   NC Up Stream Path Test Group
--     NC Path Pair Test Bit Table Group
--
--*****************************************

ncPathPairTestBitFieldTable OBJECT-TYPE
                SYNTAX  SEQUENCE OF NcPathPairTestBitFieldTableEntry
                ACCESS  not-accessible
                STATUS  mandatory
                DESCRIPTION "This table is used to report the path test results
                             for up to 192 paths. The upstream path test results
                             are packed into 12 ULONG words, 2 bits per path."
                REFERENCE   " -- "
        ::= { ncPathTest 3 }

ncPathPairTestBitFieldTableEntry OBJECT-TYPE
                SYNTAX  NcPathPairTestBitFieldTableEntry
                ACCESS  not-accessible
                STATUS  mandatory
                DESCRIPTION "A row in the Path Pair Test bit field table."
                REFERENCE   " -- "
                INDEX  { ncPathPairTestBitFieldIndex }
        ::= { ncPathPairTestBitFieldTable 1}
 
NcPathPairTestBitFieldTableEntry ::= SEQUENCE 
       {
       ncPathPairTestBitFieldIndex          INTEGER,
       ncPathPairTestBitFieldData           INTEGER
       }

ncPathPairTestBitFieldIndex OBJECT-TYPE
                SYNTAX  INTEGER
                ACCESS  not-accessible
                STATUS  mandatory
                DESCRIPTION "The row number of the table (a value between 1 
                             and 12).  Each row contains status data for up to
                             16 paths."
                REFERENCE   " -- "
        ::= { ncPathPairTestBitFieldTableEntry 1 }

ncPathPairTestBitFieldData OBJECT-TYPE
                SYNTAX  INTEGER
                ACCESS  read-only
                STATUS  mandatory
                DESCRIPTION "This is a row within the table. It is a ULONG word
                that contains the test status for 16 upstream paths (2 bits per
                path).  There are 12 of these within the table.
                  (12 words * 16 paths per word = 192 paths)"
                REFERENCE   " -- "
        ::= { ncPathPairTestBitFieldTableEntry 2 }

--*****************************************
--
-- NC Up Stream Group
--   NC Up Stream Path Test Group
--     NC Path Configuration Table Group
--
--*****************************************

ncPathConfigTable OBJECT-TYPE
                SYNTAX  SEQUENCE OF NcPathConfigTableEntry
                ACCESS  not-accessible
                STATUS  mandatory
                DESCRIPTION "This table is used to report the path 
                             configuration in terms of OM and RPDs
                             and associated downstream path ID."
                REFERENCE   " -- "
        ::= { ncPathTest 4 }

ncPathConfigTableEntry OBJECT-TYPE
                SYNTAX  NcPathConfigTableEntry
                ACCESS  not-accessible
                STATUS  mandatory
                DESCRIPTION "There are 192 rows of 23 columns each."
                REFERENCE   " -- "
                INDEX  { ncPathConfigIndex }
        ::= { ncPathConfigTable 1}
 
NcPathConfigTableEntry ::= SEQUENCE 
       {
       ncPathConfigIndex            INTEGER,
       ncPathConfigDownStreamPathId       INTEGER,
       ncPathConfigOmChassisNumber        INTEGER,
       ncPathConfigUpStreamPathId         INTEGER,
       ncPathConfigRpdChassisOne          INTEGER,
       ncPathConfigRpdChassisTwo          INTEGER,
       ncPathConfigRpdChassisThree        INTEGER,
       ncPathConfigRpdChassisFour         INTEGER,
       ncPathConfigRpdChassisFive         INTEGER,
       ncPathConfigRpdChassisSix          INTEGER,
       ncPathConfigRpdChassisSeven        INTEGER,
       ncPathConfigRpdChassisEight        INTEGER,
       ncPathConfigRpdChassisNine         INTEGER,
       ncPathConfigRpdChassisTen          INTEGER,
       ncPathConfigRpdChassisEleven       INTEGER,
       ncPathConfigRpdChassisTwelve       INTEGER,
       ncPathConfigRpdChassisThirteen     INTEGER,
       ncPathConfigRpdChassisFourteen     INTEGER,
       ncPathConfigRpdChassisFifteen      INTEGER,
       ncPathConfigRpdChassisSixteen      INTEGER,
       ncPathConfigRpdChassisSeventeen    INTEGER,
       ncPathConfigRpdChassisEighteen     INTEGER,
       ncPathConfigRpdChassisNineteen     INTEGER,
       ncPathConfigRpdChassisTwenty       INTEGER
       }

ncPathConfigIndex OBJECT-TYPE
                SYNTAX  INTEGER
                ACCESS  not-accessible
                STATUS  mandatory
                DESCRIPTION "The row number (path pair number) of the table.
                             The index value is between 1 and 192."
                REFERENCE   " -- "
        ::= { ncPathConfigTableEntry 1 }

ncPathConfigDownStreamPathId OBJECT-TYPE
                SYNTAX  INTEGER
                ACCESS  read-only
                STATUS  mandatory
                DESCRIPTION "Downstream path ID for this path"
                REFERENCE   " -- "
        ::= { ncPathConfigTableEntry 2 }

ncPathConfigOmChassisNumber OBJECT-TYPE
                SYNTAX  INTEGER
                ACCESS  read-only
                STATUS  mandatory
                DESCRIPTION "OM chassis number for this path (1-10)"
                REFERENCE   " -- "
        ::= { ncPathConfigTableEntry 3 }

ncPathConfigUpStreamPathId OBJECT-TYPE
                SYNTAX  INTEGER
                ACCESS  read-only
                STATUS  mandatory
                DESCRIPTION "Upstream path ID for this path"
                REFERENCE   " -- "
        ::= { ncPathConfigTableEntry 4 }

ncPathConfigRpdChassisOne OBJECT-TYPE
                SYNTAX  INTEGER
                ACCESS  read-only
                STATUS  mandatory
                DESCRIPTION "RPD 1 chassis number for this path (1-32)"
                REFERENCE   " -- "
        ::= { ncPathConfigTableEntry 5 }

ncPathConfigRpdChassisTwo OBJECT-TYPE
                SYNTAX  INTEGER
                ACCESS  read-only
                STATUS  mandatory
                DESCRIPTION "RPD 2 chassis number for this path (1-32)"
                REFERENCE   " -- "
        ::= { ncPathConfigTableEntry 6 }

ncPathConfigRpdChassisThree OBJECT-TYPE
                SYNTAX  INTEGER
                ACCESS  read-only
                STATUS  mandatory
                DESCRIPTION "RPD 3 chassis number for this path (1-32)"
                REFERENCE   " -- "
        ::= { ncPathConfigTableEntry 7 }

ncPathConfigRpdChassisFour OBJECT-TYPE
                SYNTAX  INTEGER
                ACCESS  read-only
                STATUS  mandatory
                DESCRIPTION "RPD 4 chassis number for this path (1-32)"
                REFERENCE   " -- "
        ::= { ncPathConfigTableEntry 8 }

ncPathConfigRpdChassisFive OBJECT-TYPE
                SYNTAX  INTEGER
                ACCESS  read-only
                STATUS  mandatory
                DESCRIPTION "RPD 5 chassis number for this path (1-32)"
                REFERENCE   " -- "
        ::= { ncPathConfigTableEntry 9 }

ncPathConfigRpdChassisSix OBJECT-TYPE
                SYNTAX  INTEGER
                ACCESS  read-only
                STATUS  mandatory
                DESCRIPTION "RPD 6 chassis number for this path (1-32)"
                REFERENCE   " -- "
        ::= { ncPathConfigTableEntry 10 }

ncPathConfigRpdChassisSeven OBJECT-TYPE
                SYNTAX  INTEGER
                ACCESS  read-only
                STATUS  mandatory
                DESCRIPTION "RPD 7 chassis number for this path (1-32)"
                REFERENCE   " -- "
        ::= { ncPathConfigTableEntry 11 }

ncPathConfigRpdChassisEight OBJECT-TYPE
                SYNTAX  INTEGER
                ACCESS  read-only
                STATUS  mandatory
                DESCRIPTION "RPD 8 chassis number for this path (1-32)"
                REFERENCE   " -- "
        ::= { ncPathConfigTableEntry 12 }

ncPathConfigRpdChassisNine OBJECT-TYPE
                SYNTAX  INTEGER
                ACCESS  read-only
                STATUS  mandatory
                DESCRIPTION "RPD 9 chassis number for this path (1-32)"
                REFERENCE   " -- "
        ::= { ncPathConfigTableEntry 13 }

ncPathConfigRpdChassisTen OBJECT-TYPE
                SYNTAX  INTEGER
                ACCESS  read-only
                STATUS  mandatory
                DESCRIPTION "RPD 10 chassis number for this path (1-32)"
                REFERENCE   " -- "
        ::= { ncPathConfigTableEntry 14 }

ncPathConfigRpdChassisEleven OBJECT-TYPE
                SYNTAX  INTEGER
                ACCESS  read-only
                STATUS  mandatory
                DESCRIPTION "RPD 11 chassis number for this path (1-32)"
                REFERENCE   " -- "
        ::= { ncPathConfigTableEntry 15 }

ncPathConfigRpdChassisTwelve OBJECT-TYPE
                SYNTAX  INTEGER
                ACCESS  read-only
                STATUS  mandatory
                DESCRIPTION "RPD 12 chassis number for this path (1-32)"
                REFERENCE   " -- "
        ::= { ncPathConfigTableEntry 16 }

ncPathConfigRpdChassisThirteen OBJECT-TYPE
                SYNTAX  INTEGER
                ACCESS  read-only
                STATUS  mandatory
                DESCRIPTION "RPD 13 chassis number for this path (1-32)"
                REFERENCE   " -- "
        ::= { ncPathConfigTableEntry 17 }

ncPathConfigRpdChassisFourteen OBJECT-TYPE
                SYNTAX  INTEGER
                ACCESS  read-only
                STATUS  mandatory
                DESCRIPTION "RPD 14 chassis number for this path (1-32)"
                REFERENCE   " -- "
        ::= { ncPathConfigTableEntry 18 }

ncPathConfigRpdChassisFifteen OBJECT-TYPE
                SYNTAX  INTEGER
                ACCESS  read-only
                STATUS  mandatory
                DESCRIPTION "RPD 15 chassis number for this path (1-32)"
                REFERENCE   " -- "
        ::= { ncPathConfigTableEntry 19 }

ncPathConfigRpdChassisSixteen OBJECT-TYPE
                SYNTAX  INTEGER
                ACCESS  read-only
                STATUS  mandatory
                DESCRIPTION "RPD 16 chassis number for this path (1-32)"
                REFERENCE   " -- "
        ::= { ncPathConfigTableEntry 20 }

ncPathConfigRpdChassisSeventeen OBJECT-TYPE
                SYNTAX  INTEGER
                ACCESS  read-only
                STATUS  mandatory
                DESCRIPTION "RPD 17 chassis number for this path (1-32)"
                REFERENCE   " -- "
        ::= { ncPathConfigTableEntry 21 }

ncPathConfigRpdChassisEighteen OBJECT-TYPE
                SYNTAX  INTEGER
                ACCESS  read-only
                STATUS  mandatory
                DESCRIPTION "RPD 18 chassis number for this path (1-32)"
                REFERENCE   " -- "
        ::= { ncPathConfigTableEntry 22 }

ncPathConfigRpdChassisNineteen OBJECT-TYPE
                SYNTAX  INTEGER
                ACCESS  read-only
                STATUS  mandatory
                DESCRIPTION "RPD 19 chassis number for this path (1-32)"
                REFERENCE   " -- "
        ::= { ncPathConfigTableEntry 23 }

ncPathConfigRpdChassisTwenty OBJECT-TYPE
                SYNTAX  INTEGER
                ACCESS  read-only
                STATUS  mandatory
                DESCRIPTION "RPD 20 chassis number for this path (1-32)"
                REFERENCE   " -- "
        ::= { ncPathConfigTableEntry 24 }

--*****************************************
--
-- NC Up Stream Group
--   NC Up Stream Demod Status Group
--
--*****************************************

ncDemodStatusTable OBJECT-TYPE
                SYNTAX  SEQUENCE OF NcDemodStatusTableEntry
                ACCESS  not-accessible
                STATUS  mandatory
                DESCRIPTION "This table is used to report the demodulator
                             status. The data is arranged in the bit fields,
                             two RPD's demods per word."
                REFERENCE   " -- "
        ::= { ncUpStream 6 }

ncDemodStatusTableEntry OBJECT-TYPE
                SYNTAX  NcDemodStatusTableEntry
                ACCESS  not-accessible
                STATUS  mandatory
                DESCRIPTION "A row in the Demod Status table."
                REFERENCE   " -- "
                INDEX  { ncDemodStatusIndex }
        ::= { ncDemodStatusTable 1}
 
NcDemodStatusTableEntry ::= SEQUENCE 
       {
       ncDemodStatusIndex       INTEGER,
       ncDemodStatus            INTEGER
       }

ncDemodStatusIndex OBJECT-TYPE
                SYNTAX  INTEGER
                ACCESS  not-accessible
                STATUS  mandatory
                DESCRIPTION "The row number of the table.  The index value is 
                             between 1 and 16, with each row having demod data
                             for two RPD's."
                REFERENCE   " -- "
        ::= { ncDemodStatusTableEntry 1 }

ncDemodStatus OBJECT-TYPE
                SYNTAX  INTEGER
                ACCESS  read-only
                STATUS  mandatory
                DESCRIPTION "Demod status for two RPDs."
                REFERENCE   " -- "
        ::= { ncDemodStatusTableEntry 2 }

--*****************************************
--
-- NC Up Stream Group
--   NC Up Stream RPD Chassis Status Group
--
--*****************************************

ncRpdChassisStatusTable OBJECT-TYPE
                SYNTAX  SEQUENCE OF NcRpdChassisStatusTableEntry
                ACCESS  not-accessible
                STATUS  mandatory
                DESCRIPTION "This table is used to report the RPD status, The 
                             data is arranged in bit fields, 16 RPD's per word."
                REFERENCE   " -- "
        ::= { ncUpStream 7 }

ncRpdChassisStatusTableEntry OBJECT-TYPE
                SYNTAX  NcRpdChassisStatusTableEntry
                ACCESS  not-accessible
                STATUS  mandatory
                DESCRIPTION "A row in the RPD Chassis Status Table."
                REFERENCE   " -- "
                INDEX  { ncRpdChassisStatusIndex }
        ::= { ncRpdChassisStatusTable 1}
 
NcRpdChassisStatusTableEntry ::= SEQUENCE 
       {
       ncRpdChassisStatusIndex       INTEGER,
       ncRpdChassisStatus            INTEGER
       }

ncRpdChassisStatusIndex OBJECT-TYPE
                SYNTAX  INTEGER
                ACCESS  not-accessible
                STATUS  mandatory
                DESCRIPTION "The row number of the table.  The index value is 
                             between 1 and 2."
                REFERENCE   " -- "
        ::= { ncRpdChassisStatusTableEntry 1 }

ncRpdChassisStatus OBJECT-TYPE
                SYNTAX  INTEGER
                ACCESS  read-only
                STATUS  mandatory
                DESCRIPTION "Status for 16 RPD's."
                REFERENCE   " -- "
        ::= { ncRpdChassisStatusTableEntry 2 }

--*****************************************
--
-- NC Settop Box Group
--   NC Settop Box Add Group
--
--*****************************************

ncSettopAddedMac OBJECT-TYPE
                SYNTAX  DisplayString
                ACCESS  read-only
                STATUS  mandatory
                DESCRIPTION "The added settop box MAC address."
                REFERENCE   " -- "
        ::= { ncSettopBoxAdd 1 }

--*****************************************
--
-- NC Settop Box Group
--   NC Settop Box Delete Group
--
--*****************************************

ncSettopDeletedMac OBJECT-TYPE
                SYNTAX  DisplayString
                ACCESS  read-write
                STATUS  mandatory
                DESCRIPTION "The deleted settop box MAC address."
                REFERENCE   " -- "
        ::= { ncSettopBoxDelete 1 }

--*****************************************
--
-- NC Settop Box Group
--   NC Settop Box IP Range Group
--
--*****************************************

ncSettopStartIp OBJECT-TYPE
                SYNTAX  IpAddress
                ACCESS  read-write
                STATUS  mandatory
                DESCRIPTION "The start of the range of IP addresses which
                             the NC1500 is allowed to assign to settops.  
                             This value will be calculated based on the Host 
                             IP & the Subnet mask."
                REFERENCE   " -- "
        ::= { ncSettopIpRange 1 }

ncSettopEndIp OBJECT-TYPE
                SYNTAX  IpAddress
                ACCESS  read-write
                STATUS  mandatory
                DESCRIPTION "The end of the range of IP addresses which
                             the NC1500 is allowed to assign to settops.
                             This value will be calculated based on the Host 
                             IP & the Subnet mask."
                REFERENCE   " -- "
        ::= { ncSettopIpRange 2 }
        
--*****************************************
--
-- NC Settop Box Group
--   NC Settop Box Table Group
--
--*****************************************

ncSettopBoxTable OBJECT-TYPE
                SYNTAX  SEQUENCE OF NcSettopBoxTableEntry
                ACCESS  not-accessible
                STATUS  mandatory
                DESCRIPTION "This table is used to access each settop box
                             related information that NC1500 manages."
                REFERENCE   " -- "
        ::= { ncSettopBox 4 }

ncSettopBoxTableEntry OBJECT-TYPE
                SYNTAX  NcSettopBoxTableEntry
                ACCESS  not-accessible
                STATUS  mandatory
                DESCRIPTION "An entry (conceptual row) in the NC1500
                             settop box class instance information table."
                REFERENCE   " -- "
                INDEX  { ncSettopBoxMacIndex }
        ::= { ncSettopBoxTable 1}
 
NcSettopBoxTableEntry ::= SEQUENCE 
       {
       ncSettopBoxMacIndex               MacAddress,
       ncSettopBoxIpAddress              IpAddress,
       ncSettopBoxUpmAddress             Counter,
       ncSettopBoxMacAddress             DisplayString,
       ncSettopBoxDownStreamPathId       INTEGER,
       ncSettopBoxReturnPathId           INTEGER,
       ncSettopBoxNumDownStreamPdu       Counter,
       ncSettopBoxNumUpStreamPdu         Counter,
       ncSettopBoxNumUpStreamCrcErr      Counter,
       ncSettopBoxRetryCount             Counter,
       ncSettopBoxReceivedPwrLevel       DisplayString,
       ncSettopBoxNumberOfEntries        Counter,
       ncSettopBoxLastIdleTime           DisplayString,
       ncSettopBoxLastMessageTime        DisplayString,
       ncSettopBoxStatus                 INTEGER
       }

ncSettopBoxMacIndex OBJECT-TYPE
                SYNTAX  MacAddress
                ACCESS  not-accessible
                STATUS  mandatory
                DESCRIPTION "The auxiliary variable used for identifying
                             instances of the columnar objects.  Here the
                             index is the MAC address (6 byte Octet String)."
                REFERENCE   " -- "
        ::= { ncSettopBoxTableEntry 1 }

ncSettopBoxIpAddress OBJECT-TYPE
                SYNTAX  IpAddress
                ACCESS  read-only
                STATUS  mandatory
                DESCRIPTION "The remote settop box IP address."
                REFERENCE   " -- "
        ::= { ncSettopBoxTableEntry 2 }

ncSettopBoxUpmAddress OBJECT-TYPE
                SYNTAX  Counter
                ACCESS  read-only
                STATUS  mandatory
                DESCRIPTION "The remote settop box UPM address."
                REFERENCE   " -- "
        ::= { ncSettopBoxTableEntry 3 }

ncSettopBoxMacAddress OBJECT-TYPE
                SYNTAX  DisplayString
                ACCESS  read-only
                STATUS  mandatory
                DESCRIPTION "The remote settop box MAC address."
                REFERENCE   " -- "
        ::= { ncSettopBoxTableEntry 4 }

ncSettopBoxDownStreamPathId OBJECT-TYPE
                SYNTAX  INTEGER
                ACCESS  read-only
                STATUS  mandatory
                DESCRIPTION "The ID for the downstream path that the remote
                             settop box uses."
                REFERENCE   " -- "
        ::= { ncSettopBoxTableEntry 5 }

ncSettopBoxReturnPathId OBJECT-TYPE
                SYNTAX  INTEGER
                ACCESS  read-only
                STATUS  mandatory
                DESCRIPTION "The ID for the upstream (return) path that the 
                             remote settop box uses."
                REFERENCE   " -- "
        ::= { ncSettopBoxTableEntry 6 }

ncSettopBoxNumDownStreamPdu OBJECT-TYPE
                SYNTAX  Counter
                ACCESS  read-write
                STATUS  mandatory
                DESCRIPTION "The number of downstream PDUs sent to the remote
                             settop box.  The 'write' function serves as a reset
                             for this variable."
                REFERENCE   " -- "
        ::= { ncSettopBoxTableEntry 7 }

ncSettopBoxNumUpStreamPdu OBJECT-TYPE
                SYNTAX  Counter
                ACCESS  read-write
                STATUS  mandatory
                DESCRIPTION "The number of upstream PDUs received from the
                             remote settop box.  The 'write' function serves
                             as a reset for this variable."
                REFERENCE   " -- "
        ::= { ncSettopBoxTableEntry 8 }

ncSettopBoxNumUpStreamCrcErr OBJECT-TYPE
                SYNTAX  Counter
                ACCESS  read-write
                STATUS  mandatory
                DESCRIPTION "The number of upstream PDUs with CRC errors
                             received from the settop box.  The 'write' function
                             serves as a reset for this variable."
                REFERENCE   " -- "
        ::= { ncSettopBoxTableEntry 9 }

ncSettopBoxRetryCount OBJECT-TYPE
                SYNTAX  Counter
                ACCESS  read-write
                STATUS  mandatory
                DESCRIPTION "The number of accumulative retransmitted upstream
                             MAC cells received from the settop.  The 'write'
                             function serves as a reset for this variable."
                REFERENCE   " -- "
        ::= { ncSettopBoxTableEntry 10 }

ncSettopBoxReceivedPwrLevel OBJECT-TYPE
                SYNTAX  DisplayString
                ACCESS  read-only
                STATUS  mandatory
                DESCRIPTION "The relative power level of the last received 
                             upstream MAC cell, measured by the RPD as an 
                             offset from its nominal input."
                REFERENCE   " -- "
        ::= { ncSettopBoxTableEntry 11 }

ncSettopBoxNumberOfEntries OBJECT-TYPE
                SYNTAX  Counter
                ACCESS  read-write
                STATUS  mandatory
                DESCRIPTION "The number times the settop entered the network."
                REFERENCE   " -- "
        ::= { ncSettopBoxTableEntry 12 }

ncSettopBoxLastIdleTime OBJECT-TYPE
                SYNTAX  DisplayString
                ACCESS  read-only
                STATUS  mandatory
                DESCRIPTION "The time the last IDLE message was received from 
                             the settop."
                REFERENCE   " -- "
        ::= { ncSettopBoxTableEntry 13 }

ncSettopBoxLastMessageTime OBJECT-TYPE
                SYNTAX  DisplayString
                ACCESS  read-only
                STATUS  mandatory
                DESCRIPTION "The time the last message was received from the 
                             settop."
                REFERENCE   " -- "
        ::= { ncSettopBoxTableEntry 14 }

ncSettopBoxStatus OBJECT-TYPE
                SYNTAX  INTEGER
                        {
                         statusOK                (1),
                         statusQuestionable      (2)
                        }
                ACCESS  read-only
                STATUS  mandatory
                DESCRIPTION "The settop status."
                REFERENCE   " -- "
        ::= { ncSettopBoxTableEntry 15 }

--*****************************************
--
-- NC Down Stream Group
--
--*****************************************

ncOmChassisStatus OBJECT-TYPE
                SYNTAX  INTEGER
                ACCESS  read-only
                STATUS  mandatory
                DESCRIPTION "The OM chassis status. This status for up to 10
                             OMs are contained in 10 2-bit fields."
                REFERENCE   " -- "
        ::= { ncDownStream 1 }
        
-- *******************************************************************
--  The NC1500 Traps Group.
--
--  This group contains those objects which are specifically related
--  to trap & alarm processed by the NC1500.  Trap ID starts at 1000.
-- *******************************************************************

trapSettopCreateFail TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             "This trap is issued if an attempt to create a settop
              settop fails.  No option parameters are used."
        ::= 1000

trapDiskLoadError TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             "This trap is issued if loading of settop information from
              the hard disk or CompactFlash fails.  No option parameters 
              are used."
        ::= 1001

trapAppNetEnetFail TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             "This trap is issued if initialization of the Application Server
              Ethernet card fails.  No option parameters are used."
         ::= 1002

trapNoOobQForPath TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued if the downstream interface service has no
               associated downstream path ID. No option parameters are used."
         ::= 1003

trapNoServiceFreq TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued when a downstream Path ID has no
               associated service channel. The trapAdditionalInfoInteger1 contains
	       related upstream path Id.  No other option parameters are used."
         ::= 1004

trapSettopDatabaseFull TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued when the settop database is full.  No other option
	       parameters are used."
        ::= 1005

trapNoMacMsgQueue TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued if the Downstream Task has no associated 
               MAC signaling message queue.  The trapAdditionalInfoInteger1 contains
	       the downstream task instance number (from 0 to 9).  No other option
	       parameters are used."
        ::= 1006

trapNoAppMsgQueue TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued if the Downstream Task has no associated
               Application message queue.  The trapAdditionalInfoInteger1 contains
	       the downstream task instance number (from 0 to 9).  No other option
	       parameters are used."
        ::= 1007

trapSocketBindFail TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued if the Downstream Task socket bind fails.  The
	       trapAdditionalInfoInteger1 contains the downstream task instance
	       number (from 0 to 9).  No other option parameters are used."
        ::= 1008

trapSendToFail TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued if the Downstream Task cannot send
               data, i.e., the sendto function call fails.  The
	       trapAdditionalInfoInteger1 contains the downstream task instance
	       number (from 0 to 9).  No other option parameters are used."
        ::= 1009

trapDemodulatorFailEvent TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued after a demodulator failure has been 
               detected during upstream path testing. The parameter 
               trapAdditionalInfoInteger1 contains the upstream path Id.  
               The parameter trapAdditionalInfoInteger2 contains the RPD 
               chassis number.  The parameter trapAdditionalInfoInteger3 
               contains the demod number."
        ::= 1010

trapUpstreamPathFailEvent TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued after an upstream path failure is detected
               during path testing. The parameter trapAdditionalInfoInteger1
               contains the upstream path Id.  The parameters 
               trapAdditionalInfoInteger2 and the trapAdditionalInfoInteger3
               are not used."
        ::= 1011

trapDownstreamPathFailEvent TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued after a downstream path failure is detected
               during path testing. The parameter trapAdditionalInfoInteger1
               contains the downstream path Id.  The parameters 
               trapAdditionalInfoInteger2 and the trapAdditionalInfoInteger3
               are not used."
        ::= 1012

trapRpdChassisFailEvent TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued when an RPD failure is detected during 
               path testing. The parameter trapAdditionalInfoInteger1 
               contains the RPD number assinged by the NC.  The
               parameters trapAdditionalInfoInteger2 and 
               trapAdditionalInfoInteger3 are not used."
        ::= 1013

trapSettopDatabaseThresholdReached TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued when the settop database has reached
             the user defined threshold.  The parameter 
             trapAdditionalInfoInteger1 contains the threshold number.  
             The parameters trapAdditionalInfoInteger2 and the 
             trapAdditionalInfoInteger3 are not used."
        ::= 1014

trapDemodulatorFailCondition TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued after the first demodulator failure is 
               detected during path testing and cleared after the last 
               demodulator is recovered. The optional parameters are not used."
        ::= 1015

trapUpstreamPathFailCondition TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued after the first upstream path failure is 
               detected during path testing and cleared after the last 
               upstream path is recovered. The optional parameters are not 
               used."
        ::= 1016

trapDownstreamPathFailCondition TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued after the first downstream path failure is 
               detected during path testing and cleared after the last 
               downstream path is recovered. The optional parameters are not 
               used."
        ::= 1017

trapRpdChassisFailCondition TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued after the first RPD chassis failure is 
               detected during path testing and cleared after the last RPD 
               chassis is recovered.  The option parameters are not used."
        ::= 1018

trapExcessiveUpstreamRetriesCondition TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued for each upstream when the number 
             of retries has exceeded as user defined percentage.  
             This will be set the first time that this condition has 
             been met and cleared when the last conditon has been cleared."
        ::= 1019

        
trapExcessiveDroppedRPDFramesEvent TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued when the NC has detected an overload
             condition resulting in excessive dropped RPD frames for a period
             of time.  The parameter trapAdditionalInfoInteger1 contains the 
             RPD chassis number.  The parameters trapAdditionalInfoInteger2 
             and the trapAdditionalInfoInteger3 are not used."
        ::= 1020  
        
trapDemodBandwidthNearCapacityEvent TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued when the NC has detected the upstream
             bandwidth is approaching capacity on a demodulator.  The parameter 
             trapAdditionalInfoInteger1 contains the RPD chassis number.  The 
             parameter trapAdditionalInfoInteger2 contains the Demod number.  
             The parameter trapAdditionalInfoInteger3 is not used."
        ::= 1021
        
trapMultipathDetected TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued when the NC suspects crosstalk to
             exist between two or more upstream paths."
        ::= 1022
        
trapExcessiveDroppedRPDFramesCondition TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued when the NC has detected an overload
             condition resulting in excessive dropped RPD frames for a period
             of time.  This will be set when the first RPD has met this condition
             and cleared when the last RPD has cleared this condition."
        ::= 1023
        
trapDemodBandwidthNearCapacityCondition TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued when the NC has detected the upstream
             bandwidth is approaching capacity on a demodulator.  This will
             be set when the first Demod has met this condition and cleared
             when the last Demod has cleared this condition."
        ::= 1024
        
trapExcessiveUpstreamRetriesEvent TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued for each upstream when the number 
             of retries has exceeded as user defined percentage.  
             The parameter trapAdditionalInfoInteger1 contains the 
             Upstream ID number.  The parameters trapAdditionalInfoInteger2 
             and the trapAdditionalInfoInteger3 are not used."
        ::= 1025
        
trapExcessiveQuestionableSettops TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued when the percentage of settops in
             the database that are questionable exceeds a configurable
             threshold.  The parameter trapAdditionalInfoInteger1 
             contains the threshold value.  The parameters 
             trapAdditionalInfoInteger2 and the 
             trapAdditionalInfoInteger3 are not used."
        ::= 1026
        
trapExcessivePurgedSettops TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued when the NC has purged 
             more then a configurable number of settops in
             the last hour.  The parameter 
             trapAdditionalInfoInteger1 
             contains the number of purged settops needed 
             to trigger the trap value.  The parameters 
             trapAdditionalInfoInteger2 and the 
             trapAdditionalInfoInteger3 are not used."
        ::= 1027
        
trapExcessDropDownstreamMsgEvent TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued when the NC has dropped 
             more then a configurable number of downstream 
             messages in a configurable amount of time on 
             a downstream.  The parameter 
             trapAdditionalInfoInteger1 contains the 
             downstream ID.  The parameters 
             trapAdditionalInfoInteger2 and 
             trapAdditionalInfoInteger3 are not used."
        ::= 1028
        
trapUpstreamBandwidthNearCapacityEvent TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued when the NC has 
             detected the upstream bandwidth is 
             approaching a user defined capacity 
             across all of the demods on that upstream.  
             The parameter trapAdditionalInfoInteger1 
             contains the Upstream path ID. The 
             parameters trapAdditionalInfoInteger2 and 
             the trapAdditionalInfoInteger3 are not used.
             Note: This alarm trap will be cleared if an 
             Upstream ID is changed, added, or deleted."
        ::= 1029
        
trapUpstreamBandwidthNearCapacityCondition TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued when the NC has 
             detected the upstream bandwidth is 
             approaching a user defined capacity 
             across all of the demods on that upstream.  
             This will be set when the first Upstream 
             has met this condition and cleared when the 
             last Upstream has cleared this condition.  
             The option parameters are not used.  Note:
             This alarm trap will be cleared if an 
             Upstream ID is changed, added, or deleted."
        ::= 1030
        
trapTrafficOnUnconfiguredDemodEvent TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued when the NC has 
             detected traffic on a demod that is not 
             configured.  The parameter 
             trapAdditionalInfoInteger1 
             contains the RPD chassis number and 
             trapAdditionalInfoInteger2 contains the
             Demod number.  The parameter 
             trapAdditionalInfoInteger3 is not used."
        ::= 1031
        
trapTrafficOnUnconfiguredDemodCondition TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued when the NC has 
             detected traffic on a demod that is not 
             configured.  This will be set when the 
             first Demod has met this condition and 
             cleared when the last Demod has cleared 
             this condition. The option parameters 
             are not used."
        ::= 1032
        
trapExcessDropDownstreamMsgCondition TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued when the NC has dropped 
             more then a configurable number of downstream 
             messages in a configurable amount of time on 
             a downstream.  This will be set when the 
             first downstream has met this condition and 
             cleared when the last downstrea has cleared 
             this condition. The option parameters 
             are not used."
        ::= 1033
        
trapPingDeviceFailureEvent TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued when the NC fails to 
             successfully ping a Gateway or Destination. 
             This trap is set after all Gateways and
             Destinations have been periodically pinged. 
             In subsequent periodic pings, if the device 
             responds, the ping is cleared.  This trap 
             may also be cleared if the device is 
             age-out due to 23 continuous hours without 
             traffic destined for this device.  
             AdditionalInfoInteger1 contains the IP 
             address of the device that has failed
             a ping.  trapAdditionalInfoInteger2 and
             trapAdditionalInfoInteger3 are not used."
        ::= 1034
        
trapAgeOutAppServerEvent TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued at or around 
             midnight if the Destination (Application 
             Server) has not been the target of 
             interactive traffic from a settop box in 
             23 continuous hours.  
             AdditionalInfoInteger1 contains the IP 
             address of the device that has failed
             a ping.  trapAdditionalInfoInteger2 and
             trapAdditionalInfoInteger3 are not used."
        ::= 1035
        
trapPingDevDatabaseFullCond TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued when the number 
             of entries in the Ping Gateway and 
             Destination database object is larger 
             than MaxEntriesForPingGateNDest. This 
             value defaults to 20 but can be made 
             larger with a config.ini change. This 
             trap can be cleared if the age-out 
             process removes a device that has has 
             not been the target of interactive 
             traffic from a settop box in 23 
             continuous hours.  The option parameters 
             are not used."
        ::= 1036
        
trapPingFailureOverallCond TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued when any device
             in the Ping Gateways and Destinations 
             database has alarmPingDeviceFailureEvent 
             set. This trap can be cleared if all 
             Gateways and Destinations successfully 
             ping or if all devices in alarm are 
             removed through the age-out process.
             The option parameters are not used."
        ::= 1037
        
trapEntitleRedundantPasswordCondition TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued when the NC has 
             received a redundant or unnecessary 
             entitlement. The option parameters are 
             not used."
        ::= 1038
        
trapEntitleAuthFailureEvent TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This trap is issued when the NC has 
             received an entitlement message 
             containing an invalid entitlement key. 
             The option parameters are not used."
        ::= 1039
        
trapSettopIPShortageCondition TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This alarm occurs when the total 
              number of IP addresses available 
              is insufficient for the configured 
              maximum settop database.  The 
              option parameters are not used."
        ::= 1040
        
trapSuspendedTaskCondition TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
              }
              DESCRIPTION
             " This alarm occurs when a suspended
             task has been detected. The NC1500 
             may reboot automatically due to the
             failure. The condition will be set
             following the reboot. The condition 
             clears if no suspended tasks are 
             detected. AdditionalInfoInteger1 is 
             the VxWorks Task Id. 
             AdditionalInfoInteger2 is remaining 
             number of times NC1500 will 
             automatically reboot. 
             AdditionalInfoInteger3 is unused."
        ::=  1041

-- *******************************************************************
--  Alarm OIDs.  These OIDs correspond to traps declared above and
--  have the same number as the trap number above.
-- *******************************************************************

alarmMasterFail OBJECT-TYPE
           SYNTAX      INTEGER
                        {
                         green        (1),
                         yellow       (2),
                         red          (3),
                         grey         (4)
                        }
           ACCESS      read-only
           STATUS      mandatory
           DESCRIPTION 
              "Alarm which occurs when any alarm appears.  Refer to the
               definitions in the NC 1500 HLD."
   ::= { ncAlarms 999 }

alarmSettopCreateFail OBJECT-TYPE
           SYNTAX      INTEGER
           ACCESS      read-only
           STATUS      mandatory
           DESCRIPTION 
              "This alarm occurs when an attempt to create a settop class 
               instance fails.  This is a counter for trap 1000."
   ::= { ncAlarms 1000 }

alarmDiskLoadError OBJECT-TYPE
           SYNTAX      INTEGER
           ACCESS      read-only
           STATUS      mandatory
           DESCRIPTION 
              "This alarm which occurs when loading settop information from
               disk or CompactFlash fails. This is a counter for trap 1001."
   ::= { ncAlarms 1001 }

alarmAppNetEnetFail OBJECT-TYPE
           SYNTAX      INTEGER
                        {
                         ok                 (1),
                         undetermined       (2),
                         warning            (3),
                         minor              (4),
                         major              (5),
                         critical           (6)
                        }
           ACCESS      read-only
           STATUS      mandatory
           DESCRIPTION 
              "This alarm occurs when initializing the Application Server 
               Ethernet card was failed. This is a condition for trap 1002."
   ::= { ncAlarms 1002 }

alarmNoOobQForPath OBJECT-TYPE
           SYNTAX      INTEGER
           ACCESS      read-only
           STATUS      mandatory
           DESCRIPTION 
              "This alarm occurs when the downstream interface service has no
               downstream path ID associated with it. This is a counter for 
               trap 1003."
   ::= { ncAlarms 1003 }

alarmNoServiceFreq OBJECT-TYPE
           SYNTAX      INTEGER
           ACCESS      read-only
           STATUS      mandatory
           DESCRIPTION 
              "This alarm occurs when a downstream path ID has no service 
               channel frequency associated with it. This is a counter for 
               trap 1004."
   ::= { ncAlarms 1004 }

alarmSettopDatabaseFull OBJECT-TYPE
           SYNTAX      INTEGER
           ACCESS      read-only
           STATUS      mandatory
           DESCRIPTION 
              "This alarm occurs when settop database table is full. This is 
               a condition for trap 1005."
   ::= { ncAlarms 1005 }

alarmNoMacMsgQueue OBJECT-TYPE
           SYNTAX      INTEGER
           ACCESS      read-only
           STATUS      mandatory
           DESCRIPTION 
              "This alarm occurs when downstream task could not find the MAC 
               message queue. This is a counter for trap 1006."
   ::= { ncAlarms 1006 }

alarmNoAppMsgQueue OBJECT-TYPE
           SYNTAX      INTEGER
           ACCESS      read-only
           STATUS      mandatory
           DESCRIPTION 
              "This alarm occurs when downstream task could not find the 
               application message queue.  This is a counter for trap 1007."
   ::= { ncAlarms 1007 }

alarmSocketBindFail OBJECT-TYPE
           SYNTAX      INTEGER
           ACCESS      read-only
           STATUS      mandatory
           DESCRIPTION 
              "This alarm occurs when a downstream task failed to bind to a 
               socket.  This is a counter for trap 1008."
   ::= { ncAlarms 1008 }

alarmSendToFail OBJECT-TYPE
           SYNTAX      INTEGER
                        {
                         ok                 (1),
                         undetermined       (2),
                         warning            (3),
                         minor              (4),
                         major              (5),
                         critical           (6)
                        }
           ACCESS      read-only
           STATUS      mandatory
           DESCRIPTION 
              "This alarm occurs when a sendto call in downstream interface
               failed.  This is a condition for trap 1009."
   ::= { ncAlarms 1009 }

alarmDemodFailEvent OBJECT-TYPE
           SYNTAX      INTEGER
           ACCESS      read-only
           STATUS      mandatory
           DESCRIPTION 
              "This alarm occurs when a demodulator fails. This is a counter
               for trap 1010."
   ::= { ncAlarms 1010 }

alarmUpstreamFailEvent OBJECT-TYPE
           SYNTAX      INTEGER
           ACCESS      read-only
           STATUS      mandatory
           DESCRIPTION 
              "This alarm occurs when a upstream path fails. This is a counter
               for trap 1011."
   ::= { ncAlarms 1011 }

alarmDownstreamFailEvent OBJECT-TYPE
           SYNTAX      INTEGER
           ACCESS      read-only
           STATUS      mandatory
           DESCRIPTION 
              "This alarm occurs when a downstream path fails. This is a 
               counter for trap 1012."
   ::= { ncAlarms 1012 }

alarmRpdChassisFailEvent OBJECT-TYPE
           SYNTAX      INTEGER
           ACCESS      read-only
           STATUS      mandatory
           DESCRIPTION 
              "This alarm occurs when a RPD chassis fails. This is a counter
               for trap 1013."
   ::= { ncAlarms 1013 }

alarmSettopDatabaseThresholdReached OBJECT-TYPE
           SYNTAX      INTEGER
           ACCESS      read-only
           STATUS      mandatory
           DESCRIPTION 
              "This trap is issued when the settop database has reached
               the user defined threshold.  This is a counter for trap 
               1014."
   ::= { ncAlarms 1014 }

alarmDemodFailCondition OBJECT-TYPE
           SYNTAX      INTEGER
           ACCESS      read-only
           STATUS      mandatory
           DESCRIPTION 
              "This alarm is set at the first demodulator failure event
               and is cleared at the last demoulator recover event.
               This is a conditional trap for trap 1010."
   ::= { ncAlarms 1015 }

alarmUpstreamFailCondition OBJECT-TYPE
           SYNTAX      INTEGER
           ACCESS      read-only
           STATUS      mandatory
           DESCRIPTION 
              "This alarm is set at the first upstream path failure event
               and is cleared at the last upstream path recover event.
               This is a conditional trap for trap 1011."
   ::= { ncAlarms 1016 }

alarmDownstreamFailCondition OBJECT-TYPE
           SYNTAX      INTEGER
           ACCESS      read-only
           STATUS      mandatory
           DESCRIPTION 
              "This alarm is set at the first downstream failure event
               and is cleared at the last downdtream recover event.
               This is a conditional trap for trap 1012."
   ::= { ncAlarms 1017 }

alarmRpdChassisFailCondition OBJECT-TYPE
           SYNTAX      INTEGER
           ACCESS      read-only
           STATUS      mandatory
           DESCRIPTION 
              "This alarm is set at the first RPD chassis failure event
               and is cleared at the last RPD chassis recover event.
               This is a conditional trap for trap 1013."
   ::= { ncAlarms 1018 }

alarmExcessiveUpstreamRetriesCondition OBJECT-TYPE
           SYNTAX      INTEGER
           ACCESS      read-only
           STATUS      mandatory
           DESCRIPTION 
              "This trap is issued for each upstream when the number 
               of retries has exceeded as user defined percentage.  
               This will be set the first time that this condition has 
               been met and cleared when the last conditon has been 
               cleared.  This is a conditional trap for trap 1025."
   ::= { ncAlarms 1019 }
   
alarmExcessiveDroppedRPDFramesEvent OBJECT-TYPE
           SYNTAX      INTEGER
           ACCESS      read-only
           STATUS      mandatory
           DESCRIPTION 
              "This trap is issued when the NC has detected an overload
               condition resulting in excessive dropped RPD frames for a period
               of time.  This is a counter for trap 1020."
   ::= { ncAlarms 1020 }
   
alarmDemodBandwidthNearCapacityEvent OBJECT-TYPE
           SYNTAX      INTEGER
           ACCESS      read-only
           STATUS      mandatory
           DESCRIPTION 
              "This trap is issued when the NC has detected the upstream
               bandwidth is approaching capacity on a demodulator.  This 
               is a counter for trap 1021."
   ::= { ncAlarms 1021 }
   
alarmMultipathDetected OBJECT-TYPE
           SYNTAX      INTEGER
           ACCESS      read-only
           STATUS      mandatory
           DESCRIPTION 
              "This trap is issued when the NC suspects crosstalk to
              exist between two or more upstream paths.  This is a 
              counter for trap 1022."
   ::= { ncAlarms 1022 }
   
alarmExcessiveDroppedRPDFramesCondition OBJECT-TYPE
           SYNTAX      INTEGER
           ACCESS      read-only
           STATUS      mandatory
           DESCRIPTION 
              "This trap is issued when the NC has detected an overload
               condition resulting in excessive dropped RPD frames for 
               a period of time.  This will be set when the first RPD 
               has met this condition and cleared when the last RPD has 
               cleared this condition.  This is a conditional trap for 
               trap 1021."
   ::= { ncAlarms 1023 }
   
alarmDemodBandwidthNearCapacityCondition OBJECT-TYPE
           SYNTAX      INTEGER
           ACCESS      read-only
           STATUS      mandatory
           DESCRIPTION 
              "This trap is issued when the NC has detected the upstream
               bandwidth is approaching capacity on a demodulator.  This will
               be set when the first Demod has met this condition and cleared
               when the last Demod has cleared this condition.  This is a 
               conditional trap for trap 1020."
   ::= { ncAlarms 1024 }
   
alarmExcessiveUpstreamRetriesEvent OBJECT-TYPE
           SYNTAX      INTEGER
           ACCESS      read-only
           STATUS      mandatory
           DESCRIPTION 
              "This trap is issued for each upstream when the number 
               of retries has exceeded as user defined percentage.
               This is a counter for trap 1025."
   ::= { ncAlarms 1025 }
   
alarmExcessiveQuestionableSettops OBJECT-TYPE
           SYNTAX      INTEGER
           ACCESS      read-only
           STATUS      mandatory
           DESCRIPTION 
              "This trap is issued when the percentage of settops in
             the database that are questionable exceeds a configurable
             threshold.  This is a counter for trap 1026."
   ::= { ncAlarms 1026 }
   
alarmExcessivePurgedSettops OBJECT-TYPE
           SYNTAX      INTEGER
           ACCESS      read-only
           STATUS      mandatory
           DESCRIPTION 
              "This trap is issued when the NC has purged more then 
             a configurable number of settops in the last hour.  
             This is a counter for trap 1027."
   ::= { ncAlarms 1027 }
   
alarmExcessDropDownstreamMsgEvent OBJECT-TYPE
           SYNTAX      INTEGER
           ACCESS      read-only
           STATUS      mandatory
           DESCRIPTION 
              "This trap is issued when the NC has dropped 
             more then a configurable number of downstream 
             messages in a configurable amount of time on a
             specific downstream.  
             This is a counter for trap 1028."
   ::= { ncAlarms 1028 }
   
alarmUpstreamBandwidthNearCapacityEvent OBJECT-TYPE
           SYNTAX      INTEGER
           ACCESS      read-only
           STATUS      mandatory
           DESCRIPTION 
              "This trap is issued when the NC has detected the upstream
               bandwidth is approaching a user defined capacity across all 
               of the demods on that upstream.  This is a counter for trap 
               1029."
   ::= { ncAlarms 1029 }
   
alarmUpstreamBandwidthNearCapacityCondition OBJECT-TYPE
           SYNTAX      INTEGER
           ACCESS      read-only
           STATUS      mandatory
           DESCRIPTION 
              "This trap is issued when the NC has detected the upstream
               bandwidth is approaching a user defined capacity across all 
               of the demods on that upstream.  This will be set when the 
               first Upstream has met this condition and cleared when the 
               last Upstream has cleared this condition.  This is a 
               conditional trap for trap 1029."
   ::= { ncAlarms 1030 }
   
alarmTrafficOnUnconfiguredDemodEvent OBJECT-TYPE
           SYNTAX      INTEGER
           ACCESS      read-only
           STATUS      mandatory
           DESCRIPTION 
              "This trap is issued when the NC has detected traffic on a 
               demod that is not configured.  This is a counter for trap 
               1031."
   ::= { ncAlarms 1031 }
   
alarmTrafficOnUnconfiguredDemodCondition OBJECT-TYPE
           SYNTAX      INTEGER
           ACCESS      read-only
           STATUS      mandatory
           DESCRIPTION 
              "This trap is issued when the NC has detected traffic on a 
               demod that is not configured.  This will be set when the 
               first Demod has met this condition and  cleared when the 
               last Demod has cleared this condition.  This is a 
               conditional trap for trap 1031."
   ::= { ncAlarms 1032 }
   
alarmExcessDropDownstreamMsgCondition OBJECT-TYPE
           SYNTAX      INTEGER
           ACCESS      read-only
           STATUS      mandatory
           DESCRIPTION 
              "This trap is issued when the NC has dropped 
             more then a configurable number of downstream 
             messages in a configurable amount of time on a
             specific downstream. This will be set when the 
             first downstream has met this condition and  
             cleared when the last downstreamd has cleared 
             this condition.  This is a conditional trap 
             for trap 1028."
   ::= { ncAlarms 1033 }
   
alarmPingDeviceFailureEvent OBJECT-TYPE
           SYNTAX      IpAddress
           ACCESS      read-only
           STATUS      mandatory
           DESCRIPTION 
              "This trap is issued when the NC fails to successfully ping a
               Gateway or Destination. This trap is set after all Gateways and
               Destinations have been periodically pinged. In subsequent
               periodic pings, if the device responds, the ping is cleared. 
               This trap may also be cleared if the device is age-out due to
               23 continuous hours without traffic destined for this device."
   ::= { ncAlarms 1034 }
   
alarmAgeOutAppServerEvent OBJECT-TYPE
           SYNTAX      IpAddress
           ACCESS      read-only
           STATUS      mandatory
           DESCRIPTION 
              "This trap is issued at or around midnight if the Destination 
               (Application Server) has not been the target of interactive 
               traffic from a settop box in 23 continuous hours."
   ::= { ncAlarms 1035 }
   
alarmPingDevDatabaseFullCond OBJECT-TYPE
           SYNTAX      INTEGER
           ACCESS      read-only
           STATUS      mandatory
           DESCRIPTION 
              "This trap is issued when the number of entries in the Ping 
               Gateway and Destination database object is larger than 
               MaxEntriesForPingGateNDest. This value defaults to 20 but
               can be made larger with a config.ini change. This trap can
               be cleared if the age-out process removes a device that has
               has not been the target of interactive traffic from a settop 
               box in 23 continuous hours."
   ::= { ncAlarms 1036 }
   
alarmPingFailureOverallCond OBJECT-TYPE
           SYNTAX      INTEGER
           ACCESS      read-only
           STATUS      mandatory
           DESCRIPTION 
              "This trap is issued when any device in the Ping Gateways and
               Destinations database has alarmPingDeviceFailureEvent set. This
               trap can be cleared if all Gateways and Destinations 
               successfully ping or if all devices in alarm are removed through
               the age-out process."
   ::= { ncAlarms 1037 }
   
alarmEntitleRedundantPasswordCondition OBJECT-TYPE
           SYNTAX      INTEGER
           ACCESS      read-only
           STATUS      mandatory
           DESCRIPTION 
              "This trap is issued when the NC has received a redundant or 
              unnecessary entitlement."
   ::= { ncAlarms 1038 }
   
alarmEntitleAuthFailureEvent OBJECT-TYPE
           SYNTAX      INTEGER
           ACCESS      read-only
           STATUS      mandatory
           DESCRIPTION 
              "This trap is issued when the NC has received an entitlement 
              message containing an invalid entitlement key."
   ::= { ncAlarms 1039 }
   
alarmSettopIPShortageCondition OBJECT-TYPE
           SYNTAX      INTEGER
                        {
                         ok                 (1),
                         undetermined       (2),
                         warning            (3),
                         minor              (4),
                         major              (5),
                         critical           (6)
                        }
           ACCESS      read-only
           STATUS      mandatory
           DESCRIPTION 
              "This alarm occurs when the total number of IP addresses 
               available is insufficient for the configured maximum 
               settop database.  This is a condition for trap 1040."
   ::= { ncAlarms 1040 }

alarmTaskSuspendedCondition OBJECT-TYPE
           SYNTAX      INTEGER
                        {
                         ok                 (1),
                         undetermined       (2),
                         warning            (3),
                         minor              (4),
                         major              (5),
                         critical           (6)
                        }
           ACCESS      read-only
           STATUS      mandatory
           DESCRIPTION 
              "This alarm occurs when a suspended task has been 
               detected. The NC1500 may reboot automatically due
               to the failure. The condition will be set 
               following the reboot. The condition clears if no
               suspended tasks are detected. This is a condition
               for trap 1041."
   ::= { ncAlarms 1041 }


-- *******************************************************************
--  The NLSBBN Traps Group.
--
--  This group contains those objects which are commonly defined but
--  the ENTERPRISE is specific to the NC1500.  Trap IDs start at 1.
-- *******************************************************************

trapNewNEFound TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedValueOID
                }
           DESCRIPTION
             "This trap is isssued if a Proxy Agent Detected A New NE.
              trapPerceivedSeverity - 'indeterminate'
              trapChangedValueOID - This  variable identifies the new
              Network Element.  This trap is not issues by non-proxy
              agents."
   ::= 1


trapNewNELost TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedValueOID
                }
           DESCRIPTION
             "This trap is isssued if a Proxy Agent lost communication with
              NE.  trapPerceivedSeverity - 'critical'.
              trapChangedValueOID - This  variable identifies the new
              Network Element. This trap is not issues by non-proxy agents."
   ::= 2


trapConfigurationChangeInteger TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger
                }
           DESCRIPTION
             "This trap is issued if configuration of a single variable
              with integer type was changed (via ANY interface).  
              TrapChangedValueInteger variable may contain current reading
              of that variable.
              trapPerceivedSeverity - 'indeterminate'"
   ::= 3


trapConfigurationChangeDisplayString TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueDisplayString
               }
           DESCRIPTION
             "This trap is issued if configuration of a single variable
              with DispalayString type was changed (via ANY interface).  
              TrapChangedValueDisplayString variable may contain current
              reading of that variable.
              trapPerceivedSeverity - 'indeterminate'"
   ::= 4


trapConfigurationChangeOID TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueOID
               }
           DESCRIPTION
             "This trap is issued if configuration of a single variable
              with OID type was changed (via ANY interface).  
              TrapChangedValueOID variable may contain current reading
              of that variable.
              trapPerceivedSeverity - 'indeterminate'"
   ::= 5

trapConfigurationChangeIpAddress TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueIpAddress
               }
           DESCRIPTION
             "This trap is issued if configuration of a single variable
              with IpAddress type was changed (via ANY interface).  
              TrapChangedValueIpAddress variable may contain current reading
              of that variable.
              trapPerceivedSeverity - 'indeterminate'"
   ::= 6


trapToBeSendQueueOverflow TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp
               }
           DESCRIPTION
             "This trap is issued if SNMP agent's TrapToBeSendQueue is full.
              trapPerceivedSeverity - 'major'
              trapNetworkElemModelNumber - Model # of the Agent
              trapNetworkElemSerialNum - Serial # of the Agent
              trapNetworkElemOperState - from Ident MIB
              trapNetworkElemAlarmStatus - from Ident MIB   
              trapNetworkElemAdminState - from Ident MIB
              trapNetworkElemAvailStatus - from Ident MIB"
   ::= 7

-- *******************************************************************
--  The DNS Traps Group.
--
--  This group contains those objects which are commonly defined but
--  ENTERPRISE is sepecific to NC1500. Traps ID starts from 20. 
-- *******************************************************************

trapConditionNotInList TRAP-TYPE
           ENTERPRISE nc1500
           VARIABLES
               {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
                }
            DESCRIPTION
              "This trap is issued if a condition is being cleared and
               it is not in the condition list.
               trapAdditionalInfoInteger1 : Task and Function ID (task
                                            and function generates the
                                            error condition)
               trapAdditionalInfoInteger2 : Condition number
               trapAdditionalInfoInteger3 : Condition severity" 
   ::= 20

trapConditionAlreadyInList TRAP-TYPE
            ENTERPRISE nc1500
            VARIABLES
                {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
                }
            DESCRIPTION
              "This trap is issued if a condition is being set and
               it is already in the condition list.
               trapAdditionalInfoInteger1 : Task and Function ID (task
                                            and function generates the
                                            error condition)
               trapAdditionalInfoInteger2 : Condition number
               trapAdditionalInfoInteger3 : Condition severity"
   ::= 21

trapConditionListFull TRAP-TYPE
            ENTERPRISE nc1500
            VARIABLES
                {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
                }
            DESCRIPTION
              "This trap is issued if a condition is being set and
               the condition list is full.
               trapAdditionalInfoInteger1 : Task and Function ID (task
                                            and function generates the
                                            error condition)
               trapAdditionalInfoInteger2 : Condition number
               trapAdditionalInfoInteger3 : Condition servirty" 
   ::= 22

trapInvalidCaseInSwitch TRAP-TYPE
            ENTERPRISE nc1500
            VARIABLES
                {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                       trapText,
                        trapNETrapLastTrapTimeStamp,
                        trapChangedObjectId,
                        trapChangedValueInteger,  
                        trapAdditionalInfoInteger1, 
                        trapAdditionalInfoInteger2, 
                        trapAdditionalInfoInteger3     
                }
            DESCRIPTION
              "This trap is issued when in a switch statement the
               default case is reached.  The trapAdditionalInfoInteger1
               will contain the task and Function ID.  The
               trapAdditionalInfoInteger2 will contain value of the switch.
               The trapAdditionalInfoInteger3 is not used."
   ::= 23

trapCannotCreateSemaphore TRAP-TYPE
            ENTERPRISE nc1500
            VARIABLES
                {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
                }
            DESCRIPTION
              "This trap is issued when a semaphore cannot
               be created. The trapAdditionalInfoInteger1 will contain the
               task and Function ID, the trapAdditionalInfoInteger2 and
               trapAdditionalInfoInteger3 will not be used."
   ::= 24

trapCannotOpenSocket TRAP-TYPE
            ENTERPRISE nc1500
            VARIABLES
                {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
                }
            DESCRIPTION
              "This trap is issued when a socket cannot
               be opened. The trapAdditionalInfoInteger1 will contain the
               task and Function ID. The trapAdditionalInfoInteger2 will
               contain the errno returned by the call to socket(). The
               trapAdditionalInfoInteger3 is not used."
   ::= 25

trapUnknownMessageReceived TRAP-TYPE
            ENTERPRISE nc1500
            VARIABLES
                {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
                }
            DESCRIPTION
              "This trap is issued when an unknown message
               is received.  The trapAdditionalInfoInteger1 will contain the
               task and Function ID. The trapAdditionalInfoInteger2 will 
               contain the message ID and the trapAdditionalInfoInteger3 is
               not used."
   ::= 26

trapInvalidMessageReceived TRAP-TYPE
            ENTERPRISE nc1500
            VARIABLES
                {       
                        trapIdentifier,
                        trapNetworkElemModelNumber,
                        trapNetworkElemSerialNum,
                        trapPerceivedSeverity,
                        trapNetworkElemOperState,
                        trapNetworkElemAlarmStatus,  
                        trapNetworkElemAdminState,
                        trapNetworkElemAvailStatus,
                        trapText,
                        trapNETrapLastTrapTimeStamp,
                        trapChangedObjectId,
                        trapChangedValueInteger,  
                        trapAdditionalInfoInteger1, 
                        trapAdditionalInfoInteger2, 
                        trapAdditionalInfoInteger3     
                }
            DESCRIPTION
              "This trap is issued when an invalid message
               is received.  The trapAdditionalInfoInteger1 will contain the
               task and Function ID. The trapAdditionalInfoInteger2 will
               contain the message ID and the trapAdditionalInfoInteger3 is
               not used."
   ::= 27

END
