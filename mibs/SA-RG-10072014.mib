--**************************************************************************
--                                                                          
--    Copyright 2011 Cisco Systems, Inc.
--    All Rights Reserved                                                   
--    No portions of this material may be reproduced in any
--    form without the written permission of:                                                
--        Cisco Systems, Inc.
--        170 West Tasman Dr.
--        San Jose, CA 95134
--        USA
--                                                 
--**************************************************************************

SA-RG-MIB DEFINITIONS ::= BEGIN
IMPORTS
        MODULE-IDENTITY, 
        OBJECT-TYPE,
        enterprises, 
        Integer32,
        IpAddress
                FROM SNMPv2-SMI
        ifIndex
                FROM IF-MIB
        RowStatus,
        DisplayString,
        MacAddress,
        PhysAddress,
        TruthValue,
        DateAndTime
                FROM SNMPv2-TC
        InetAddressType,
        InetAddress,
		InetAddressIPv6,
        InetPortNumber
                FROM INET-ADDRESS-MIB
        SnmpAdminString 
                FROM SNMP-FRAMEWORK-MIB ;

sa           OBJECT IDENTIFIER ::= { enterprises 1429 }
saModules    OBJECT IDENTIFIER ::= { sa 79 }
                
saRg    MODULE-IDENTITY
        LAST-UPDATED    "201409220000Z"
        ORGANIZATION    "Cisco Systems, Inc."
        CONTACT-INFO    "http://support.cisco.com"
        DESCRIPTION
            "Controls the behavior of router/wireless functions.
             Can be part of CM configuration file."

        -- History  
        REVISION "201409220000Z"
        DESCRIPTION "Added saRgIpMgmtConnectedDevices MIB tree node"
        
        REVISION "201409090000Z"
        DESCRIPTION "Added value of 0(disable) to saRgDeviceMode to correlate with TLV202"
        
        
		REVISION "201406130000Z"
    DESCRIPTION "Change of saRgDot11BssPrimarySsidSuffix feature. Suffix added is now G instead of Ghz (CR24389)"
	
		REVISION "201405160000Z"
    DESCRIPTION "Added saRgL2ogreTcpMssClamping"

		REVISION "201403270000Z"
	DESCRIPTION "Added saRgIpMgmtWanAddrDynamicGateway, replaced saRgIpMgmtLanAddrRequestedIpAddress with saRgIpMgmtLanAddrRequestedOptionsList"

		REVISION "201403260000Z"
	DESCRIPTION "Added MIBs for VSAF"

        REVISION "201403250000Z"
	DESCRIPTION "Added 
				saRgIpMgmtDnsServerIpv6 (CR23803)
				saRgDot11ClientConnectMode (CR23649)
				saRgFirewallIpv6Protection (CR23798)
				saRgDot11BssRejectPriSsidStaCount (CR23390)
				saRgIpMgmtLanAddrIpv6Table (CR24093)
				"
		
        REVISION "201402180000Z"
	DESCRIPTION "Added bitmask on WebWizard for USB setting, NAS and media server tab(23504)"
	             
                   
		REVISION "201401160000Z"
	DESCRIPTION "Changed saRgWifiHotspotInsertDhcpOptionsMask. Added option for CM MAC address included in DHCP option 82.2 (CR23343)"
			
		REVISION "201401140000Z"
	DESCRIPTION "Add rgPortForward(3) to saRgDeviceConfigSnmpEnable(CR23485)"
		
		REVISION "201312190000Z"
	DESCRIPTION "Added saRgDot11BssPrimarySsidSuffix, saRgWifiHotspotDisablePMKCaching, saRgWifiHotspotConnectionSpeedMin, saRgWifiHotspotConnectionSpeedTimeout, saRgWifiHotspotRadiusAccInterimInterval"

                REVISION "201311050000Z"
	DESCRIPTION "Modified values and description for saRgDot11nMode/nExtMode"

                REVISION "201309200000Z"
	DESCRIPTION "Added support for saRgNetworkExtenders MIB
                Added:  saRgNetworkExtenderTable
                        saRgNetworkExtenderRadioTable
                        saRgNetworkExtenderClientTable"

                REVISION "201309170000Z"
	DESCRIPTION "Modified Values and description for
                   saRgDot11nMode
                   saRgDot11nExtMode"

                REVISION "201308280000Z"
	DESCRIPTION "Added WiFi 2.4 and 5 Ghz support for saRgIpMgmtLanAddrInterface MIB

                Added: saRgFirewallPortForwardEnable
                saRgFirewallPortTriggerEnable
                saRgFirewallIpFilterTrusted
                saRgFirewallIpFilterPolicy
                saRgFirewallPortFilterAlwaysBlock
                saRgFirewallPortFilterBlockStartTime
                saRgFirewallPortFilterBlockEndTime
                saRgFirewallPortFilterBlockDays
                saRgFirewallMacFilterAlwaysBlock
                saRgFirewallMacFilterBlockStartTime
                saRgFirewallMacFilterBlockEndTime
                saRgFirewallMacFilterBlockDays
                saRgFirewallPortFilterEnable
                saRgFirewallUrlKeywordFilterTable
                saRgFirewallUrlKeywordFilterEnable"

                REVISION "201308270000Z"
        DESCRIPTION "Added saRgDot11ApsScan MIB tree"

                REVISION "201308140000Z"
        DESCRIPTION "Added saRgDeviceIanaContent, saRgDeviceIapdContent"

                REVISION "201308070000Z"
        DESCRIPTION "Added saRgIGMP, saRgIGMPMaxRspTime"

                REVISION "201307220000Z"
        DESCRIPTION "Added saRgL2ogreKeepAliveFailureInterval, saRgL2ogreKeepAliveReattemptInterval, saRgWifiHotspotCapable and saRgWifiHotspotConnectedClientsTable"

        REVISION "201306240000Z"
        DESCRIPTION "Added saRgIpMgmtWanStaticNameServerEnable, saRgIpMgmtWanStaticHostName, saRgIpMgmtWanStaticDomainName"

        REVISION "201306110000Z"
        DESCRIPTION "Added saRgFirewallIdentBlockingEnable, saRgFirewallIcmpBlockingEnable, saRgFirewallMulticastBlockingEnable"

        REVISION "201306070000Z"
        DESCRIPTION "Modified saRgdot11nBandWidth and saRgdot11nExtBandWidth to include support for 80MHz BW on 802.11ac cards"

  REVISION "201305010000Z"
  DESCRIPTION "Added saRgDeviceIpv6Passthrough"

  REVISION "201303040000Z"
  DESCRIPTION "Added saRgL2TPv3TunnelInterface value allEthernet(0) and updated the description"

        REVISION "201301020000Z"
        DESCRIPTION "Added saRgRipAuthType and saRgRipAuthSimplePassword"

        REVISION "201212070000Z"
        DESCRIPTION "Addes saRgDot11ChannelSelectionPolicy"

    REVISION "201211070000Z"
    DESCRIPTION "Added saRgFirewallPortFwdExternalPortStart and saRgFirewallPortFwdExternalPortEnd"

    REVISION "201210010000Z"
    DESCRIPTION "Modified saRgL2ogreOrigIf"

        REVISION "201209190000Z"
    DESCRIPTION "Added saRgIpMgmtLanDhcpOption43"

    REVISION "201209190000Z"
    DESCRIPTION "Added saRgFirewallPortTrigSrvcName, changed saRgDot11BssSecSsidTrafficPriority value 1 to acBk"

    REVISION "201209100000Z"
    DESCRIPTION "Added saRgFirewallPortFwdSrvcName to saRgFirewallPortFwdEntry"

    REVISION "201209070000Z"
    DESCRIPTION "Updated saRgFirewallProtection with custom(4), and saRgFirewallTrafficPassThru with ident(3) and icmp(4)"

    REVISION "201208270000Z"
    DESCRIPTION "Added saRgDot11BssRejectPriSsidSta (21104)"

    REVISION "201208270000Z"
    DESCRIPTION "Added saRgDot11BssSecSsidTrafficPriority (20232)"

    REVISION "201208230000Z"
    DESCRIPTION "Corrected syntax errors in saRgDeviceFactoryReset and saRgDeviceReset
                        Modified saRgDot11BssMaxNumSta from read-only to read-write"

    REVISION "201207250000Z"
    DESCRIPTION "Modified the default values of saRgDot11WpaGroupRekeyInterval and saRgDot11RadiusReAuthInterval - CR 21057"

    REVISION "201207120000Z"
    DESCRIPTION "Added: saRgIpMgmtWanAddrDynamicIp
                                                saRgIpMgmtWanAddrDynamicLeaseTime
                                                saRgFirewallFactoryReset
                                                saRgFirewallHttpBlockingEnable
                                                saRgFirewallP2pBlockingEnable
                                                saRgIpMgmtLanAddrClientNotes
                                                saRgIpMgmtLanAddrCpeStatus
                                                saRgIpMgmtLanDhcpServerDomainName
                                                saRgDeviceFactoryReset
                                                saRgDeviceReset"

    REVISION "201207110000Z"
    DESCRIPTION "Added plain/encapsulation mode mappings to the saRgDslitePcpMode description"

    REVISION "201207010000Z"
    DESCRIPTION "ADDED saRgWifiHotspot MIB tree
                         ADDED saRgL2oGRE MIB tree"

    REVISION "201206140000Z"
    DESCRIPTION "Modified the data types of saRgIpMgmtNatTcpWait, saRgIpMgmtNatUdpWait, and saRgIpMgmtNatIcmpWait from INTEGER to Unsigned32 - CR 20790"

    REVISION "201206120000Z"
    DESCRIPTION "Fixed small error in comments causing compile problems"

    REVISION "201204160000Z"
    DESCRIPTION "Removed saRgDot1154gNetMode and saRgDot11Ext54gNetMode - CR 20357/19913"

    REVISION "201203160000Z"
    DESCRIPTION "Added saRgDot11ExtCtsProtectionEnable and removed saRgdot11Ext54gProtectionEnable/nExtProtection. Also, added the n-only(3) option in saRgdot11nMode/nExtMode - CR 20227/20246"

    REVISION "201203080000Z"
    DESCRIPTION "Modified saRgIpMgmtLanUpnp to indicate UPnP control is now available for all networks - CR 19832"

    REVISION "201203060000Z"
    DESCRIPTION "Added saRgDot11ExtMgmt and saRgDot11nExt trees for multi-radio operation - CR 20227"

    REVISION "201203050000Z"
    DESCRIPTION "Added saRgDslitePcpMode MIB - CR20218"

    REVISION "201202010000Z"
    DESCRIPTION "Added saRgIpMgmtLanAddrInterface - CR -- 19894"

    REVISION "201201190000Z"
    DESCRIPTION "Updated saRgDsliteTcpMssClamping and saRgDsliteIPv4FragEnabled description -- CR 19941"

    REVISION "201201180000Z"
    DESCRIPTION "Added saRgDsliteTcpMssClamping and saRgDsliteIPv4FragEnabled -- CR 19941"

    REVISION "201112150000Z"
    DESCRIPTION "Changed default value of saRgVlanStripTagsWan to true - CR 18055
                Updated saRgDot11WmmNoAck MIB descriptions --CR 18824"

    REVISION "201111220000Z"
    DESCRIPTION "Updated saRgDot11Wmm and saRgDot11WmmNoAck MIB descriptions --CR 18824"

    REVISION "201111170000Z"
    DESCRIPTION "Changed saRgDeviceIpv6Trans to read-only, updated description to reflect new behavior"

    REVISION "201111160000Z"
    DESCRIPTION "Removed option-54(2) from saRgDsliteOption"

    REVISION "201111100000Z"
    DESCRIPTION "Added saRgIpMgmtLanExtraSubnetGateway.x and changed saRgIpMgmtLanExtraSubnetIpAddress from
    read-only to read-write access. -- CR 19474.
    Added saRgDot11WirelessButtonOperation : Wireless ON/OFF Button Operation (if exit) --CR 19443.
    Updated description of saRgDot11BssUserStatus."

    REVISION "201110270000Z"
    DESCRIPTION "Added saRgDeviceIpv6Trans, saRgDsliteOption, saRgDsliteAftrAddress, saRgDsliteAftrName, saRgDsliteApplySettings - CRs 19548, 19572, 19573, 19576, 19586"

    REVISION "201110190000Z"
    DESCRIPTION "Removed saRgVlanIndex.x -- CR 18055
    Added saRgDeviceLanLanIsolation, saRgDeviceLanWlanIsolation and saRgDot11BssApIsolation -- CR 15633"

    REVISION "201110060000Z"
    DESCRIPTION "Updated description for saRgDot11MbssUserControl and saRgDot11MbssAdminControl
    Support for utilizing Bit16 and above as a bit mask value for allowing/disallowing MBSS configuration"

    REVISION "201109280000Z"
    DESCRIPTION "Updated saRgFirewallTrafficBlock and saRgFirewallProtection (Updated low/ enable in desc) MIB description -- CR 19428"

    REVISION "201109070000Z"
    DESCRIPTION "Updated saRgDevUserLanAccessEnabled MIB definition."

    REVISION "201109060000Z"
    DESCRIPTION "Updated saRgDevUserLanAccessEnabled MIB definition CR-19105. This MIB is only available for D2.0"

    REVISION "201108030000Z"
    DESCRIPTION "Updated MIB descriptions for saRgIpMgmtLanMode, saRgVlanStripTagsWan and saRgVlanStripTagsLan CR-18556"

    REVISION "201107250000Z"
    DESCRIPTION "Added clarification about saRgIpMgmtLanNetworksAllow MIB behavior when the
    MIB value is a default value - CR 188670"

    REVISION "201107110000Z"
    DESCRIPTION "Added saRgFirewallMacFilterEnable and saRgFirewallMacFilterMode to sync with MAC Address Filter
    Web GUI controls - CR 17542
    Added saRgDot11Wmm MIB to enable/disable Wifi Multi Media QOS feature -CR 18824
    Added saRgDot11WmmNoAck MIB to enable/disable Wifi Multimedia No Acknowledgement feature -CR 18824
    Added saRgVlanUpnp and saRgVlanApplySettings MIBs- CR 18055
    Added saRgDot11BssHotSpot to saRgDot11BssEntry per CR 18153
    Added saRgDot11MulticastRate and saRgdot11nMulticastRate mulitcast rate configuration MIBs -CR 18899."

    REVISION "201107010000Z"
    DESCRIPTION "Added saRgDot11BssUserStatus mibs for 18263"

    REVISION "201106100000Z"
    DESCRIPTION "Added saRgVlan mibs and added vlan(5) control option to saRgIpMgmtLanMode CR 18055"

    REVISION "201106070000Z"
    DESCRIPTION "Updated saRgIpMgmtLanMode MIB description to indicate Mixed Mode support NOT AVAILABLE for DOCSIS 2.0 products."

    REVISION "201105020000Z"
    DESCRIPTION "Added saRgdot11nObssCoex to saRgDot11n tree"

        REVISION "201104210000Z"
        DESCRIPTION "Modified the index size for saRgFirewallMacFilterIndex from 10 to 20 - CR 17294
                     Updated the index size for saRgFirewallPortFwdIndex from 10 to 30 - CR 17891"

        REVISION "201102080000Z"
        DESCRIPTION "Modified the list size saRgDot11CurrentChannel to reflect channels supported in 802.11n 2.4 & 5 GHz band"

    REVISION "201101190000Z"
    DESCRIPTION "Changed saRgDeviceRemoteWebAccessPort MIB to be stored in non-vol"

    REVISION "201101100000Z"
    DESCRIPTION "BAC RG-MIB compile issue. Removed an extra ',' in the saRgQosSwitchClassPrioritySetPort MIB"

        REVISION "201012200000Z"
        DESCRIPTION "i) Changed ip_mac_portFiltering(7) to ipMacPortFiltering(7) in SaRgUserChangedFlag
                        As the MIB tool will report an error for the use of '_'"

        REVISION "201011300000Z"
        DESCRIPTION "Added saRgIpMgmtRestoreDefaults"

    REVISION "201011160000Z"
    DESCRIPTION "i) Updated saRgDeviceMode
                    ii) Updated saRgIpMgmtLanMode "

    REVISION "201010190000Z"
    DESCRIPTION "i) Added l2TP(25) under SaRgUserChangedFlag for L2TP feature
                     ii)Added ethernet(1..4) under saRgL2TPv3TunnelInterface MIB"

    REVISION "201010070000Z"
    DESCRIPTION "i) Updated saRgDeviceL2TP to saRgL2TP for all the MIBs under saRgL2TP tree "

    REVISION "201010060000Z"
        DESCRIPTION "i) saRgDeviceMode modified for eRouter CR17253
                                        Added values (3)ipv4, (4)ipv6, and (5)dualstack.
                                        Added default value (1)
                                        Updated description to clarify interaction with TLV202
                    ii) saRgIpMgmtLanMode  modified for eRouter CR17253
                                        Clarified description
                                        Added Default value (2)
                   iii) saRgDeviceConfigSnmpEnable modified for eRouter CR17253
                                        Updated description (ipv4RG only)"

    REVISION "201010050000Z"
        DESCRIPTION "i)Added a saRgDeviceL2TP MIB tree under saRg 10 - CR17249
                    ii)saRgIpMgmtLanMode no longer supports l2tp-client(3)
                   iii)saRgIpMgmtL2tpClientTable is obsoleted and will not be supported"


    REVISION "201009020000Z"
        DESCRIPTION "Updated description for saRgIpMgmtLanPortMode"

    REVISION "201009020000Z"
        DESCRIPTION "Updated description for saRgDot11MbssUserControl and saRgDot11MbssAdminControl
        support for 8 SSIDs"

    REVISION "201008230000Z"
    DESCRIPTION "Renamed saRgDeviceLanPortControl MIB tree to saRgIpMgmtLanPortControl
                                 and moved saRgDeviceLanPortControl MIB tree under saRgIpMgmt"

    REVISION "201008200000Z"
    DESCRIPTION "Added value mixed(4) to saRgIpMgmtLanMode,
                        Added saRgDeviceLanPortControl MIB tree"

        REVISION "201008130000Z"
        DESCRIPTION " Increase the range of the saRgDot11MbssUserControl and saRgDot11MbssAdminControl from
        1..4 to 1..8 to support 8 SSIDs"

        REVISION "201007300000Z"
        DESCRIPTION "Add rgLanIp(2) to saRgDeviceConfigSnmpEnable"

        REVISION     "201007280000Z"
        DESCRIPTION
             "Added saRgHomePlugAV module under saRg {saRg 9} which includes the following tables (16664)
             1. saRgHomePlugAVBasicInfoTable
                This table provides network id of Home Plug AV device on the AVLN and CCO information.
             2. saRgHomePlugAVDeviceTable
                This table shows firmware version, MAC address of Home Plug AV device, chipset, Tx rate,
                Rx rate and other information. Besides providing local Home Plug AV device information
                (saRgHPAVDeviceAdaptor OID = ‘local’), the table also provides remote Home Plug AV device
                information (saRgHPAVDeviceAdaptor OID = ‘remote’).
             3. saRgHomePlugAVHostTable
                This table provides bridge MAC address information of Home Plug AV device that are connected
                with Ethernet port behind RG.
             4. Operation OIDs
                These OIDs include saRgHomePlugAVPollRate, saRgHomePlugAVClearTable and
                saRgHomePlugAVRefreshTable, which provide operations on manipulation of above tables
                to scan Home Plug AV devices or to clear (reset) saRgHomePlugAVBasicInfoTable,
                saRgHomePlugAVDeviceTable and saRgHomePlugAVHostTable."


        REVISION     "201007120000Z"
    DESCRIPTION
             "Updated saRgDeviceConfigSnmpEnable to allow SNMP access on RG LAN side.(16317)
              Added saRgIpMgmtLanUpnp to control the UPnP agent (16623)"

    REVISION     "201006240000Z"
    DESCRIPTION
             "Added saRgIpMgmtLanNetworksAllow to control the classes of Lan Networks allowed
              behind the router (16626)"

    REVISION     "201006150000Z"
    DESCRIPTION
             "Changing the bits in SaRgUserChangedFlag as per the current
             implementation"

    REVISION     "201006040000Z"
    DESCRIPTION
             "Correcting the description in saRgDot1154gNetMode. Correcting
             the values in SaRgUserChangedFlag "


    REVISION     "201005210000Z"
    DESCRIPTION
             "saRgDeviceRemoteWebAccessEnable is applicable for legacy web
             pages. So making the status as current from obsolete and adding
             a note that it is only applicable for legacy style web pages"


    REVISION     "201005130000Z"
    DESCRIPTION
             "Updated the SaRgUserChangedFlag and saRgDeviceUserChangedFlag
                 by adding the relavent sections that were missing in the web pages
             and added a note for the behavior of MIB on the legacy style web
             pages"

    REVISION     "201005050000Z"
    DESCRIPTION
             "Moved the relavent Web Access MIBs to SA-CM.mib and obsoleted
             SaRgWebWizardSetup2,
             saRgDeviceUserAccessReadPages2,
             saRgDeviceUserAccessWritePages2,
             saRgDeviceAdminReadOnly,
             saRgDevUserLanAccessEnabled,
             saRgDeviceRemoteWebAccessEnable,
             saRgDevUserAccessClearPassword,
             saRgDevUserAccessDefaultPassword,
             saRgDevUserAccessUsername
             "

    REVISION     "201003120000Z"
    DESCRIPTION
             "Added saRgDot11OnOffPushButtonTime (15869)"

    REVISION     "201002010000Z"
    DESCRIPTION
             "Added saRgIpMgmtWanAddrBackupDefGw (15736)
              Changed saRgIpMgmtStaticRouteTable to be stored in non-vol (4213)
              Added saRgFirewallReportEmailUsername (15735)
              Added saRgFirewallReportEmailPassword (15735)"

    REVISION     "200912140000Z"
    DESCRIPTION
             "Added saRgDeviceConfigIgnore (3203)
              Changed saRgIpMgmtWanTtl DEFVAL to 0 (4630)
              Added enableOnline(3) to saRgDot11BssEnable (4614)
              Added saRgDot11BssMaxNumSta (4615)
              Added saRgDot11BssCountStaAsCpe (4617)
              Added saRgFirewallWANBlockingEnable (4743)
              Changed saRgDevUserAccessEnabled to saRgDevUserLanAccessEnabled (4854)
              Added remoteAccess(30) to SaRgWebWizardSetup (4855)
              Added variables to SaRgWebWizardSetup2 (4858)
              Added saRgQosLanIgmpSnooping (4891)
              Added saRgIpMgmtLanDhcp125Option (15007)
              Added saRgDeviceAdminReadOnly (15056)"

    REVISION     "200907240000Z"
    DESCRIPTION
             "Added saRgDevUserAccessUsername (4274)
              Added saRgDeviceUserChangedFlag (3301)"

    REVISION     "200907060000Z"
    DESCRIPTION
             "Added saRgDeviceConfigSnmpEnable (4167,4168)"

    REVISION     "200907020000Z"
    DESCRIPTION
             "Added SaRgWebWizardSetup2
              Obsoleted SaRgWebWizardSetup
              Added saRgDeviceUserAccessReadPages2
              Added saRgDeviceUserAccessWritePages2
              Obsoleted saRgDeviceUserAccessReadPages
              Obsoleted saRgDeviceUserAccessWritePages (4131, 4858)"

    REVISION     "200906240000Z"
    DESCRIPTION
             "Added saRgDot11n tree (4067)"

    REVISION     "200906020000Z"
    DESCRIPTION
             "Added l2tp-client(3) to saRgIpMgmtLanMode (3200)
              Added saRgIpMgmtL2tpClientTable (3200)
              Added saRgQos (4065)"

    REVISION     "200902160000Z"
    DESCRIPTION
             "Removed maxCompatibility(5) from saRgDot1154gNetMode (3200)"

    REVISION     "200809300000Z"
    DESCRIPTION
            "Changed saRgIpMgmtDnsServerIp to store in non-vol (2623)
             Added saRgIpMgmtPassthroughTable (2954)
             Added saRgIpMgmtLanExtraSubnetTable (2980)
             Added saRgFirewallMacFilterTable (3254)
             Changes saRgDot11PrivacyWpsPushButtonTime default to 1 (3278)"

    REVISION     "200806060000Z"
    DESCRIPTION
            "Added saRgDeviceTimeSetup (2629)
             Added saRgDot11PrivacyWpsPushButtonTime (2632)"

    REVISION     "200806020000Z"
    DESCRIPTION
            "Added firewall tree (2607)
             Added saRgIpMgmtWanMtu (2608)
             Added saRgIpMgmtWanTtl (2608)"

    REVISION     "200805270000Z"
    DESCRIPTION
            "Added saRgIpMgmtWanAddr (2595)"

    REVISION     "200804300000Z"
    DESCRIPTION
            "Initial release"

        ::= { saModules 2 }

-- RG Device

saRgDevice   OBJECT IDENTIFIER ::=  { saRg 1 }

saRgDeviceBase   OBJECT IDENTIFIER ::=  { saRgDevice 1 }

saRgDeviceMode OBJECT-TYPE
    SYNTAX INTEGER { 
    	disable(0),
        multiSsid(1),
        cableHome11(2),
                ipv4(3),
                ipv6(4),
                dualstack(5) }
    MAX-ACCESS    read-write
    STATUS        current
    DESCRIPTION
        "Defines the mode of operation for the device.
        This parameter is stored in non-vol and is multiSsid(1) by default.
        Setting this object via SNMP will cause
        the unit to reboot.
                This MIB will be superseded in the config file by TLV202.
                This MIB will read the proper value if set from TLV202.
                This MIB will be superseded by saRgIpMgmtLanMode inbridge(1) or mixed(4).
                disable(0):  Value will reflect when TLV202 is set to 0. Not all platforms have this value implemented.
                multiSsid(1): Default Value. Value supports IPv4RG with multiple SSID
                        configuration and bridge mode via saRgIpMgmtLanMode MIB.
                        Bridge mode is the same as eRouter disabled mode.
                        IPV4RG is the non eRouter behavior that existed before
                        in our router products.
                cableHome11(2): <deprecated>. Mode is not supported for eRouter devices.
                Ipv4(3): eRouter IPv4 only mode
                Ipv6(4): eRouter IPv6 only mode
                Dualstack(5): eRouter IPv4 and IPv6 dualstack
                Note: cableHome11(2) is deprecated."
    DEFVAL { 1 }
    ::= { saRgDeviceBase 1 }

saRgDeviceResetDefaultEnable OBJECT-TYPE
    SYNTAX TruthValue
    MAX-ACCESS read-write
    STATUS current
    DESCRIPTION	
        "This object controls the reset to factory default functionality
         of the gateway. This prevents the local user from using the reset
         switch to gain access to the setup pages using the default user
         name and password. The objective is to prevent theft of service
         from a user who reconfigures the device to add users or change
         wireless settings.
         Enable (object set to true):
          1. Momentary press of the Reset Switch (<5 seconds)
             DOCSIS restart of the modem (reboot, no reset to factory
             default values).
          2. Pressing the reset switch for >5 seconds
             Reboots and resets of all values (modem and router) to
             factory default.
         Disable (object set to false):
          1. Momentary press of the Reset Switch (<5 seconds)
             DOCSIS restart of the modem (reboot, no reset to factory
             default values).
          2. Pressing the reset switch for >5 seconds
             Modem reboots and resets only the cable modem settings to
             factory default values. The router settings should remain and
             should not NOT reset to factory default."
    DEFVAL { true }
    ::= { saRgDeviceBase 2 } 

saRgDeviceRemoteWebAccessEnable OBJECT-TYPE 
    SYNTAX      TruthValue 
    MAX-ACCESS  read-write 
    STATUS      current 
    DESCRIPTION  
            "Controls web page access to the WAN IP address on the gateway.
             If DMS is available in the hardware, and saRgDmsBaseWebRedirect
             is set to true, enabling this feature means to enable port
             forwarding for web access to the DMS (to port 80). Note: the
             entry for this does not appear in port forwarding table or on
             the web pages. Example of the rule: WAN_IP:8080->DMS_IP:80.
             This value is stored in non-vol and is false after factory reset.
             This value can be controlled via a setup web page.
             
             NOTE: This MIB is applicable only for legacy style web pages"
    ::= { saRgDeviceBase 3 } 

saRgDeviceRemoteWebAccessPort OBJECT-TYPE 
    SYNTAX      InetPortNumber 
    MAX-ACCESS  read-write 
    STATUS      current 
    DESCRIPTION  
            "Defines what port to use for the WAN IP address of the gateway
             to be able to access RG web pages.
             This value is to be stored in non-vol and will persist across reboots. 
             Only a factory reset would clear it"
    DEFVAL { 8080 }
    ::= { saRgDeviceBase 4 } 


saRgDeviceLanLanIsolation OBJECT-TYPE
    SYNTAX INTEGER {
        disable(0),
        enable(1)
        }
    MAX-ACCESS    read-write
    STATUS        current
    DESCRIPTION
        "This MIB is only available in D3.0 products.
	  This MIB does not take effect if the modem is in VLAN mode i.e if saRgIpMgmtLanMode.32=vlan(5).
        Lan-Lan Isolation allows you block IP access between CPEs connected to the Ethernet ports.
        Use this mib in conjunction with saRgDeviceLanWlanIsolation and saRgDot11BssApIsolation.x for
	  complete isolation between CPEs connected to the RG.
        This MIB is written to non-vol and set to disable(0) after a factory reset.
        disable(0)- No Isolation
        enable(1)- Enable Isolation feature"
    DEFVAL { 0 }
    ::= { saRgDeviceBase 6 }

saRgDeviceLanWlanIsolation OBJECT-TYPE
    SYNTAX INTEGER {
        disable(0),
        enable(1)
        }
    MAX-ACCESS    read-write
    STATUS        current
    DESCRIPTION
        "This MIB is only available in D3.0 products.
        This MIB does not take effect if the modem is in VLAN mode i.e if saRgIpMgmtLanMode.32=vlan(5).
        Lan-Wlan Isolation allows you block IP access between CPEs connected to the Ethernet port and 
        Wireless SSIDs.
        Use this mib in conjunction with saRgDeviceLanLanIsolation and saRgDot11BssApIsolation.x for
	  complete isolation between CPEs connected to the RG.        
        This MIB is written to non-vol and set to disable(0) after a factory reset.
        disable(0)- No Isolation
        enable(1)- Enable Isolation feature"
    DEFVAL { 0 }
    ::= { saRgDeviceBase 7 }
	
saRgDeviceIpv6Trans OBJECT-TYPE
    SYNTAX INTEGER {
        disable(0),
        dslite(1)
        }
    MAX-ACCESS    read-only
    STATUS        current
    DESCRIPTION
        "This MIB will control which IPv6 transition technology is enabled on the device.
        After setting this MIB to disable in the config file, IPv4 traffic will pass normally
		through the device. When switched to dslite, the DSLite feature will be enabled.
		If eRouter is in IPv6-only mode, DS Lite will tunnel IPv4 traffic over IPv6 to the AFTR
		address specified either manually or in the DHCPv6 option-64. See saRgDslite MIB tree
		for more details.
        If this setting is changed by the config file, the CM will reboot.		
        This MIB is written to non-vol and set to disable(0) after a factory reset.
        disable(0) - No technology is enabled
        enable(1) - DS lite feature is enabled"
    DEFVAL { 0 }
    ::= { saRgDeviceBase 8 }
	
saRgDeviceFactoryReset	OBJECT-TYPE
    SYNTAX INTEGER {
		false(0),
        routerAndWifi(1),
        routerOnly(2),
        wifi(3)
        }
	MAX-ACCESS	read-write
	STATUS		current
	DESCRIPTION
        "Set routerAndWifi(1) to restore default settings of both the router and wifi.
		Set routerOnly(2) to restore default settings of the router.
		Set wifi(3) to restore default settings of the wifi.
		Return false(0) when read."
	DEFVAL { 0 }
	::= { saRgDeviceBase 1002 }

saRgDeviceReset	OBJECT-TYPE
    SYNTAX INTEGER {
		false(0),
        routerAndWifi(1),
        routerOnly(2),
        wifi(3)
        }
    MAX-ACCESS  read-write
    STATUS      current
    DESCRIPTION
		"Set routerAndWifi(1) to reboot the router and WiFi.
		Set routerOnly(2) to reboot the router.
		Set wifi(3) to reboot the WiFi.
		Return false(0) when read."
	DEFVAL { 0 }
	::= { saRgDeviceBase 1003 }


SaRgUserChangedFlag ::= TEXTUAL-CONVENTION  
    STATUS       current  
    DESCRIPTION    
        "WebWizard Setup user changed flag sections.
        NOTE: Only Bits from 0-21 are supported for legacy web pages"
    SYNTAX BITS { 
        lanParameters(0),
        wanMTU(1),
        wirelessBasic(2),
        wirelessAdvanced(3),
        wirelessSecurity(4),
        wirelessAccessControl(5),
        fixedCPE(6),
        ipMacPortFiltering(7),
        dmzHost(8),
        blockProxy(9),
        blockCookies(10),
        blockJava(11),
        blockActiveX(12),
        blockPopup(13),
        blockFragments(14),
        detectPortScan(15),
        detectFlood(16),
        firewallEvent(17),
        firewallProtection(18),
	    ipsecPassthru(19),
	    pptpPassthru(20),
	    multicastPassthru(21),
        blockAnonymousIpWan(22),
        wanSetup(23),
        remoteMgmt(24),
        l2TP(25)
        }


saRgDeviceConfiguration   OBJECT IDENTIFIER ::=  { saRgDevice 4 }

saRgDeviceConfigFilename OBJECT-TYPE
    SYNTAX SnmpAdminString
    MAX-ACCESS    read-write
    STATUS        current
    DESCRIPTION
        "Configuration filename from DHCP ACK."
    ::= { saRgDeviceConfiguration 1 }

saRgDeviceConfigStatus OBJECT-TYPE
    SYNTAX INTEGER {
        notSpecified(1),
        inProgress(2),
        success(3),
        errorServer(4),
        errorFileNotFound(5),
        errorBadFile(6),
        download(7)
        }
    MAX-ACCESS read-write
    STATUS current
    DESCRIPTION
        "Status of configuration file download.
         - notSpecified(1): DHCP ACK did not contain necessary information
         - inProgress(2): Configuration file is being downloaded
         - success(3): configuration file download completed successfully
         - errorServer(4): TFTP server did not respond
         - errorFileNotFound(5): no file on the server
         - errorBadFile(6): the file is not good, cannot be processed
         - download(7): commands the unit to download configuration file."
    ::= { saRgDeviceConfiguration 2 }

saRgDeviceUserChangedFlag OBJECT-TYPE 
    SYNTAX SaRgUserChangedFlag
    MAX-ACCESS read-write     
    STATUS current 
    DESCRIPTION 
       "Specifies which user changed flags are set. The value of (1) means
        that user changed flag value is set; the value of (0) means that
        the user changed flag is not set.
        The user changed flags are stored in non-vol.
        Default value after factory reset is 0x00000000
        NOTE: Legacy style web pages only support bits from 0-21
        "
    ::= { saRgDeviceConfiguration 3 }

saRgDeviceConfigSnmpEnable OBJECT-TYPE
    SYNTAX BITS {
        rgWan(0),
        rgDualIp(1),
		rgLanIp(2)
    }
    MAX-ACCESS    read-write
    STATUS        current
    DESCRIPTION
        "Controls SNMP manager status on interfaces. If bit set to 0, the SNMP
         access is disabled. If bit set to 1, the SNMP access is enabled.
		 This MIB only applies to IPv4RG mode and is not relevant in 
		 eRouter modes. "
    DEFVAL { '00'h }
    ::= { saRgDeviceConfiguration 4 }

saRgDeviceConfigIgnore  OBJECT-TYPE
    SYNTAX INTEGER {
        require(0),
        notRequire(1),
        notDownload(2)
        }
    MAX-ACCESS  read-only
    STATUS      current
    DESCRIPTION
        "This object controls if RG configuration file is to be downloaded.
         require(0): per specification, if DHCP contains parameters for the
                     file dowload, the RG MUST try to download it.
         notRequire(1): when config file download fails after exponential backoff,
                        RG will not retry DHCP and continue to be operational.
         notDownload(2): RG will not download config file.
         This MIB can be only in CM configuration file."
    DEFVAL { 0 }
    ::= { saRgDeviceConfiguration 5 }

saRgDeviceIapdContent   OBJECT IDENTIFIER ::=  { saRgDevice 8 }

saRgDeviceIapdIAID OBJECT-TYPE
        SYNTAX Unsigned32
        MAX-ACCESS read-only
        STATUS current
        DESCRIPTION
                "Returns the IAID value embedded in the IA_PD for the
eRouter's DHCPv6 lease."
        ::= { saRgDeviceIapdContent 1 }

saRgDeviceIapdT1 OBJECT-TYPE
        SYNTAX Integer32
        MAX-ACCESS read-only
        STATUS current
        DESCRIPTION
                "Returns the T1 value embedded in the IA_PD for the eRouter's
DHCPv6 lease."
        ::= { saRgDeviceIapdContent 2 }

saRgDeviceIapdT2 OBJECT-TYPE
        SYNTAX Integer32
        MAX-ACCESS read-only
        STATUS current
        DESCRIPTION
                "Returns the T2 value embedded in the IA_PD for the eRouter's
DHCPv6 lease."
        ::= { saRgDeviceIapdContent 3 }

saRgDeviceIapdTable OBJECT-TYPE
        SYNTAX SEQUENCE OF SaRgDeviceIapdEntry
        MAX-ACCESS not-accessible
        STATUS current
        DESCRIPTION
                "Table of IA Prefix entries associated with IA_PD for the
eRouter's DHCPv6 lease."
        ::= { saRgDeviceIapdContent 4 }

saRgDeviceIapdEntry OBJECT-TYPE
    SYNTAX      SaRgDeviceIapdEntry
    MAX-ACCESS  not-accessible
    STATUS      current
    DESCRIPTION
            "Table of IA Address entries associated with IA_PD for the
eRouter's DHCPv6 lease."
    INDEX { saRgDeviceIapdIndex }
    ::= { saRgDeviceIapdTable 1 }

SaRgDeviceIapdEntry ::= SEQUENCE {
    saRgDeviceIapdIndex              INTEGER,
    saRgDeviceIapdPreferredLifetime  Integer32,
    saRgDeviceIapdValidLifetime      Integer32,
    saRgDeviceIapdPrefixLength       INTEGER,
    saRgDeviceIapdPrefixValue        InetAddress
    }

saRgDeviceIapdIndex OBJECT-TYPE
    SYNTAX      INTEGER (1..4)
    MAX-ACCESS  not-accessible
    STATUS      current
    DESCRIPTION
            "The index"
    ::= { saRgDeviceIapdEntry 1 }

saRgDeviceIapdPreferredLifetime OBJECT-TYPE
    SYNTAX      Integer32
    MAX-ACCESS  read-only
    STATUS      current
    DESCRIPTION
            "Preferred Lifetime setting for an IPv6 address assigned to the
eRouter."
    ::= { saRgDeviceIapdEntry 2 }

saRgDeviceIapdValidLifetime OBJECT-TYPE
    SYNTAX      Integer32
    MAX-ACCESS  read-only
    STATUS      current
    DESCRIPTION
            "Valid Lifetime setting for an IPv6 address assigned to the
eRouter."
    ::= { saRgDeviceIapdEntry 3 }

saRgDeviceIapdPrefixLength OBJECT-TYPE
        SYNTAX          INTEGER
        MAX-ACCESS      read-only
        STATUS          current
        DESCRIPTION
                "Length (in bits) for this prefix."
        ::= { saRgDeviceIapdEntry 4 }

saRgDeviceIapdPrefixValue OBJECT-TYPE
        SYNTAX          InetAddress
        MAX-ACCESS      read-only
        STATUS          current
        DESCRIPTION
                "Prefix address specified in the IA_PD."
        ::= { saRgDeviceIapdEntry 5 }

-- ******************
-- ***** 802.11 *****
-- ******************

saRgDot11 OBJECT IDENTIFIER ::=  { saRg 2 }


-- *************************
-- GENERAL AND CHANNEL SETUP
-- *************************

-- =====================
-- PER BSS CONFIGURATION
-- =====================
-- The interface numbers are:
-- 32: SSID1 + LAN
-- 33: SSID2
-- 34: SSID3
-- 35: SSID4
-- 36: SSID5
-- 37: SSID6
-- 38: SSID7
-- 39: SSID8


saRgDot11Bss OBJECT IDENTIFIER ::= { saRgDot11 2 }


saRgDot11BssTable  OBJECT-TYPE
    SYNTAX      SEQUENCE OF SaRgDot11BssEntry
    MAX-ACCESS  not-accessible
    STATUS      current
    DESCRIPTION
        "BSS table"
    ::= { saRgDot11Bss 1 }
    
saRgDot11BssEntry OBJECT-TYPE
    SYNTAX  	SaRgDot11BssEntry    
    MAX-ACCESS  not-accessible
    STATUS      current
    DESCRIPTION
        "A row in the table which represents parameters for SSID."
    INDEX   { ifIndex }
    ::= { saRgDot11BssTable 1 }
    
SaRgDot11BssEntry ::= 
    SEQUENCE {
        saRgDot11BssId            PhysAddress,
        saRgDot11BssEnable        INTEGER,
        saRgDot11BssSsid          OCTET STRING,
        saRgDot11BssSecurityMode  INTEGER,
        saRgDot11BssClosedNetwork TruthValue,
        saRgDot11BssAccessMode    INTEGER,
        saRgDot11BssMaxNumSta     INTEGER
        }

saRgDot11BssId OBJECT-TYPE
    SYNTAX      PhysAddress
    MAX-ACCESS  read-only
    STATUS      current
    DESCRIPTION
        "Returns the BSSID"
    ::= { saRgDot11BssEntry 1 }

saRgDot11BssEnable OBJECT-TYPE
    SYNTAX INTEGER {
        enable(1),
        disable(2),
        enableOnline(3)
        }
    MAX-ACCESS  read-write
    STATUS      current
    DESCRIPTION
        "Controls the BSS state. 
         When set to enableOnline(3), the SSID is enabled only
         when the cable modem is online. When the modem changes
         state to offline, the AP will send dissasociation messages
         to the STAs connected to the SSID and then disable.
         The value of primary BSS is stored in non-vol and is enabled(1)
         after factory reset.         
         The other BSSs are disabled by default. If other
         BSS's SSID name is not defined, the BSS will not
         be enabled."
    ::= { saRgDot11BssEntry 2 }

saRgDot11BssSsid OBJECT-TYPE
    SYNTAX      OCTET STRING (SIZE(0..32))
    MAX-ACCESS  read-write
    STATUS      current
    DESCRIPTION
        "Controls and reflects the service set identifier.
         The value of primary BSS is stored in non-vol and is
         empty after factory reset.
         If other BSS's SSID name is not defined, the BSS
         will not be enabled."
    ::= { saRgDot11BssEntry 3 }

saRgDot11BssSecurityMode OBJECT-TYPE
    SYNTAX INTEGER {
        disabled(0),
        wep(1),
        wpaPsk(2),
        wpa2Psk(3),
        wpaEnterprise(4),
        wpa2Enterprise(5),
        --radiusWep(6)
        wpaWpa2Psk(7),
        wpaWpa2Enterprise(8)
        }
    MAX-ACCESS  read-write
    STATUS      current
    DESCRIPTION
        "Secrity for BSS.
         Beacause WPA2 is backwords compatible with WPA, setting this
         object to wpaWpa2Psk(7) is allowed and has the same effect as
         setting to wpa2Psk(3). The same is true for wpaWpa2Enterprise(8)
         and wpa2Enterprise(5).
         The value for primary BSS is stored in non-vol and is wpaWpa2Psk(7)
         after factory reset.
         For each other BSS security has to be included in configuration
         file or the BSS will be disabled."
    ::= { saRgDot11BssEntry 4 }

saRgDot11BssClosedNetwork OBJECT-TYPE
    SYNTAX      TruthValue
    MAX-ACCESS  read-write
    STATUS      current
    DESCRIPTION
        "Controls whether the device will operate in closed network mode.  If
         set to true(1), then the network mode is closed and the SSID will not
         be broadcast in beacon packets.  If set to false(2), then the network
         mode is open and the SSID will be broadcast in beacon packets.
         The value for primary BSS is stored in non-vol.
         The default value for other BSSs is false."
    ::= { saRgDot11BssEntry 5 }

saRgDot11BssAccessMode OBJECT-TYPE
    SYNTAX      INTEGER {
                allowAny(0),
                allowList(1),
                denyList(2)
    }
    MAX-ACCESS  read-write
    STATUS      current
    DESCRIPTION
        "Controls what stations will be given access to the device.  If set to
         allowAny(0), then any station will be allowed to connect.  If set
         to allowList(1), then only stations whose MAC address appears in
         the saRgDot11AccessMacTable will be allowed to connect.
         The value for primary BSS is stored in non-vol.
         The default value for other BSSs is 0."
    ::= { saRgDot11BssEntry 6 }

saRgDot11BssMaxNumSta OBJECT-TYPE
    SYNTAX INTEGER (1..128)
    MAX-ACCESS read-write
    STATUS current
    DESCRIPTION
        "This object defines the maximum number of STAs that can connect to
         this SSID. Note that the maximum number of STA accross all SSIDs in
         the AP is 128.
         Default value is 128 for all SSIDs.
         The value for primary BSS is stored in non-vol."
    ::= { saRgDot11BssEntry 11 }


-- ******************
-- PRIVACY PARAMETERS
-- ******************

-- saRgDot11MgmtPrivacy contains objects from the 'Privacy' web page

saRgDot11Privacy OBJECT IDENTIFIER ::= { saRgDot11 3 }


-- WPA

saRgDot11WpaTable  OBJECT-TYPE
    SYNTAX      SEQUENCE OF SaRgDot11WpaEntry
    MAX-ACCESS  not-accessible
    STATUS      current
    DESCRIPTION
        "WPA table"
    ::= { saRgDot11Privacy 1 }
    
saRgDot11WpaEntry OBJECT-TYPE
    SYNTAX      SaRgDot11WpaEntry
    MAX-ACCESS  not-accessible
    STATUS      current
    DESCRIPTION
        "A row in the table which represents WPA parameters for BSS."
    INDEX   { ifIndex }
    ::= { saRgDot11WpaTable 1 }
    
SaRgDot11WpaEntry ::= 
    SEQUENCE    {
        saRgDot11WpaAlgorithm          INTEGER,
        saRgDot11WpaPreSharedKey       OCTET STRING,
        saRgDot11WpaGroupRekeyInterval INTEGER
    }

saRgDot11WpaAlgorithm OBJECT-TYPE
    SYNTAX INTEGER {
        tkip(0),
        aes(1),
        tkipPlusAes(2)
        }
    MAX-ACCESS  read-write
    STATUS      current
    DESCRIPTION
        "The value of tkip(0) is not allowed when security is WPA2.
         The value for primary BSS is stored in non-vol and tkipPlusAes(2)
         after factory reset.
         The default value for other BSSs is tkip."
    ::= { saRgDot11WpaEntry 1 }

saRgDot11WpaPreSharedKey OBJECT-TYPE
    SYNTAX      OCTET STRING (SIZE(8..64))
    MAX-ACCESS  read-write
    STATUS      current
    DESCRIPTION
        "Sets the WPA Pre-Shared Key (PSK).  This value MUST be either a 
         64-digit hexadecimal number, OR a 8 to 63 character ASCII string.
         The value for primary BSS is stored in non-vol and is the serial
         number of the device after factory reset.
         The default value for other BSSs is 8 0's.
         This object return an empty string when read."
    ::= { saRgDot11WpaEntry 2 }
    
saRgDot11WpaGroupRekeyInterval OBJECT-TYPE
    SYNTAX      INTEGER
    UNITS       "seconds"
    MAX-ACCESS  read-write
    STATUS      current
    DESCRIPTION
        "Sets the WPA Group Rekey Interval in seconds. Set to zero to disable 
         periodic rekeying.
         The value for primary BSS is stored in non-vol and is 3600 after
         factory reset.
         The default value for other BSSs is 3600."
    ::= { saRgDot11WpaEntry 3 }


-- RADIUS

saRgDot11RadiusTable  OBJECT-TYPE
    SYNTAX      SEQUENCE OF SaRgDot11RadiusEntry
    MAX-ACCESS  not-accessible
    STATUS      current
    DESCRIPTION
        "WPA table"
    ::= { saRgDot11Privacy 2 }
    
saRgDot11RadiusEntry OBJECT-TYPE
    SYNTAX      SaRgDot11RadiusEntry
    MAX-ACCESS  not-accessible
    STATUS      current
    DESCRIPTION
        "A row in the table which represents WPA parameters for BSS."
    INDEX   { ifIndex }
    ::= { saRgDot11RadiusTable 1 }
    
SaRgDot11RadiusEntry ::= 
    SEQUENCE    {
        saRgDot11RadiusAddressType    InetAddressType,
        saRgDot11RadiusAddress        InetAddress,
        saRgDot11RadiusPort           InetPortNumber,
        saRgDot11RadiusKey            DisplayString,
        saRgDot11RadiusReAuthInterval INTEGER
    }


saRgDot11RadiusAddressType OBJECT-TYPE
    SYNTAX      InetAddressType
    MAX-ACCESS  read-write
    STATUS      current
    DESCRIPTION
            "Type of RADIUS server IP address."
    DEFVAL { ipv4 }
    ::= { saRgDot11RadiusEntry 1 }


saRgDot11RadiusAddress OBJECT-TYPE
    SYNTAX      InetAddress
    MAX-ACCESS  read-write
    STATUS      current
    DESCRIPTION
        "Sets RADIUS server IP address.
         The value for primary BSS is stored in non-vol and is 0.0.0.0
         after factory reset.
         The default value for other BSSs is 0.0.0.0."
    ::= { saRgDot11RadiusEntry 2 }
    
saRgDot11RadiusPort OBJECT-TYPE
    SYNTAX      InetPortNumber
    MAX-ACCESS  read-write
    STATUS      current
    DESCRIPTION
        "Sets the UDP port used to communicate with the RADIUS server.
         The value for primary BSS is stored in non-vol and is 1645
         after factory reset.
         The default value for other BSSs is 1645."
    ::= { saRgDot11RadiusEntry 3 }
    
saRgDot11RadiusKey OBJECT-TYPE
    SYNTAX      DisplayString
    MAX-ACCESS  read-write
    STATUS      current
    DESCRIPTION
        "Sets or displays the RADIUS key.
         The value for primary BSS is stored in non-vol and is null
         after factory reset.
         The default value for other BSSs is null.
         This object return an empty string when read."
    ::= { saRgDot11RadiusEntry 4 }

saRgDot11RadiusReAuthInterval OBJECT-TYPE
    SYNTAX      INTEGER
    UNITS       "seconds"
    MAX-ACCESS  read-write
    STATUS      current
    DESCRIPTION
        "Sets the RADIUS Rekey Interval in seconds.
         Set to zero to disable periodic rekeying.
         The value for primary BSS is stored in non-vol and is 3600
         after factory reset.
         The default value for other BSSs is 3600."
    ::= { saRgDot11RadiusEntry 5 }


-- WEP

saRgDot11WepTable  OBJECT-TYPE
    SYNTAX      SEQUENCE OF SaRgDot11WepEntry
    MAX-ACCESS  not-accessible
    STATUS      current
    DESCRIPTION
        "WEP table"
    ::= { saRgDot11Privacy 3 }
    
saRgDot11WepEntry OBJECT-TYPE
    SYNTAX      SaRgDot11WepEntry
    MAX-ACCESS  not-accessible
    STATUS      current
    DESCRIPTION
        "A row in the table which represents WPA parameters for BSS."
    INDEX   { ifIndex }
    ::= { saRgDot11WepTable 1 }
    
SaRgDot11WepEntry ::= 
    SEQUENCE {
        saRgDot11WepDefaultKey      INTEGER,
        saRgDot11WepEncryptionMode  INTEGER,
        saRgDot11WepPassPhrase      OCTET STRING
    }

saRgDot11WepDefaultKey OBJECT-TYPE
    SYNTAX      INTEGER (1..4)
    MAX-ACCESS  read-write
    STATUS      current
    DESCRIPTION
        "Controls and reflects the default key which will be used when 64 or
         128 bit encryption is enabled.  Indicates the entry from the 
         saRgDot1164BitKeyTable if saRgDot11EncryptionMode is set to wep64(1), or
         the entry from the saRgDot11128BitKeyTable if saRgDot11EncryptionMode is set 
         to wep128(2).
         The value for primary BSS is stored in non-vol and is 1 after factory reset.
         The default value for other BSSs is 1."
    ::= { saRgDot11WepEntry 1 }

saRgDot11WepEncryptionMode OBJECT-TYPE
    SYNTAX INTEGER {
        wep64(0),
        wep128(1)
        }
    MAX-ACCESS  read-write
    STATUS      current
    DESCRIPTION
         "The value for primary BSS is stored in non-vol and is wep128(1)
          after factory reset.
          The default value for other BSSs is wep128."
    ::= { saRgDot11WepEntry 2 }

saRgDot11WepPassPhrase OBJECT-TYPE
    SYNTAX      DisplayString (SIZE(0..32))
    MAX-ACCESS  read-write
    STATUS      current
    DESCRIPTION
        "Controls and reflects the WEP pass phrase.
         The value for primary BSS is stored in non-vol and is null
         after factory reset.
         The default value for other BSSs is null.
         This object return an empty string when read."
    ::= { saRgDot11WepEntry 3 }



-- WEP 64-bit keys:

saRgDot11Wep64BitKeyTable  OBJECT-TYPE
    SYNTAX      SEQUENCE OF SaRgDot11Wep64BitKeyEntry
    MAX-ACCESS  not-accessible
    STATUS      current
    DESCRIPTION
        "A table of 40 bit key values used when saRgDot11WepEncryptionMode
         is set to wep64(0)."
    ::= { saRgDot11Privacy 4 }
    
saRgDot11Wep64BitKeyEntry OBJECT-TYPE
    SYNTAX      SaRgDot11Wep64BitKeyEntry
    MAX-ACCESS  not-accessible
    STATUS      current
    DESCRIPTION
        "A row in the table which represents a single 64 bit key."
    INDEX   { ifIndex, saRgDot11Wep64BitKeyIndex }
    ::= { saRgDot11Wep64BitKeyTable 1 }
    
SaRgDot11Wep64BitKeyEntry ::= 
    SEQUENCE    {
                saRgDot11Wep64BitKeyIndex       Integer32,
                saRgDot11Wep64BitKeyValue       OCTET STRING
    }
    
saRgDot11Wep64BitKeyIndex OBJECT-TYPE
    SYNTAX      Integer32 (1..4)
    MAX-ACCESS  not-accessible
    STATUS      current
    DESCRIPTION
        "Identifies the instance of this table row."
    ::= { saRgDot11Wep64BitKeyEntry 1 }
    
saRgDot11Wep64BitKeyValue OBJECT-TYPE
    SYNTAX      OCTET STRING (SIZE(5))
    MAX-ACCESS  read-write
    STATUS      current
    DESCRIPTION
        "A 40 bit key to be used when saRgDot11WepEncryptionMode is set to wep64(1).
         The value for primary BSS is stored in non-vol and is all 1's after factory
         reset.
         The default value for other BSSs is all 0's.
         This object return an empty string when read."
    ::= { saRgDot11Wep64BitKeyEntry 2 }

-- WEP 128-bit keys:

saRgDot11Wep128BitKeyTable  OBJECT-TYPE
    SYNTAX      SEQUENCE OF SaRgDot11Wep128BitKeyEntry
    MAX-ACCESS  not-accessible
    STATUS      current
    DESCRIPTION
        "A table of 104 bit key values used when saRgDot11WepEncryptionMode
         is set to wep128(1)."
    ::= { saRgDot11Privacy 5 }
    
saRgDot11Wep128BitKeyEntry OBJECT-TYPE
    SYNTAX      SaRgDot11Wep128BitKeyEntry
    MAX-ACCESS  not-accessible
    STATUS      current
    DESCRIPTION
        "A row in the table which represents a single 128 bit key."
    INDEX   { ifIndex, saRgDot11Wep128BitKeyIndex }
    ::= { saRgDot11Wep128BitKeyTable 1 }
    
SaRgDot11Wep128BitKeyEntry ::= 
    SEQUENCE    {
                saRgDot11Wep128BitKeyIndex       Integer32,
                saRgDot11Wep128BitKeyValue       OCTET STRING
    }
    
saRgDot11Wep128BitKeyIndex OBJECT-TYPE
    SYNTAX      Integer32 (1..4)
    MAX-ACCESS  not-accessible
    STATUS      current
    DESCRIPTION
        "Identifies the instance of this table row."
    ::= { saRgDot11Wep128BitKeyEntry 1 }
    
saRgDot11Wep128BitKeyValue OBJECT-TYPE
    SYNTAX      OCTET STRING (SIZE(13))
    MAX-ACCESS  read-write
    STATUS      current
    DESCRIPTION
        "A 104 bit key to be used when saRgDot11WepEncryptionMode is set to wep128(2).
         The value for primary BSS is stored in non-vol and is all 1's.
         The default value for other BSSs is all 0's.
         This object return an empty string when read."
    ::= { saRgDot11Wep128BitKeyEntry 2 }


saRgDot11PrivacyWps OBJECT IDENTIFIER ::= { saRgDot11Privacy 6 }

saRgDot11PrivacyWpsPushButtonTime OBJECT-TYPE
    SYNTAX      INTEGER (0..10)
    UNITS       "seconds"
    MAX-ACCESS  read-write
    STATUS      current
    DESCRIPTION
        "Specifies how long to press WPS button to start the WPS
         procedure. 0 means disable WPS.
         Stored in non-vol, 1 after factory reset."
    ::= { saRgDot11PrivacyWps 1 }



----------------------------------------------------------------------
---  saRgDot11ExtMgmt
---  Table to support Multiple Radios
---  Note: Indexes may be set to support specific hardware interfaces.  
---  Index 32 MUST match saRgDot11OperMode and vice versa
-----------------------------------------------------------------------

saRgDot11ExtMgmt OBJECT IDENTIFIER ::= { saRgDot11 6 }

saRgDot11ExtMgmtTable  OBJECT-TYPE
    SYNTAX      SEQUENCE OF SaRgDot11ExtMgmtEntry
    MAX-ACCESS  not-accessible
    STATUS      current
    DESCRIPTION
        "Multiple Radio Configuration Table"
    ::= { saRgDot11ExtMgmt 1 }
    
saRgDot11ExtMgmtEntry OBJECT-TYPE
    SYNTAX  	SaRgDot11ExtMgmtEntry    
    MAX-ACCESS  not-accessible
    STATUS      current
    DESCRIPTION
        "A row in the table which represents parameters for a Radio.
		 Index 32 should be set for Radio 0 -- 2.4 GHz if populated.
		 Index 112 should be set for Radio 1"

    INDEX   { ifIndex }
    ::= { saRgDot11ExtMgmtTable 1 }
    
SaRgDot11ExtMgmtEntry ::= 
    SEQUENCE {
		saRgDot11ExtOperMode                INTEGER,
		saRgDot11ExtCurrentChannel          Unsigned32,
		saRgDot11ExtBeaconInterval          Unsigned32,
		saRgDot11ExtDTIMInterval            Unsigned32,
		saRgDot11ExtFragThresh              Unsigned32,
		saRgDot11ExtRTSThresh               Unsigned32,
		saRgDot11ExtSRL                     Unsigned32,
		saRgDot11ExtLRL                     Unsigned32,
		saRgDot11ExtCtsProtectionEnable     TruthValue,
		saRgDot11ExtRate                    INTEGER,
		saRgDot11ExtOutputPower             INTEGER,
		saRgDot11ExtCountry                 INTEGER,
		saRgDot11ExtAntenna                 INTEGER,
		saRgDot11ExtMbssUserControl         INTEGER,
		saRgDot11ExtMbssUseNonvol           TruthValue,
		saRgDot11ExtMbssAdminControl        INTEGER,
		saRgDot11ExtActualChannel           INTEGER,
		saRgDot11ExtOnOffPushButtonTime     INTEGER,
		saRgDot11ExtWmm                     INTEGER,
		saRgDot11ExtWmmNoAck                INTEGER,
		saRgDot11ExtMulticastRate           INTEGER,
		saRgDot11ExtWirelessButtonOperation INTEGER
        }		 
				 
saRgDot11ExtOperMode OBJECT-TYPE
    SYNTAX      INTEGER {
                notAvailable(0),
                off(1),
                remote(2),
                local(3)
    }
    MAX-ACCESS  read-write
    STATUS      current
    DESCRIPTION
        "Used to control the 802.11 operational mode. If set to 
         notAvailable(0), then the wireless interface will be disabled, with
         the radio off, and no wireless settings web pages will be available to 
         the user.  
         If set to off(1) then the wireless interface will be disabled, but 
         there may be a web page present which indicates that wireless service 
         is available and that the MSO should be contacted to enable it. 
         If set to remote(2), then the wireless interface will be enabled, but 
         the configuration web pages are read-only so that the user may not 
         change the settings. 
         If set to local(3), then the wireless interface will be enabled, and 
         the web pages will be read-write so that the user has full control over 
         the settings.
         This parameter is stored in non-vol and set to local(3) after factory
         reset."
    ::= { saRgDot11ExtMgmtEntry 1 }

saRgDot11ExtCurrentChannel OBJECT-TYPE
    SYNTAX      Unsigned32 (0..216)
    MAX-ACCESS  read-write
    STATUS      current
    DESCRIPTION
        "Controls and reflects the current channel number.
         The value of 0 means auto channel selection.
         This parameter is stored in non-vol and is 0
         after factory reset.
         
         For 802.11b/g/n modes in 2.4 GHz, the available channels are 1-14.
         For 802.11a/n modes in 5 GHz, the available channels are 34-216.
         Channel selection is subjected to restrictions based on Wifi
         Country Code"
    ::= { saRgDot11ExtMgmtEntry 3 }

saRgDot11ExtBeaconInterval OBJECT-TYPE
    SYNTAX      Unsigned32  (1..65535)
    UNITS       "milliseconds"
    MAX-ACCESS  read-write
    STATUS      current
    DESCRIPTION
        "Controls and reflects the beacon interval for the device.
         This parameter is stored in non-vol."
    ::= { saRgDot11ExtMgmtEntry 4 }

saRgDot11ExtDTIMInterval OBJECT-TYPE
    SYNTAX      Unsigned32  (1..255)
    UNITS       "milliseconds"
    MAX-ACCESS  read-write
    STATUS      current
    DESCRIPTION
        "Controls and reflects the DTIM interval for the device.
         This parameter is stored in non-vol."
    ::= { saRgDot11ExtMgmtEntry 5 }

-- Renamed from saRgDot11FragmentationThreshold to avoid conflict w/ IEEE 802.11 MIB
saRgDot11ExtFragThresh OBJECT-TYPE
    SYNTAX      Unsigned32  (256..2346)
    UNITS       "bytes"
    MAX-ACCESS  read-write
    STATUS      current
    DESCRIPTION
        "Controls and reflects the fragmentation threshold for the device.
         This parameter is stored in non-vol."
    ::= { saRgDot11ExtMgmtEntry 6 }

-- Renamed from saRgDot11RTSThreshold to avoid conflict w/ IEEE 802.11 MIB
saRgDot11ExtRTSThresh OBJECT-TYPE
    SYNTAX      Unsigned32  (0..2347)
    MAX-ACCESS  read-write
    STATUS      current
    DESCRIPTION
        "Controls and reflects the RTS threshold for the device.
         This parameter is stored in non-vol."
    ::= { saRgDot11ExtMgmtEntry 7 }


-- Renamed from saRgDot11ShortRetryLimit to avoid conflict w/ IEEE 802.11 MIB
saRgDot11ExtSRL OBJECT-TYPE
    SYNTAX      Unsigned32  (1..255)
    MAX-ACCESS  read-write
    STATUS      current
    DESCRIPTION
        "Controls and reflects the short retry limit for the device.
         This parameter is stored in non-vol."
    ::= { saRgDot11ExtMgmtEntry 8 }
    
-- Renamed from saRgDot11LongRetryLimit to avoid conflict w/ IEEE 802.11 MIB
saRgDot11ExtLRL OBJECT-TYPE
    SYNTAX      Unsigned32  (1..255)
    MAX-ACCESS  read-write
    STATUS      current
    DESCRIPTION
        "Controls and reflects the long retry limit for the device.
         This parameter is stored in non-vol."
    ::= { saRgDot11ExtMgmtEntry 9 }
    
saRgDot11ExtCtsProtectionEnable OBJECT-TYPE
    SYNTAX      TruthValue
    MAX-ACCESS  read-write
    STATUS      current
    DESCRIPTION
        "Controls and reflects the state of CTS protection.
         If set to true(1), the AP will use RTS/CTS to improve 802.11 
         performance in mixed 802.11 networks. Set to false(2) to 
         maximize 802.11 throughput under most conditions.
         This parameter is stored in non-vol."
    ::= { saRgDot11ExtMgmtEntry 10 }

saRgDot11ExtRate OBJECT-TYPE
    SYNTAX      INTEGER {
                auto(0),
                mbits1(1),
                mbits2(2),
                mbits5-5(5),
                mbits6(6),
                mbits9(9),
                mbits11(11),
                mbits12(12),
                mbits18(18),
                mbits24(24),
                mbits36(36),
                mbits48(48),
                mbits54(54)
    }
    MAX-ACCESS  read-write
    STATUS      current
    DESCRIPTION
        "Forces the transmission rate for the AP to a particular speed.
         Note that the 802.11b rates, including mbits1(1), mbits2(2), 
         mbits5-5(5), and mbits11(11), are not available in 5GHz.
         This parameter is stored in non-vol."
    ::= { saRgDot11ExtMgmtEntry 11 }

saRgDot11ExtOutputPower OBJECT-TYPE
    SYNTAX      INTEGER {
                percent25(25),
                percent50(50),
                percent75(75),
                percent100(100)
    }
    MAX-ACCESS  read-write
    STATUS      current
    DESCRIPTION
        "Sets the output power relative to the hardware's maximum capability.
         This parameter is stored in non-vol."
    ::= { saRgDot11ExtMgmtEntry 12 }
    
saRgDot11ExtCountry OBJECT-TYPE
    SYNTAX      INTEGER {
                worldWide(0),
                thailand(1),
                israel(2),
                jordan(3),
                china(4),
                japan(5),
                usa(6),
                europe(7),
                allChannels(8)
    }
    MAX-ACCESS  read-write
    STATUS      current
    DESCRIPTION
        "Restricts the channel set based on country requirements.
         This parameter is stored in non-vol and is worldWide(0)
         (channels 1-11) after factory reset."
    ::= { saRgDot11ExtMgmtEntry 13 }

saRgDot11ExtAntenna OBJECT-TYPE
    SYNTAX  INTEGER {
        disableIntTx(0),
        enableIntTx(1)
        }
    MAX-ACCESS  read-write
    STATUS      current
    DESCRIPTION
        "This parameter is stored in non-vol and set to
         disableIntTx(0) after factory reset."
    ::= { saRgDot11ExtMgmtEntry 14 }

saRgDot11ExtMbssUserControl OBJECT-TYPE
    SYNTAX INTEGER (1..8|65536..16711680)
    MAX-ACCESS read-write
    STATUS current
    DESCRIPTION
        "Sets the number of user controlled Wifi networks via web pages.
         1: The user has control over the primary wireless network only.
            No guest network page is displayed.
         2: The user has control over the primary wireless network and
            one guest network. No drop down menu (or only 1 item in the
            menu) for additional guest network configuration.
         3: Same as above with 2 guest networks.
         4: Same as above with 3 guest networks.
         5: Same as above with 4 guest networks.
	     6: Same as above with 5 guest networks.
	     7: Same as above with 6 guest networks.
         8: Same as above with 7 guest networks.
         
         Bit Mask Control:
         Bit 16: -- User has control over Primary Wireless Network		 :  65536
         Bit 17: -- User has control over Guest Network 1 (interface 33) : 131072
         Bit 18: -- User has control over Guest Network 2 (interface 34) : 262144 
         Bit 19: -- User has control over Guest Network 3 (interface 35) : 524288
         Bit 20: -- User has control over Guest Network 4 (interface 36) :1048576
         Bit 21: -- User has control over Guest Network 5 (interface 37) :2097152
         Bit 22: -- User has control over Guest Network 6 (interface 38) :4194304
         Bit 23: -- User has control over Guest Network 7 (interface 39) :8388608
         
         This object value is stored in non-vol and set to 1 
         after factory reset."
    ::= { saRgDot11ExtMgmtEntry 15 }
    
saRgDot11ExtMbssUseNonvol OBJECT-TYPE
    SYNTAX TruthValue
    MAX-ACCESS read-write
    STATUS current
    DESCRIPTION
        "Allows to save additional BSS parameters to non-vol if set to true.
         Primary BSS parameters are ALWAYS stored in non-vol.
         This object value is stored in non-vol and set to false 
         after factory reset."
    ::= { saRgDot11ExtMgmtEntry 16 }

saRgDot11ExtMbssAdminControl OBJECT-TYPE
    SYNTAX INTEGER (1..8|65536..16711680)
    MAX-ACCESS read-write
    STATUS current
    DESCRIPTION
        "Sets the number of admin controlled Wifi networks via web pages.
         1: The admin has control over the primary wireless network only.
            No guest network page is displayed.
         2: The admin has control over the primary wireless network and
            one guest network. No drop down menu (or only 1 item in the
            menu) for additional guest network configuration.
         3: Same as above with 2 guest networks.
         4: Same as above with 3 guest networks.
         5: Same as above with 4 guest networks.
	     6: Same as above with 5 guest networks.
	     7: Same as above with 6 guest networks.
         8: Same as above with 7 guest networks. 
         
         Bit 16: -- Admin Has control over Primary Wireless Network		  :  65536
         Bit 17: -- Admin Has control over Guest Network 1 (interface 33) : 131072
         Bit 18: -- Admin Has control over Guest Network 2 (interface 34) : 262144 
         Bit 19: -- Admin Has control over Guest Network 3 (interface 35) : 524288
         Bit 20: -- Admin Has control over Guest Network 4 (interface 36) :1048576
         Bit 21: -- Admin Has control over Guest Network 5 (interface 37) :2097152
         Bit 22: -- Admin Has control over Guest Network 6 (interface 38) :4194304
         Bit 23: -- Admin Has control over Guest Network 7 (interface 39) :8388608
         
         This object value is stored in non-vol and set to 1 
         after factory reset."
         
    ::= { saRgDot11ExtMgmtEntry 17 }

saRgDot11ExtActualChannel OBJECT-TYPE
    SYNTAX      INTEGER
    MAX-ACCESS  read-only
    STATUS      current
    DESCRIPTION
        "Reports the current channel number that wireless is on.
         The value of 0 means wireless is disabled."
    ::= { saRgDot11ExtMgmtEntry 18 }

saRgDot11ExtOnOffPushButtonTime OBJECT-TYPE
    SYNTAX      INTEGER (0..11)
    UNITS       "seconds"
    MAX-ACCESS  read-write
    STATUS      current
    DESCRIPTION
        "Specifies how long to press WPS button to enable or disable
         the WiFi interface (primary SSID). When set to 11, the feature
         is disabled.  
         Note that if the device has multiple radios but a single WPS HW button, 
         only the first instance (saRgDot11ExtOnOffPushButtonTime.32) should be used.
         Stored in non-vol, 5, 10 after factory reset."
    ::= { saRgDot11ExtMgmtEntry 19 }

saRgDot11ExtWmm OBJECT-TYPE
    SYNTAX  INTEGER {
        disable(0),
        enable(1)
        }
    MAX-ACCESS  read-write
    STATUS      current
    DESCRIPTION
        "Mib to Enable/Disable Wifi-Multi Media (WMM) QOS fetures.
        This parameter is stored in non-vol and set to
        enable(1) after a factory reset."
    DEFVAL { 1 }
    ::= { saRgDot11ExtMgmtEntry 20 }

 saRgDot11ExtWmmNoAck OBJECT-TYPE
    SYNTAX  INTEGER {
        disable(0),
        enable(1)
        }
    MAX-ACCESS  read-write
    STATUS      current
    DESCRIPTION
        "Mib to control whether Wifi packets require acknowledgement.
        disable(0) Use acknowledgemnet for Wifi packets.
        enable(1)  Sets No acknowledgement which allows for higher throughput and lower latency when some
                   packetloss is acceptable (ex. VoIP).
        Note: If WMM is disabled then this setting has no effect, and you can Not disable Acks from being
        returned from the stations.
        This parameter is stored in non-vol and set to disable(0) after a factory reset."
    DEFVAL { 0 }        
    ::= { saRgDot11ExtMgmtEntry 21 }
    
 saRgDot11ExtMulticastRate OBJECT-TYPE
    SYNTAX      INTEGER {
				disable(0),
                mbits1(1),
                mbits2(2),
                mbits5-5(5),
                mbits6(6),
                mbits9(9),
                mbits11(11),
                mbits12(12),
                mbits18(18),
                mbits24(24),
                mbits36(36),
                mbits48(48),
                mbits54(54)
	}
    UNITS       "Mbps"
    MAX-ACCESS  read-write
    STATUS      current
    DESCRIPTION
        "Forces the dot11 multicast Phy transmission rate.
         Note that the 802.11b rates, including mbits1(1), mbits2(2), 
         mbits5-5(5), and mbits11(11), are not available in 5GHz.  
         This object is stored in non-vol and defaults to disable(0) after factory reset."
    DEFVAL { 0 }
    ::= { saRgDot11ExtMgmtEntry 22 }   

saRgDot11ExtWirelessButtonOperation OBJECT-TYPE
    SYNTAX  INTEGER {
        disable(0),
        enable(1)
    }
    MAX-ACCESS    read-write
    STATUS        current
    DESCRIPTION  
        "To enable or disable the button press of wireless ON/OFF button. 
         This feature will work only on products that have the wireless ON/OFF button. 
         This MIB will control if the Wireless ON/OFF button can be pressed or not. 
         If it's enabled then button press would take effect otherwise there will not be any effect on button press.
         Note that if the device has multiple radios but a single Wireless ON/OFF button, 
         only the first instance (saRgDot11ExtWirelessButtonOperation.32) should be used.
         By default value will be set to enable(1)."
    DEFVAL { 1 }                  
    ::= { saRgDot11ExtMgmtEntry 23 }   


---------------------------------------
-- Dot11nExt - Radio Settings Table 
---  Table to support Multiple 802.11n Radios
---  Note: Indexes may be set to support specific hardware interfaces.  
---  Index 32 MUST match saRgDot11n.
---------------------------------------

saRgDot11nExt OBJECT IDENTIFIER ::= { saRgDot11 7 }

saRgDot11nExtTable  OBJECT-TYPE
    SYNTAX      SEQUENCE OF SaRgDot11nExtEntry
    MAX-ACCESS  not-accessible
    STATUS      current
    DESCRIPTION
        "Multiple 802.11n Radio Configuration Table
		 Index 32 should be set for Radio 0 -- 2.4 GHz if populated.
		 Index 112 should be set for Radio 1"
    ::= { saRgDot11nExt 1 }
    
saRgDot11nExtEntry OBJECT-TYPE
    SYNTAX  	SaRgDot11nExtEntry
    MAX-ACCESS  not-accessible
    STATUS      current
    DESCRIPTION
        "A row in the table which represents parameters for an 802.11n Radio."
    INDEX   { ifIndex }
    ::= { saRgDot11nExtTable 1 }
    
SaRgDot11nExtEntry ::= 
    SEQUENCE {
		saRgdot11nExtMode               INTEGER,
		saRgdot11nExtPhyRate            INTEGER,
		saRgdot11nExtBand               INTEGER,
		saRgdot11nExtBandWidth          INTEGER,
		saRgdot11nExtSideBand           INTEGER,
		saRgdot11nExtObssCoex           INTEGER,
		saRgdot11nExtMulticastRate      INTEGER
        }

saRgdot11nExtMode OBJECT-TYPE
    SYNTAX INTEGER {
        auto(1),
        off(2),
        n-mode(3),
        b-mode(16),
        g-mode(32),
        a-mode(64),
        n-mode(128),
        ac-mode(256)
        }
    MAX-ACCESS  read-write
    STATUS      current
    DESCRIPTION
        "Determines the radio Operational Mode.

         auto(1): The device will accept both legacy, 11n and 11ac capable clients
                  DualBandConcurrent Puma6 11n based devices will set to g+n or a+n
                          Legacy single band devices will set to b+g+n or a+n depending on band.

         off(2): Will accept both but will not support the 11n mode.
         NOTE: This is being deprecated for Dual Band Concurrent, or Dual Band Capable devices

         n-only(3): Will accept only the 11n-capable clients.

         Individual bit settings for other rates may be combined for specific customer requirements:
         Supported Valid Modes:

         N-Supported Modes:
         1) b/g/n = 16+32+128 --> 176 (10110000b, 0xb0)
         2) g/n = 32+128 -------> 160 (10100000b, 0xa0)
         3) a/n = 64+128 -------> 192 (11000000b, 0xc0)
         4) n = 128 ------------> 128 (10000000b, 0x80)

         Legacy Modes:
         1) b only ------------->  16 (00010000b, 0x10)
         2) b/g = 16+32 -------->  48 (00110000b, 0x30)
         3) a only ------------->  64 (01000000b, 0x40)

         AC-Modes will track radio supported Modes + 256

        Note: This is for all ac /n cards, and will also affect other MIB selections
        (saRgdot11nExtBandWidth)

        This object is stored in non-vol and defaults to auto(1) after factory reset."
     ::= { saRgDot11nExtEntry 1 }

   
saRgdot11nExtPhyRate OBJECT-TYPE
    SYNTAX INTEGER {
        auto(0),
        legacy(1),
        mbits6-5or13-5(2),
        mbits13or27(3),
        mbits19-5or40-5(4),
        mbits26or54(5),
        mbits39or81(6),
        mbits52or108(7),
        mbits58-5or121-5(8),
        mbits65or135(9),
        reserved1(10),
        reserved2(11),
        reserved3(12),
        reserved4(13),
        mbits78or162(14),
        mbits104or216(15),
        mbits117or243(16),
        mbits130or270(17)
        }
    MAX-ACCESS  read-write
    STATUS      current
    DESCRIPTION
        "Forces the N Phy transmission rate for the AP to a particular speed.  Each pair of rates
         corresponds to a 20 MHz or 40 MHz channel configuration.
         This object is stored in non-vol and defaults to auto(0) after factory reset."
    DEFVAL { auto }
    ::= { saRgDot11nExtEntry 2 }
 

saRgdot11nExtBand OBJECT-TYPE
    SYNTAX INTEGER {
        band-2-4G(1),
        band-5G(2)
        }
    MAX-ACCESS  read-write
    STATUS      current
    DESCRIPTION
        "Determines which Band that we will be operating in. Either the 2.4G or the 5G Hz.
         Note: This is for N cards only.
         This object is stored in non-vol and defaults to band-2-4G(1) after factory reset."
    ::= { saRgDot11nExtEntry 3 }

saRgdot11nExtBandWidth OBJECT-TYPE
    SYNTAX INTEGER {
        width-20MHz(1),
        width-40MHz(2)
        }
    MAX-ACCESS  read-write
    STATUS      current
    DESCRIPTION
        "Determines which Band Width that we will be operating in. Either the 20MHz or the 40MHz.
         Note: This is for N cards only, and this also affect other MIB selections such as saRgdot11nSideBand.
         This object is stored in non-vol and defaults to ? after factory reset."
    ::= { saRgDot11nExtEntry 4 }

saRgdot11nExtSideBand OBJECT-TYPE
    SYNTAX INTEGER {
        upper(1),
        lower(2)
        }
    MAX-ACCESS  read-write
    STATUS      current
    DESCRIPTION
        "Determines which side Band the channel will operate in.
         Note: This is for N cards only, this mib is dependent of what saRgdot11nBandWidth is selected and only
         applies when 40MHz is selected.
         This object is stored in non-vol and defaults to lower(2) after factory reset."
    ::= { saRgDot11nExtEntry 5 }

saRgdot11nExtObssCoex OBJECT-TYPE
	SYNTAX INTEGER {
		disable(0),
		enable(1)
		}
	MAX-ACCESS read-write
	STATUS 	   current
	DESCRIPTION
		"Allows MSO to control OBSS (Overlapping BSS) Coexistance parameter for 802.11n 40MHz channel width.
		 By default it is enabled and is stored in non-vol
		 Factory reset would clear it and would be enable(1) after factory reset.
		 When disabled, the 802.11n Wifi would stay in 40 MHz channel-width inspite of interference from other 
		 wifi channels. While enabled, 802.11n would coexist with 802.11g channels using 20 MHz default channel-width 
		 "  
	::= { saRgDot11nExtEntry 6 }

saRgdot11nExtMulticastRate OBJECT-TYPE
    SYNTAX INTEGER {
        disable(0),
        legacy(1),
        mbits6-5or13-5(2),
        mbits13or27(3),
        mbits19-5or40-5(4),
        mbits26or54(5),
        mbits39or81(6),
        mbits52or108(7),
        mbits58-5or121-5(8),
        mbits65or135(9),
        reserved1(10),
        reserved2(11),
        reserved3(12),
        reserved4(13),
        mbits78or162(14),
        mbits104or216(15),
        mbits117or243(16),
        mbits130or270(17)
        }
    MAX-ACCESS  read-write
    STATUS      current
    DESCRIPTION
        "Forces the dot11n Multicast Phy transmission rate.  Legacy mode forces the rate to be set 
		 by dot11MulticastRate.
         This object is stored in non-vol and defaults to disable(0) after factory reset."
    DEFVAL { 0 }
    ::= { saRgDot11nExtEntry 7 }


-- saRgDot11ApplySettings: do 'on the fly' config with settings from above.
-- This scalar object was placed by itself at ieee802saRgDot11Mgmt 100 because
-- it applies all settings from all current and possibly future 802.11
-- groups.  Wanted to leave plenty of room to add new groups in the future.

saRgDot11ApplySettings OBJECT-TYPE
    SYNTAX      TruthValue
    MAX-ACCESS  read-write
    STATUS      current
    DESCRIPTION
        "If set to true(1), then all the settings (MIB values)
         from this MIB tree will be applied to run time configuration,
         modifying previous RG operation with the new settings.
         Before setting the value to true, MIBs modified in the MIB
         tree are stored in non-vol and will not modify RG operation
         until saRgDot11ApplySettings is set to true or CM resets.
         Note: this applies only to the MIB objects that are stored
         in non-vol.
         Always returns false(2) when read."
    ::= { saRgDot11 1001 }


-- ============= 
-- IP management
-- =============

saRgIpMgmt OBJECT IDENTIFIER ::=  { saRg 3 }


-- { saRgIpMgmt 1 } reserved for WAN IP definition (currently only DHCP)


-- LAN NETWORK DEFINITIONS

saRgIpMgmtLanTable OBJECT-TYPE
    SYNTAX SEQUENCE OF SaRgIpMgmtLanEntry
    MAX-ACCESS not-accessible
    STATUS current
    DESCRIPTION
            "Networks on the LAN side.
             Primary BSS stored in non-vol."
    ::= { saRgIpMgmt 2 }

saRgIpMgmtLanEntry OBJECT-TYPE
    SYNTAX      SaRgIpMgmtLanEntry
    MAX-ACCESS  not-accessible
    STATUS     current
    DESCRIPTION
            "List of networks on the LAN side."
    INDEX { ifIndex }
    ::= { saRgIpMgmtLanTable 1 }

SaRgIpMgmtLanEntry ::= SEQUENCE {
    saRgIpMgmtLanMode              INTEGER,
    saRgIpMgmtLanNetwork           IpAddress,
    saRgIpMgmtLanNetworksAllow     INTEGER, 
    saRgIpMgmtLanSubnetMask        IpAddress,
    saRgIpMgmtLanGateway           IpAddress,
    saRgIpMgmtLanDhcpServer        INTEGER,
    saRgIpMgmtLanNapt              INTEGER,
    saRgIpMgmtLanTypeOfService     INTEGER,
    saRgIpMgmtLanDhcp125Option     INTEGER,
    saRgIpMgmtLanHnap		       INTEGER,
	saRgIpMgmtLanUpnp			   INTEGER
    }

saRgIpMgmtLanMode OBJECT-TYPE
    SYNTAX INTEGER {
        bridge(1),
        router(2),
        l2tpv2-client(3),
        mixed(4),
        vlan(5)
        }
    MAX-ACCESS    read-write
    STATUS        current
    DESCRIPTION
       	"Defines the mode of operation for the device.
       	Setting this object via SNMP for the primary BSS will cause
       	the unit to reboot.
       	Setting this object via SNMP for the secondary BSSs will not
       	cause the unit to reboot.
       	The value for primary BSS is stored in non-vol and is router
       	after factory reset.
       	The default value for other BSSs is router.
		This MIB supersedes saRgDeviceMode for the .32 interface.
      	l2tpv2-client(3)is obsoleted and NOT supported.
		 
		bridge(1):	Sets individual interface to bridging mode
					(for IPv6 interfaces DHCPv6 is external)
		router(2): 	Sets individual interface to routing mode
					(for IPv6 interfaces DHCPv6 is internal)
		l2tpv2-client(3): <obsolete>
		mixed(4): 	For mixed mode. This setting is applicable only to 
					.32 interface. This value is used on conjunction with 
					saRgIpMgmtLanPortControlTable
					*Note: mixed(4) mode NOT Supported by DOCSIS 2.0 products.
		vlan (5): 	Enables the vlan control feature. 
					See saRgVlanTable MIBs for VLAN configuration information."
    DEFVAL { 2 }		 
    ::= { saRgIpMgmtLanEntry 1 }

saRgIpMgmtLanNetwork OBJECT-TYPE
    SYNTAX      IpAddress
    MAX-ACCESS  read-write
    STATUS      current
    DESCRIPTION
            "The LAN-Trans network number. 
            Default for primary BSS is 192.168.0.0
            Default for other BSSs is 192.168.ifIndex.0"
    ::= { saRgIpMgmtLanEntry 3 }


saRgIpMgmtLanNetworksAllow OBJECT-TYPE 
		SYNTAX	INTEGER { 
		default(0), 
		anyPrivateClass(1), 
		anyClass(2) 
        } 
    MAX-ACCESS  read-write 
    STATUS      current 
    DESCRIPTION 
		"Allows the user via the internal Web GUI (Lan Setup page
		to input an IPv4 public or private Local IP address other than a
		class C Private address (the default Network for the Primary BSS = 192.168.0.0/24, with
		the default Local Ip address = 192.168.0.1.)
		In all cases the mask must be 255.255.255.x since the RG is limited to supporting
		a maximum of 253 IP addresses.
		(See RFC1918 for a description of private IP addresses and specified ranges.)
		Available Mib settings:
		default(0):			Only the third and fourth octets are editable in
							the Web GUI for the Local IP address (Ex. 192.168.x.x/24).
		anyPrivateClass(1):	All 4 octets are editable in the Web GUI for Local IP address, but
							the network specified must be a Private class A, B or C network address.
							(Ex. A=10.x.x.x, B=172.16.x.x, C=192.168.x.x).
		anyClass(2):		All 4 octets are editable in the Web GUI for Local IP address, and
							the network specified could be any public or private class A, B, or C address.
		
		If the MSO specifically sets a Local IP address in saRgIpMgmtLanNetwork to a value other than
		the default value (for example: 192.168.0.1) then these fields will be uneditable by the user (grayed out)."
    	DEFVAL { 0 }
	::= { saRgIpMgmtLanEntry 4 } 

saRgIpMgmtLanSubnetMask OBJECT-TYPE
    SYNTAX      IpAddress
    MAX-ACCESS  read-write
    STATUS      current
    DESCRIPTION
            "The device MUST provide the value of this MIB
            object in the Option 1 (Subnet Mask) of
            DHCP OFFER and ACK messages sent to a LAN IP Device."
    DEFVAL { 'ffffff00'h }    -- 255.255.255.0
    ::= { saRgIpMgmtLanEntry 5 }

saRgIpMgmtLanGateway OBJECT-TYPE
    SYNTAX      IpAddress
    MAX-ACCESS  read-write
    STATUS      current
    DESCRIPTION
        	"The type of this address is specified by
            saRgIpMgmtLanNetwokRouterType. The PS MUST
            provide the value of this MIB object in the
            Option 3 (Router IP address) of the DHCP
            OFFER and ACK messages sent to the LAN IP Device.
            Default for primary BSS is 192.168.0.1
            Default for other BSSs is 192.168.ifIndex.1"
    ::= { saRgIpMgmtLanEntry 7 }

saRgIpMgmtLanDhcpServer OBJECT-TYPE
    SYNTAX INTEGER {
        disable(0),
        enable(1)
        }
    MAX-ACCESS    read-write
    STATUS        current
    DESCRIPTION
        "The value for primary BSS is stored in non-vol.
         The default value for other BSSs is:
         Enabled by default if interface is in router mode.
         Always disabled if interface is in bridge mode."
    ::= { saRgIpMgmtLanEntry 8 }

saRgIpMgmtLanNapt OBJECT-TYPE
    SYNTAX INTEGER {
        disable(0),
        enable(1)
        }
    MAX-ACCESS    read-write
    STATUS        current
    DESCRIPTION
        "The value for primary BSS is stored in non-vol.
         The default value for other BSSs is:
         Enabled by default if interface is in router mode.
         Always disabled if interface is in bridge mode."
    ::= { saRgIpMgmtLanEntry 9 }

saRgIpMgmtLanTypeOfService OBJECT-TYPE
      SYNTAX      INTEGER 
      MAX-ACCESS  read-write
      STATUS      current
      DESCRIPTION
          "Definition of the TOS bits for the Network.
           This object does not apply to primary BSS."
      DEFVAL { 0 }
      ::= { saRgIpMgmtLanEntry 10 }

saRgIpMgmtLanDhcp125Option OBJECT-TYPE
      SYNTAX      INTEGER {
        disable(0),
        addSsidName(1)
        }
      MAX-ACCESS  read-write
      STATUS      current
      DESCRIPTION
          "This option controls if the RG adds a Cisco specific
           suboption (number 17) to DHCP DISCOVER and REQUEST
           from the clients that are bridged on the BSS:
         0: do not add the option
         1: add suboption 17 to Cisco specific enterprise-id
            (9) within DHCP option 125. The content is the SSID name."
      DEFVAL { 0 }
      ::= { saRgIpMgmtLanEntry 11 }

saRgIpMgmtLanHnap OBJECT-TYPE
    SYNTAX INTEGER {
        disable(0),
        enable(1)
        }
    MAX-ACCESS    read-write
    STATUS        current
    DESCRIPTION
        "The value for primary BSS is stored in non-vol and
         is enable after factory default.
         The default value for other BSSs is disable."
    ::= { saRgIpMgmtLanEntry 12 }
	
saRgIpMgmtLanUpnp OBJECT-TYPE
    SYNTAX INTEGER {
        disable(0),
        enable(1)
        }
    MAX-ACCESS    read-write
    STATUS        current
    DESCRIPTION
        "Enable/Disable the UPnP agent.
	     The value is stored in non-vol and is disabled after factory default for the primary SSID.
                     The UPnP agents for additional networks are enabled by default.
         "
    DEFVAL { 0 }
    ::= { saRgIpMgmtLanEntry 13 }

-- LAN DHCP SERVERS DEFINITIONS

saRgIpMgmtLanDhcpServerTable OBJECT-TYPE
    SYNTAX SEQUENCE OF SaRgIpMgmtLanDhcpServerEntry
    MAX-ACCESS not-accessible
    STATUS current
    DESCRIPTION
            "Networks on the LAN side.
             Stored in non-vol. .10-.128 for primary BSS
             after factory reset."
    ::= { saRgIpMgmt 3 }

saRgIpMgmtLanDhcpServerEntry OBJECT-TYPE
    SYNTAX      SaRgIpMgmtLanDhcpServerEntry
    MAX-ACCESS  not-accessible
    STATUS     current
    DESCRIPTION
            "List of networks on the LAN side."
    INDEX { ifIndex }
    ::= { saRgIpMgmtLanDhcpServerTable 1 }

SaRgIpMgmtLanDhcpServerEntry ::= SEQUENCE {
    saRgIpMgmtLanDhcpServerPoolStart         IpAddress,
    saRgIpMgmtLanDhcpServerPoolEnd           IpAddress,
    saRgIpMgmtLanDhcpServerLeaseTime         Unsigned32,
    saRgIpMgmtLanDhcpServerTimeOffset        Integer32,
	saRgIpMgmtLanDhcpServerDomainName        SnmpAdminString,
    }


saRgIpMgmtLanDhcpServerPoolStart OBJECT-TYPE
    SYNTAX      IpAddress
    MAX-ACCESS  read-write
    STATUS      current
    DESCRIPTION
            "The start of range LAN Trans IP Addresses. The type of
            this address is specified by saRgIpMgmtLanDhcpServerPoolStartType.
            Default value depends on IP network and subnet."
    ::= { saRgIpMgmtLanDhcpServerEntry 2 }

saRgIpMgmtLanDhcpServerPoolEnd OBJECT-TYPE
    SYNTAX      IpAddress
    MAX-ACCESS  read-write
    STATUS      current
    DESCRIPTION
            "The end of range for LAN-Trans IP Addresses. The type of
            this address is specified by saRgIpMgmtLanDhcpServerPoolEndType.
            Default value depends on IP network and subnet."
    ::= { saRgIpMgmtLanDhcpServerEntry 4 }

saRgIpMgmtLanDhcpServerLeaseTime OBJECT-TYPE
    SYNTAX      Unsigned32
    UNITS       "seconds"
    MAX-ACCESS  read-write
    STATUS      current
    DESCRIPTION
            "The PS MUST provide the value of this MIB object in the
            Option 51 (IP Address lease time) of the DHCP OFFER and
            ACK messages sent to the LAN IP Device."
    DEFVAL { 3600 }
    ::= { saRgIpMgmtLanDhcpServerEntry 5 }

saRgIpMgmtLanDhcpServerTimeOffset OBJECT-TYPE
    SYNTAX      Integer32 (-86400..86400) -- 0 to 24 hours (in seconds)
    UNITS       "seconds"
    MAX-ACCESS  read-write
    STATUS      current
    DESCRIPTION
            "The PS MUST provide the value of this MIB object in
            the Option 2 (Time Offset from Coordinated
            Universal Time-UTC) in the DHCP OFFER and ACK
            messages sent to the LAN IP Device."
    DEFVAL { 0 }    -- UTC
    ::= { saRgIpMgmtLanDhcpServerEntry 6 }

saRgIpMgmtLanDhcpServerDomainName OBJECT-TYPE
    SYNTAX      SnmpAdminString 
    MAX-ACCESS  read-write 
    STATUS      current 
    DESCRIPTION 
            "This is the domain name given to this DHCP server's clients."
    ::= { saRgIpMgmtLanDhcpServerEntry 7 } 
    	
--===================================================================
--
-- saRgIpMgmtDnsServerTable (CDP WAN DNS Server Table)
--
-- The saRgIpMgmtDnsServerTable is a table of 3 cable network
-- and Internet DNS Servers.
--
--===================================================================

saRgIpMgmtDnsServerTable OBJECT-TYPE
    SYNTAX SEQUENCE OF SaRgIpMgmtDnsServerEntry
    MAX-ACCESS not-accessible
    STATUS current
    DESCRIPTION
            " This table contains the IP addresses of cable network and
            Internet DNS servers, in the order of preference in which
            the PS's CNP will query them, when it cannot resolve a DNS
            query using local information. Entries in this table are
            updated with the information contained in DHCP Option 6,
            received during both the WAN-Man and WAN-Data IP 
            acquisition processes.
            Stored in non-vol and 0.0.0.0 for all servers after
            factory reset."
    ::= { saRgIpMgmt 5 }

saRgIpMgmtDnsServerEntry OBJECT-TYPE
    SYNTAX      SaRgIpMgmtDnsServerEntry
    MAX-ACCESS  not-accessible
    STATUS     current
    DESCRIPTION
            "List of cable network and Internet DNS servers."
    INDEX { saRgIpMgmtDnsServerOrder }
    ::= { saRgIpMgmtDnsServerTable 1 }

SaRgIpMgmtDnsServerEntry ::= SEQUENCE {
    saRgIpMgmtDnsServerOrder  INTEGER,
    saRgIpMgmtDnsServerIp     IpAddress
    }

saRgIpMgmtDnsServerOrder OBJECT-TYPE
    SYNTAX      INTEGER {
                    primary(1),
                    secondary(2),
                    tertiary(3)
                }
    MAX-ACCESS  not-accessible
    STATUS      current
    DESCRIPTION
            "The order of preference for cable network and Internet DNS
            servers, as listed in DHCP option 6 (Domain Server)."
    ::= { saRgIpMgmtDnsServerEntry 1 }

saRgIpMgmtDnsServerIp OBJECT-TYPE
    SYNTAX      IpAddress
    MAX-ACCESS  read-write
    STATUS      current
    DESCRIPTION
            "This parameter indicates the IP address of a WAN DNS
            server."
    ::= { saRgIpMgmtDnsServerEntry 3 }



-- WAN interface

saRgIpMgmtWanAddr OBJECT IDENTIFIER ::= { saRgIpMgmt 9 }

saRgIpMgmtWanAddrBase OBJECT IDENTIFIER ::= { saRgIpMgmtWanAddr 1 }

saRgIpMgmtWanMode OBJECT-TYPE
    SYNTAX INTEGER {
        dhcp(1),
        static(2),
        dualIp(3)
        }
    MAX-ACCESS    read-write
    STATUS        current
    DESCRIPTION 
        "When dualIp(3) is selected, the second IP stack is used for
         user operations.
         Stored in non-vol, dhcp(1) after factory reset."
    ::= { saRgIpMgmtWanAddrBase 1 }

saRgIpMgmtWanMtu OBJECT-TYPE
    SYNTAX INTEGER (0..1500)
    UNITS       "bytes"
    MAX-ACCESS     read-write
    STATUS         current
    DESCRIPTION 
        "MTU size for the IP layer. Valid range is 256 to 1500.
         0 is the default which is 1500.
         Stored in non-vol, 0 after factory reset."
    ::= { saRgIpMgmtWanAddrBase 2 }

saRgIpMgmtWanTtl OBJECT-TYPE
    SYNTAX INTEGER (0..255)
    UNITS       "hops"
    MAX-ACCESS     read-write
    STATUS         current
    DESCRIPTION 
        "TTL for the IP packets forwarded to WAN.
         0 means no change to the original TTL (after
         being decreased by 1).
         Stored in non-vol, 0 after factory reset."
    ::= { saRgIpMgmtWanAddrBase 3 }


saRgIpMgmtWanAddrDynamic OBJECT IDENTIFIER ::= { saRgIpMgmtWanAddr 2 }

saRgIpMgmtWanAddrDynamicIp OBJECT-TYPE
    SYNTAX      IpAddress
    MAX-ACCESS  read-write
    STATUS      current
    DESCRIPTION 
        "The IP address for the DHCP-assigned router address. This is the outside-facing WAN address of the router. Stored in non-vol, 0.0.0.0 after factory reset."
    ::= { saRgIpMgmtWanAddrDynamic 1 }

saRgIpMgmtWanAddrDynamicLeaseTime OBJECT-TYPE
    SYNTAX      Unsigned32
    UNITS       "seconds"
    MAX-ACCESS  read-write
    STATUS      current
    DESCRIPTION
            "The lease time for the dynamically assigned WAN address."
    DEFVAL { 3600 }
    ::= { saRgIpMgmtWanAddrDynamic 2 }

saRgIpMgmtWanAddrStatic OBJECT IDENTIFIER ::= { saRgIpMgmtWanAddr 3 }

saRgIpMgmtWanStaticNetwork OBJECT-TYPE
    SYNTAX      IpAddress
    MAX-ACCESS  read-write
    STATUS      current
    DESCRIPTION 
        "Stored in non-vol, 0.0.0.0 after factory reset."
    ::= { saRgIpMgmtWanAddrStatic 1 }

saRgIpMgmtWanStaticSubnetMask OBJECT-TYPE
    SYNTAX      IpAddress
    MAX-ACCESS  read-write
    STATUS      current
    DESCRIPTION 
        "Stored in non-vol, 0.0.0.0 after factory reset."
    ::= { saRgIpMgmtWanAddrStatic 2 }

saRgIpMgmtWanStaticGateway OBJECT-TYPE
    SYNTAX      IpAddress
    MAX-ACCESS  read-write
    STATUS      current
    DESCRIPTION 
        "Stored in non-vol, 0.0.0.0 after factory reset."
    ::= { saRgIpMgmtWanAddrStatic 3 }

saRgIpMgmtWanAddrDualIp OBJECT IDENTIFIER ::= { saRgIpMgmtWanAddr 4 }

saRgIpMgmtWanDualIpAddr OBJECT-TYPE
    SYNTAX      IpAddress
    MAX-ACCESS  read-only
    STATUS      current
    DESCRIPTION 
        "IP address for the second IP stack.
         If not specified and saRgIpMgmtWanMode is set to
         dualIp(3), DHCP is used to acquire the IP address.
         Note: this object can only be set from config file."
    DEFVAL  { '00000000'h }
    ::= { saRgIpMgmtWanAddrDualIp 1 }

saRgIpMgmtWanDualIpRipAdvertised OBJECT-TYPE
    SYNTAX      TruthValue
    MAX-ACCESS  read-write
    STATUS      current
    DESCRIPTION
        "Specifies if the IP address is to be advertised in RIP,
         if RIP is enabled.
         Note: this object can only be set from config file."
    DEFVAL { true }
    ::= { saRgIpMgmtWanAddrDualIp 2 }

saRgIpMgmtWanAddrBackup OBJECT IDENTIFIER ::= { saRgIpMgmtWanAddr 5 }

saRgIpMgmtWanAddrBackupDefGw OBJECT-TYPE
    SYNTAX      IpAddress
    MAX-ACCESS  read-write
    STATUS      current
    DESCRIPTION 
        "IP address for the default gateway that is used when the
         cable modem interface is offline. This object is not in
         effect when the cable modem is online.         
         Note: this object is stored in non-vol and is 0.0.0.0
               after factory reset.
         The value of 0.0.0.0 means that this object is not in
         effect."
    ::= { saRgIpMgmtWanAddrBackup 1 }



-- **********************
-- LAN PORT Control Table    
-- **********************    
saRgIpMgmtLanPortControl   OBJECT IDENTIFIER ::=  { saRgIpMgmt 13 }


saRgIpMgmtLanPortControlTable OBJECT-TYPE
       SYNTAX      SEQUENCE OF SaRgIpMgmtLanPortControlEntry
       MAX-ACCESS  not-accessible
       STATUS      current
       DESCRIPTION
               "Table to control the mode for each LAN PORT. 
               LAN PORTs are numbered 1-4 and are mapped to physical
               port location. Each port can either be in router or
               in bridge mode."
    ::= { saRgIpMgmtLanPortControl 1 } 
    
saRgIpMgmtLanPortControlEntry OBJECT-TYPE 
    SYNTAX      SaRgIpMgmtLanPortControlEntry 
    MAX-ACCESS  not-accessible 
    STATUS      current 
    DESCRIPTION 
            "" 
    INDEX { saRgIpMgmtLanPortControlIndex } 
    ::= { saRgIpMgmtLanPortControlTable 1 } 
    
SaRgIpMgmtLanPortControlEntry ::= SEQUENCE {
    saRgIpMgmtLanPortControlIndex       INTEGER,
    saRgIpMgmtLanPortMode               INTEGER
    } 
    
saRgIpMgmtLanPortControlIndex OBJECT-TYPE 
    SYNTAX      INTEGER (1..4)
    MAX-ACCESS  not-accessible 
    STATUS      current 
    DESCRIPTION 
            "The index for each LAN port"
    ::= { saRgIpMgmtLanPortControlEntry 1 } 

saRgIpMgmtLanPortMode OBJECT-TYPE
    SYNTAX  INTEGER {
            bridge (1),
            router (2)
            }
    MAX-ACCESS  read-write 
    STATUS      current 
    DESCRIPTION
            "Each physical LAN port can either be controlled 
            as bridge or router. The saRgIpMgmtLanPortMode MIB only works
            when SaRgIpMgmtLanMode.32=4(Mixed). Setting this MIB
            through SNMP will take effect only after
            saRgIpMgmtApplySettings.0 set to true and this setting will
            reboot to take effect"
    ::= { saRgIpMgmtLanPortControlEntry 2 }     
    
saRgIpMgmtRestoreDefaults OBJECT-TYPE
   SYNTAX INTEGER {
   			disable(0),
   			bridgeDefaults(1),
   			routerDefaults(2)
   			}        
   MAX-ACCESS read-write
   STATUS current
   DESCRIPTION 
   		"MIB to control the default behavior for LAN mode. 
   		NOTE: This is customer specific ONLY. Not available in GA yet
   		Default behavior is disabled (0). - This means that GA behavior is the normal behavior. 
   		bridgeDefaults(1) - All the MIB objects in bridgeDefaults group would be set when CM boots up and would be retained across reboots/factory reset
   		routerDefaults(2) - All the MIB objects in routerDefaults group would be set when CM boots up and would be retained across reboots/factory reset"
  DEFVAL { 0 }
  
  ::= { saRgIpMgmt 14 }      
  
--============================================================================
--
--    saRgIpMgmtConnectedDevices 
--
--    The table contains a summary of devices connected over various interfaces
--   
--
--=============================================================================
                                                                                
saRgIpMgmtConnectedDevices   OBJECT IDENTIFIER ::=  { saRgIpMgmt 16 }
                                                                                
                                                                                
saRgIpMgmtConnectedDevicesSummary  OBJECT IDENTIFIER ::= { saRgIpMgmtConnectedDevices 1 }    

saRgIpMgmtTotalClientsOverMoCA OBJECT-TYPE      
    SYNTAX        INTEGER
    MAX-ACCESS    read-only
    STATUS        current
    DESCRIPTION
        "This MIB provides total number of devices that are connected over MoCA and have received IP address from
        gateway's DHCP pool"
    ::= { saRgIpMgmtConnectedDevicesSummary 1 }  

  

-- Apply setting to activate chagnes:
saRgIpMgmtApplySettings OBJECT-TYPE
    SYNTAX      TruthValue
    MAX-ACCESS  read-write
    STATUS      current
    DESCRIPTION
        "If set to true(1), then all the settings (MIB values)
         from this MIB tree will be applied to run time configuration,
         modifying previous RG operation with the new settings.
         Before setting the value to true, MIBs modified in the MIB
         tree are stored in non-vol and will not modify RG operation
         until saRgIpMgmtApplySettings is set to true or CM resets.
         Note: this applies only to the MIB objects that are stored
         in non-vol.
         Always returns false(2) when read."
    ::= { saRgIpMgmt 1001 }



-- =============================================
-- FIREWALL
--
-- Also includes port tiggering, forwarding, DMZ
-- =============================================

saRgFirewall OBJECT IDENTIFIER ::=  { saRg 4 }

saRgFirewallBase OBJECT IDENTIFIER ::=  { saRgFirewall 1 }

saRgFirewallProtection OBJECT-TYPE
SYNTAX INTEGER {
disable(0),
low(1),
medium (2),
high (3),
custom (4)
}
MAX-ACCESS read-write
STATUS current
DESCRIPTION
"Controls the firewall. This parameter is stored in non-vol and 
is enabled after factory reset.
Disable: Completely disables the SPI Firewall
Low/ Enable: Is Equivalent to Old Firewall Enable Mode with No Ports Restricted
Medium: Enables the SPI Firewall plus includes a list of Allowed Services that will be allowed to through the Firewall
High: Enables the SPI Firewall plus a shortened list of Allowed Services
Custom: Enables the SPI Firewall set to custom values. For use with Puma-based products."
::= { saRgFirewallBase 1 }

saRgFirewallDmzAddress OBJECT-TYPE 
    SYNTAX      IpAddress 
    MAX-ACCESS  read-write 
    STATUS      current 
    DESCRIPTION  
            "Stored in non-vol, 0.0.0.0 after facroty reset."
    ::= { saRgFirewallBase 2 } 
	
saRgFirewallPortForwardEnable OBJECT-TYPE
    SYNTAX      TruthValue
    MAX-ACCESS  read-write
    STATUS      current
    DESCRIPTION
        "Enables or disables firewall port forwarding on the device."
    DEFVAL { false }
    ::= { saRgFirewallBase 3 }
	
saRgFirewallPortTriggerEnable OBJECT-TYPE
    SYNTAX      TruthValue
    MAX-ACCESS  read-write
    STATUS      current
    DESCRIPTION
        "Enables or disables firewall port triggering on the device."
    DEFVAL { false }
    ::= { saRgFirewallBase 4 }

saRgFirewallTraffic OBJECT IDENTIFIER ::=  { saRgFirewall 2 }

saRgFirewallTrafficBlock OBJECT-TYPE
    SYNTAX BITS {
        proxy(0),
        cookies(1),
        javaApplets(2),
        activeX(3),
        popUp(4),
        fragmentedIp(5)
    }
    MAX-ACCESS    read-write
    STATUS        current
    DESCRIPTION
        "Controls blocking of certain traffic.
         Stored in non-vol, 0x00 after factory reset.
	Note: For DOCSIS 3.0 products with 553 and newer SW, 
	proxy(0), cookies(1), javaApplets(2), activeX(3), popUp(4) are NOT Supported."
    ::= { saRgFirewallTraffic 1 }

saRgFirewallTrafficDetect OBJECT-TYPE
    SYNTAX BITS {
        portScan(0),
        ipFlood(1)
    }
    MAX-ACCESS    read-write
    STATUS        current
    DESCRIPTION
        "Controls detecting of certain traffic.
         Stored in non-vol, 0x40 after factory reset."
    ::= { saRgFirewallTraffic 2 }

saRgFirewallTrafficPassThru OBJECT-TYPE
    SYNTAX BITS {
        ipsec(0),
        pptp(1),
        multicast(2),
		ident(3),
		icmp(4)
    }
    MAX-ACCESS    read-write
    STATUS        current
    DESCRIPTION
        "Controls passthru for certain traffic:
		ipsec(0), Block IPSec
		pptp(1), Block PPTP
		multicast(2), Block Multicast
		ident(3), Block IDENT (port 113), for use with Puma-based products
		icmp(4), Block ICMP, for use with Puma-based products
        Stored in non-vol, 0xe0 after factory reset."
    ::= { saRgFirewallTraffic 3 }

saRgFirewallWANBlockingEnable OBJECT-TYPE
    SYNTAX TruthValue
    MAX-ACCESS  read-write
    STATUS      current
    DESCRIPTION
        "Controls WAN blocking RG feature.
         Stored in non-vol, enabled after factory reset."
    ::= { saRgFirewallTraffic 4 }


-- Firewall events reporting

saRgFirewallReport OBJECT IDENTIFIER ::=  { saRgFirewall 4 }

saRgFirewallReportEventTable OBJECT-TYPE
       SYNTAX      SEQUENCE OF SaRgFirewallReportEventEntry
       MAX-ACCESS  not-accessible
       STATUS      current
       DESCRIPTION
               "This table is stored in non-vol and is empty
                after factory reset."
    ::= { saRgFirewallReport 1 } 
    
saRgFirewallReportEventEntry OBJECT-TYPE 
    SYNTAX      SaRgFirewallReportEventEntry 
    MAX-ACCESS  not-accessible 
    STATUS      current 
    DESCRIPTION 
            "" 
    INDEX { saRgFirewallReportEventIndex } 
    ::= { saRgFirewallReportEventTable 1 } 
    
SaRgFirewallReportEventEntry ::= SEQUENCE {
    saRgFirewallReportEventIndex          INTEGER,
    saRgFirewallReportEventDescription    SnmpAdminString,
    saRgFirewallReportEventCount          INTEGER, 
    saRgFirewallReportEventLastOccurance  SnmpAdminString,
    saRgFirewallReportEventTarget         SnmpAdminString,
    saRgFirewallReportEventSource         SnmpAdminString
    } 
    
saRgFirewallReportEventIndex OBJECT-TYPE 
    SYNTAX      INTEGER 
    MAX-ACCESS  not-accessible 
    STATUS      current 
    DESCRIPTION 
            "The index"
    ::= { saRgFirewallReportEventEntry 1 } 

saRgFirewallReportEventDescription OBJECT-TYPE 
    SYNTAX      SnmpAdminString 
    MAX-ACCESS  read-only 
    STATUS      current 
    DESCRIPTION 
            ""
    ::= { saRgFirewallReportEventEntry 2 } 

saRgFirewallReportEventCount OBJECT-TYPE 
    SYNTAX      INTEGER 
    MAX-ACCESS  read-only 
    STATUS      current 
    DESCRIPTION 
            ""
    ::= { saRgFirewallReportEventEntry 3 } 

saRgFirewallReportEventLastOccurance OBJECT-TYPE 
    SYNTAX      SnmpAdminString 
    MAX-ACCESS  read-only 
    STATUS      current 
    DESCRIPTION 
            ""
    ::= { saRgFirewallReportEventEntry 4 } 

saRgFirewallReportEventTarget OBJECT-TYPE 
    SYNTAX      SnmpAdminString 
    MAX-ACCESS  read-only 
    STATUS      current 
    DESCRIPTION 
            ""
    ::= { saRgFirewallReportEventEntry 5 } 

saRgFirewallReportEventSource OBJECT-TYPE 
    SYNTAX      SnmpAdminString 
    MAX-ACCESS  read-only 
    STATUS      current 
    DESCRIPTION 
            ""
    ::= { saRgFirewallReportEventEntry 6 } 


saRgFirewallReportMgmt OBJECT IDENTIFIER ::=  { saRgFirewallReport 2 }

saRgFirewallReportMgmtClearLog OBJECT-TYPE
    SYNTAX TruthValue
    MAX-ACCESS    read-write
    STATUS        current
    DESCRIPTION
        "Note: this object does not need saRgFirewallApplySettings
         to take effect."
    DEFVAL { false }
    ::= { saRgFirewallReportMgmt 1 }

saRgFirewallReportEmailLogNow OBJECT-TYPE
    SYNTAX TruthValue
    MAX-ACCESS    read-write
    STATUS        current
    DESCRIPTION
        "Triggers sending currect logs via email. Always returns false.
         Note: this objects does not need saRgFirewallApplySettings to
         send the logs."
    DEFVAL { false }
    ::= { saRgFirewallReportMgmt 2 }


saRgFirewallReportEmail OBJECT IDENTIFIER ::=  { saRgFirewallReport 3 }

saRgFirewallReportEmailEnable OBJECT-TYPE
    SYNTAX TruthValue
    MAX-ACCESS    read-write
    STATUS        current
    DESCRIPTION
        "Enables sending logs via email. Email is sent when an event happens."
    ::= { saRgFirewallReportEmail 1 }

saRgFirewallReportEmailAddress OBJECT-TYPE
    SYNTAX SnmpAdminString
    MAX-ACCESS    read-write
    STATUS        current
    DESCRIPTION
        "This is stored in non-vol and is empty after factory reset."
    ::= { saRgFirewallReportEmail 2 }

saRgFirewallReportEmailSmtpServer OBJECT-TYPE
    SYNTAX SnmpAdminString
    MAX-ACCESS    read-write
    STATUS        current
    DESCRIPTION
        "IP address or FQDN.
         Stored in non-vol. Empty after factory reset."
    ::= { saRgFirewallReportEmail 3 }

saRgFirewallReportEmailUsername OBJECT-TYPE
    SYNTAX SnmpAdminString
    MAX-ACCESS    read-write
    STATUS        current
    DESCRIPTION
        "This is stored in non-vol and is empty after factory reset."
    ::= { saRgFirewallReportEmail 4 }

saRgFirewallReportEmailPassword OBJECT-TYPE
    SYNTAX SnmpAdminString
    MAX-ACCESS    read-write
    STATUS        current
    DESCRIPTION
        "This is stored in non-vol and is empty after factory reset."
    ::= { saRgFirewallReportEmail 5 }


-- Firewall IP filtering

saRgFirewallRules OBJECT IDENTIFIER ::=  { saRgFirewall 5 }

saRgFirewallIpFilterTable OBJECT-TYPE
       SYNTAX      SEQUENCE OF SaRgFirewallIpFilterEntry
       MAX-ACCESS  not-accessible
       STATUS      current
       DESCRIPTION
               "This table is stored in non-vol and is empty
                after factory reset."
    ::= { saRgFirewallRules 1 } 
    
saRgFirewallIpFilterEntry OBJECT-TYPE 
    SYNTAX      SaRgFirewallIpFilterEntry 
    MAX-ACCESS  not-accessible 
    STATUS      current 
    DESCRIPTION 
            "" 
    INDEX { saRgFirewallIpFilterIndex } 
    ::= { saRgFirewallIpFilterTable 1 } 
    
SaRgFirewallIpFilterEntry ::= SEQUENCE {
    saRgFirewallIpFilterIndex              INTEGER,
    saRgFirewallIpFilterRowStatus          RowStatus,
    saRgFirewallIpFilterAddressStart       IpAddress, 
    saRgFirewallIpFilterAddressEnd         IpAddress,
    saRgFirewallIpFilterTrusted            INTEGER,
    saRgFirewallIpFilterPolicy             INTEGER
    } 
    
saRgFirewallIpFilterIndex OBJECT-TYPE 
    SYNTAX      INTEGER (1..10) 
    MAX-ACCESS  not-accessible 
    STATUS      current 
    DESCRIPTION 
            "The index"
    ::= { saRgFirewallIpFilterEntry 1 } 

saRgFirewallIpFilterRowStatus OBJECT-TYPE 
    SYNTAX      RowStatus 
    MAX-ACCESS  read-write 
    STATUS      current 
    DESCRIPTION 
            "The row status. A row can be destroyed.
             If the row is not used, set to notInService."
    ::= { saRgFirewallIpFilterEntry 2 } 

saRgFirewallIpFilterAddressStart OBJECT-TYPE 
    SYNTAX      IpAddress 
    MAX-ACCESS  read-write 
    STATUS      current 
    DESCRIPTION  
            ""
    ::= { saRgFirewallIpFilterEntry 3 } 

saRgFirewallIpFilterAddressEnd OBJECT-TYPE 
    SYNTAX      IpAddress 
    MAX-ACCESS  read-write 
    STATUS      current 
    DESCRIPTION  
            ""
    ::= { saRgFirewallIpFilterEntry 4 } 

saRgFirewallIpFilterTrusted OBJECT-TYPE 
    SYNTAX      INTEGER {
        block(1),
        permit(2)
    }	
    MAX-ACCESS  read-write 
    STATUS      current 
    DESCRIPTION  
            "Block/Permit this IP address based on saRgFirewallIpFilterPolicy"
    DEFVAL { block }
    ::= { saRgFirewallIpFilterEntry 5 }
	
saRgFirewallIpFilterPolicy OBJECT-TYPE
    SYNTAX      INTEGER {
        urlkeyword(1),
        port(2),
		none(3)
    }	
    MAX-ACCESS  read-write 
    STATUS      current 
    DESCRIPTION  
            "If urlkeyword(1), saRgFirewallIpFilterTrusted can be set to permit a particular computer regardless of saRgFirewallUrlKeywordFilterTable rules
	    If port(2), saRgFirewallIpFilterTrusted can be set to permit a particular computer regardless of saRgFirewallPortFilterTable rules
		If none(3), saRgFirewallIpFilterTrusted can be set to block or permit a computer regardless of any existing rules"
    DEFVAL { none }
    ::= { saRgFirewallIpFilterEntry 6 }
	
saRgFirewallPortFilterTable OBJECT-TYPE
       SYNTAX      SEQUENCE OF SaRgFirewallPortFilterEntry
       MAX-ACCESS  not-accessible
       STATUS      current
       DESCRIPTION
               "This table is stored in non-vol and is empty
                after factory reset."
    ::= { saRgFirewallRules 2 } 
    
saRgFirewallPortFilterEntry OBJECT-TYPE 
    SYNTAX      SaRgFirewallPortFilterEntry 
    MAX-ACCESS  not-accessible 
    STATUS      current 
    DESCRIPTION 
            "" 
    INDEX { saRgFirewallPortFilterIndex } 
    ::= { saRgFirewallPortFilterTable 1 } 
    
SaRgFirewallPortFilterEntry ::= SEQUENCE {
    saRgFirewallPortFilterIndex              INTEGER,
    saRgFirewallPortFilterRowStatus          RowStatus,
    saRgFirewallPortFilterPortStart          InetPortNumber,
    saRgFirewallPortFilterPortEnd            InetPortNumber,
    saRgFirewallPortFilterProto              INTEGER,
    saRgFirewallPortFilterAlwaysBlock        TruthValue,
    saRgFirewallPortFilterBlockStartTime     OCTET STRING,
    saRgFirewallPortFilterBlockEndTime       OCTET STRING,
    saRgFirewallPortFilterBlockDays          BITS
    } 
    
saRgFirewallPortFilterIndex OBJECT-TYPE 
    SYNTAX      INTEGER (1..10) 
    MAX-ACCESS  not-accessible 
    STATUS      current 
    DESCRIPTION 
            "The index"
    ::= { saRgFirewallPortFilterEntry 1 } 

saRgFirewallPortFilterRowStatus OBJECT-TYPE 
    SYNTAX      RowStatus 
    MAX-ACCESS  read-write 
    STATUS      current 
    DESCRIPTION 
            "The row status. A row can be destroyed.
             If the row is not used, set to notInService."
    ::= { saRgFirewallPortFilterEntry 2 } 

saRgFirewallPortFilterPortStart OBJECT-TYPE 
    SYNTAX      InetPortNumber 
    MAX-ACCESS  read-write 
    STATUS      current 
    DESCRIPTION  
            ""
    ::= { saRgFirewallPortFilterEntry 5 } 

saRgFirewallPortFilterPortEnd OBJECT-TYPE 
    SYNTAX      InetPortNumber 
    MAX-ACCESS  read-write 
    STATUS      current 
    DESCRIPTION  
            ""
    ::= { saRgFirewallPortFilterEntry 6 } 

saRgFirewallPortFilterProto OBJECT-TYPE 
    SYNTAX  INTEGER {
        udp(1),
        tcp(2),
        udpTcp(3)
        } 
    MAX-ACCESS  read-write 
    STATUS      current 
    DESCRIPTION  
            "IP protocol to block."
    DEFVAL { 3 }
    ::= { saRgFirewallPortFilterEntry 7 } 

saRgFirewallPortFilterAlwaysBlock OBJECT-TYPE 
    SYNTAX      TruthValue
    MAX-ACCESS  read-write 
    STATUS      current 
    DESCRIPTION  
        "If True(1), always be blocked, regardless of startTime, endTime and blockDays
	If False(2), blocked at time set in startTime, endTime and blockDays"
    DEFVAL { true }
    ::= { saRgFirewallPortFilterEntry 8 }
	
saRgFirewallPortFilterBlockStartTime OBJECT-TYPE 
    SYNTAX      OCTET STRING (SIZE (5))
    MAX-ACCESS  read-write 
    STATUS      current 
    DESCRIPTION  
        "24 Hour format HH:MM to set the start time to block"
    ::= { saRgFirewallPortFilterEntry 9 }
	
saRgFirewallPortFilterBlockEndTime OBJECT-TYPE 
    SYNTAX      OCTET STRING (SIZE (5))
    MAX-ACCESS  read-write 
    STATUS      current 
    DESCRIPTION  
        "24 Hour format HH:MM to set the end time to block"
    ::= { saRgFirewallPortFilterEntry 10 }

saRgFirewallPortFilterBlockDays OBJECT-TYPE 
    SYNTAX      BITS {
        sun(0),
        mon(1),
        tue(2),
        wed(3),
	thu(4),
	fri(5),
	sat(6)
	}
    MAX-ACCESS  read-write 
    STATUS      current 
    DESCRIPTION  
        "BITMAP to indicate which days to block"
    ::= { saRgFirewallPortFilterEntry 11 }
saRgFirewallMacFilterTable  OBJECT-TYPE
    SYNTAX      SEQUENCE OF SaRgFirewallMacFilterEntry
    MAX-ACCESS  not-accessible
    STATUS      current
    DESCRIPTION
        "A table of clients MAC addresses that are denied from accessing Internet."
    ::= { saRgFirewallRules 3 }

saRgFirewallMacFilterEntry OBJECT-TYPE
    SYNTAX      SaRgFirewallMacFilterEntry
    MAX-ACCESS  not-accessible
    STATUS      current
    DESCRIPTION
        "A row in the table that specifies a single station MAC address."
    INDEX   { saRgFirewallMacFilterIndex }
    ::= { saRgFirewallMacFilterTable 1 }

SaRgFirewallMacFilterEntry ::= 
    SEQUENCE    {
            saRgFirewallMacFilterIndex              INTEGER,
            saRgFirewallMacFilterRowStatus          RowStatus,
            saRgFirewallMacFilterAddress          MacAddress,
	    saRgFirewallMacFilterAlwaysBlock      TruthValue,
	    saRgFirewallMacFilterBlockStartTime   OCTET STRING,
	    saRgFirewallMacFilterBlockEndTime     OCTET STRING,
	    saRgFirewallMacFilterBlockDays        BITS
    }

saRgFirewallMacFilterIndex OBJECT-TYPE 
    SYNTAX      INTEGER (1..20) 
    MAX-ACCESS  not-accessible 
    STATUS      current 
    DESCRIPTION 
            "The index"
    ::= { saRgFirewallMacFilterEntry 1 } 

saRgFirewallMacFilterRowStatus OBJECT-TYPE 
    SYNTAX      RowStatus 
    MAX-ACCESS  read-write 
    STATUS      current 
    DESCRIPTION 
            "The row status. A row can be destroyed.
             If the row is not used, set to notInService."
    ::= { saRgFirewallMacFilterEntry 2 } 

saRgFirewallMacFilterAddress OBJECT-TYPE 
    SYNTAX      MacAddress
    MAX-ACCESS  read-write 
    STATUS      current 
    DESCRIPTION  
        "A MAC address of a station that cannot access Internet."
    ::= { saRgFirewallMacFilterEntry 3 }
	
saRgFirewallMacFilterAlwaysBlock OBJECT-TYPE 
    SYNTAX      TruthValue
    MAX-ACCESS  read-write 
    STATUS      current 
    DESCRIPTION  
        "If true(1), always be blocked/permitted, regardless of startTime, endTime and blockDays
	If false(2), blocked/permitted at time set in startTime, endTime and blockDays"
    DEFVAL { true }
    ::= { saRgFirewallMacFilterEntry 4 }
	
saRgFirewallMacFilterBlockStartTime OBJECT-TYPE 
    SYNTAX      OCTET STRING (SIZE (5))
    MAX-ACCESS  read-write 
    STATUS      current 
    DESCRIPTION  
        "24 Hour format HH:MM to set the start time to block/permit"
    ::= { saRgFirewallMacFilterEntry 5 }
	
saRgFirewallMacFilterBlockEndTime OBJECT-TYPE 
    SYNTAX      OCTET STRING (SIZE (5))
    MAX-ACCESS  read-write 
    STATUS      current 
    DESCRIPTION  
        "24 Hour format HH:MM to set the end time to block/permit"
    ::= { saRgFirewallMacFilterEntry 6 }

saRgFirewallMacFilterBlockDays OBJECT-TYPE 
    SYNTAX      BITS {
        sun(0),
        mon(1),
        tue(2),
        wed(3),
	thu(4),
	fri(5),
	sat(6)
	}
    MAX-ACCESS  read-write 
    STATUS      current 
    DESCRIPTION  
        "BITMAP to indicate which days to block/permit"
    ::= { saRgFirewallMacFilterEntry 7 }

saRgFirewallMacFilterEnable OBJECT-TYPE
    SYNTAX      TruthValue
    MAX-ACCESS  read-write
    STATUS      current
    DESCRIPTION
        "True = Enable the Mac address filtering feature. False = disable.
        this Value is written to non-vol and set to false after a factory reset."
    DEFVAL { false }
    ::= { saRgFirewallRules 4 }

saRgFirewallMacFilterMode OBJECT-TYPE
    SYNTAX      INTEGER {
        block(0),
        permit(1)
        } 
    MAX-ACCESS  read-write
    STATUS      current
    DESCRIPTION
        "block(0)- Macs listed in the saRgFirewallMacFilterEntryTable will be blocked.
        permit(1)- Macs listed in the saRgFirewallMacFilterEntryTable will be permitted.
        This value is written to non-vol and is set to block(0) after a factory reset."
    DEFVAL { 0 }
    ::= { saRgFirewallRules 5 }
	
saRgFirewallPortFilterEnable OBJECT-TYPE
    SYNTAX      TruthValue
    MAX-ACCESS  read-write
    STATUS      current
    DESCRIPTION
        "True = Enable the Port filtering feature. False = disable.
        this Value is written to non-vol and set to false after a factory reset."
    DEFVAL { false }
    ::= { saRgFirewallRules 6 }

saRgFirewallUrlKeywordFiltering   OBJECT IDENTIFIER ::=  { saRgFirewallRules 7 }
	
saRgFirewallUrlKeywordFilterEnable OBJECT-TYPE
    SYNTAX      TruthValue
    MAX-ACCESS  read-write
    STATUS      current
    DESCRIPTION
        "True = Enable the Url Keyword filtering feature. False = disable.
        this Value is written to non-vol and set to false after a factory reset."
    DEFVAL { false }
    ::= { saRgFirewallUrlKeywordFiltering 1 }
	
saRgFirewallUrlKeywordFilterTable  OBJECT-TYPE
    SYNTAX      SEQUENCE OF SaRgFirewallUrlKeywordFilterEntry
    MAX-ACCESS  not-accessible
    STATUS      current
    DESCRIPTION
        "A table of url and keyword rules that are denied from accessing Internet."
    ::= { saRgFirewallUrlKeywordFiltering 2 }

saRgFirewallUrlKeywordFilterEntry OBJECT-TYPE
    SYNTAX      SaRgFirewallUrlKeywordFilterEntry
    MAX-ACCESS  not-accessible
    STATUS      current
    DESCRIPTION
        "A row in the table that specifies a single station MAC address."
    INDEX   { saRgFirewallUrlKeywordFilterIndex }
    ::= { saRgFirewallUrlKeywordFilterTable 1 }

SaRgFirewallUrlKeywordFilterEntry ::= 
    SEQUENCE    {
            saRgFirewallUrlKeywordFilterIndex            INTEGER,
            saRgFirewallUrlKeywordFilterRowStatus        RowStatus,
            saRgFirewallUrlKeywordFilterMethod           INTEGER,
	    saRgFirewallUrlKeywordFilterMatch            OCTET STRING,
	    saRgFirewallUrlKeywordFilterAlwaysBlock      TruthValue,
	    saRgFirewallUrlKeywordFilterBlockStartTime   OCTET STRING,
	    saRgFirewallUrlKeywordFilterBlockEndTime     OCTET STRING,
	    saRgFirewallUrlKeywordFilterBlockDays        BITS
    }

saRgFirewallUrlKeywordFilterIndex OBJECT-TYPE 
    SYNTAX      INTEGER (1..20) 
    MAX-ACCESS  not-accessible 
    STATUS      current 
    DESCRIPTION 
            "The index"
    ::= { saRgFirewallUrlKeywordFilterEntry 1 } 

saRgFirewallUrlKeywordFilterRowStatus OBJECT-TYPE 
    SYNTAX      RowStatus 
    MAX-ACCESS  read-write 
    STATUS      current 
    DESCRIPTION 
            "The row status. A row can be destroyed.
             If the row is not used, set to notInService."
    ::= { saRgFirewallUrlKeywordFilterEntry 2 } 

saRgFirewallUrlKeywordFilterMethod OBJECT-TYPE 
    SYNTAX      INTEGER {
		url(1),
		keyword(2)
	}
    MAX-ACCESS  read-write 
    STATUS      current 
    DESCRIPTION  
        "If url(1),deny access to specific websites (URLs)
	If keyword(2), deny access to websites containing specific words"
    ::= { saRgFirewallUrlKeywordFilterEntry 3 }
	
saRgFirewallUrlKeywordFilterMatch OBJECT-TYPE 
    SYNTAX      OCTET STRING
    MAX-ACCESS  read-write 
    STATUS      current 
    DESCRIPTION  
        "URLs or specific words according to Method set"
    ::= { saRgFirewallUrlKeywordFilterEntry 4 }
	
saRgFirewallUrlKeywordFilterAlwaysBlock OBJECT-TYPE 
    SYNTAX      TruthValue
    MAX-ACCESS  read-write 
    STATUS      current 
    DESCRIPTION  
        "If true(1), always be blocked, regardless of startTime, endTime and blockDays
	If false(2), blocked at time set in startTime, endTime and blockDays"
    DEFVAL { true }
    ::= { saRgFirewallUrlKeywordFilterEntry 5 }
	
saRgFirewallUrlKeywordFilterBlockStartTime OBJECT-TYPE 
    SYNTAX      OCTET STRING (SIZE (5))
    MAX-ACCESS  read-write 
    STATUS      current 
    DESCRIPTION  
        "24 Hour format HH:MM to set the start time to block"
    ::= { saRgFirewallUrlKeywordFilterEntry 6 }
	
saRgFirewallUrlKeywordFilterBlockEndTime OBJECT-TYPE 
    SYNTAX      OCTET STRING (SIZE (5))
    MAX-ACCESS  read-write 
    STATUS      current 
    DESCRIPTION  
        "24 Hour format HH:MM to set the end time to block"
    ::= { saRgFirewallUrlKeywordFilterEntry 7 }

saRgFirewallUrlKeywordFilterBlockDays OBJECT-TYPE 
    SYNTAX      BITS {
        sun(0),
        mon(1),
        tue(2),
        wed(3),
	thu(4),
	fri(5),
	sat(6)
	}
    MAX-ACCESS  read-write 
    STATUS      current 
    DESCRIPTION  
        "BITMAP to indicate which days to block"
    ::= { saRgFirewallUrlKeywordFilterEntry 8 }
	
saRgFirewallHttpBlockingEnable OBJECT-TYPE
    SYNTAX      TruthValue
    MAX-ACCESS  read-write
    STATUS      current
    DESCRIPTION
        "Enables or disables firewall HTTP blocking on the device."
    DEFVAL { false }
    ::= { saRgFirewall 8 }

saRgFirewallP2pBlockingEnable OBJECT-TYPE
    SYNTAX      TruthValue
    MAX-ACCESS  read-write
    STATUS      current
    DESCRIPTION
        "Enables or disables firewall P2P blocking on the device."
    DEFVAL { false }
    ::= { saRgFirewall 9 }

saRgFirewallIdentBlockingEnable OBJECT-TYPE
    SYNTAX      TruthValue
    MAX-ACCESS  read-write
    STATUS      current
    DESCRIPTION
        "Enables or disables firewall ident blocking on the device."
    DEFVAL { false }
    ::= { saRgFirewall 10 }

saRgFirewallIcmpBlockingEnable OBJECT-TYPE
    SYNTAX      TruthValue
    MAX-ACCESS  read-write
    STATUS      current
    DESCRIPTION
        "Enables or disables firewall ICMP blocking on the device."
    DEFVAL { false }
    ::= { saRgFirewall 11 }

saRgFirewallMulticastBlockingEnable OBJECT-TYPE
    SYNTAX      TruthValue
    MAX-ACCESS  read-write
    STATUS      current
    DESCRIPTION
        "Enables or disables firewall multicast blocking on the device."
    DEFVAL { false }
    ::= { saRgFirewall 12 }


saRgFirewallApplySettings OBJECT-TYPE
    SYNTAX      TruthValue
    MAX-ACCESS  read-write
    STATUS      current
    DESCRIPTION
        "If set to true(1), then all the settings (MIB values)
         from this MIB tree will be applied to run time configuration,
         modifying previous RG operation with the new settings.
         Before setting the value to true, MIBs modified in the MIB
         tree are stored in non-vol and will not modify RG operation
         until saRgFirewallApplySettings is set to true or CM resets.
         Note: this applies only to the MIB objects that are stored
         in non-vol.
         Always returns false(2) when read."
    ::= { saRgFirewall 1001 }

saRgFirewallFactoryReset OBJECT-TYPE
    SYNTAX      TruthValue
    MAX-ACCESS  read-write
    STATUS      current
    DESCRIPTION
        "Set true(1) to restore default settings of firewall.
         Always returns false(2) when read."
    ::= { saRgFirewall 1002 }

-- ===
-- RIP
-- ===

saRgRip OBJECT IDENTIFIER ::=  { saRg 5 }

saRgRipBase OBJECT IDENTIFIER ::=  { saRgRip 1 }

saRgRipEnabled OBJECT-TYPE
    SYNTAX      TruthValue
    MAX-ACCESS  read-write
    STATUS      current
    DESCRIPTION
        "Enables or disables router information protocol support in the device."
    DEFVAL { false }
    ::= { saRgRipBase 1 }

saRgRipMd5AuthEnable	OBJECT-TYPE
    SYNTAX     TruthValue
    MAX-ACCESS read-write
    STATUS     current
    DESCRIPTION
        "Setting this object to true(1) causes the device to enable md5 auth"
    ::= { saRgRipBase 2 }

saRgRipMd5KeyId	OBJECT-TYPE
    SYNTAX     INTEGER (0..255)
    MAX-ACCESS read-write
    STATUS     current
    DESCRIPTION
        "Key ID value for Md5 auth.
         This object return an empty string when read."
    ::= { saRgRipBase 3 }

saRgRipMd5KeyValue OBJECT-TYPE
    SYNTAX     OCTET STRING (SIZE(0..16))
    MAX-ACCESS read-write
    STATUS     current
    DESCRIPTION
        "MD5 Key Value"
    ::= { saRgRipBase 4 }

saRgRipInterval	OBJECT-TYPE
    SYNTAX     INTEGER  (10..600)
    MAX-ACCESS read-write
    STATUS     current
    DESCRIPTION
        "Interval in Seconds for the Rip Reporting interval."
    ::= { saRgRipBase 5 }

saRgRipDestIpAddressType OBJECT-TYPE
    SYNTAX      InetAddressType
    MAX-ACCESS  read-write
    STATUS      current
    DESCRIPTION
        "The type of IP address assigned to the rgIpRipDestIpAddress."
    DEFVAL { ipv4 }
    ::= { saRgRipBase 6 }
  
saRgRipDestIpAddress OBJECT-TYPE
    SYNTAX      InetAddress
    MAX-ACCESS  read-write
    STATUS      current
    DESCRIPTION 
        "Defines the RIP unicast destination IP Address for Rip Reports.
         If this value returns 0.0.0.0 then this is the default
         multicast IP address in the RFC (224.0.0.9)"
    ::= { saRgRipBase 7 }

saRgRipAuthType  OBJECT-TYPE
    SYNTAX      INTEGER {
        noAuth(1),
        simplePassword(2),
        md5(3)
        }
    MAX-ACCESS read-write
    STATUS     current
    DESCRIPTION
        "For use with puma-based products,
		NoAuth(1), no authentication,
		SimplePassword(2), simple plain password,
		MD5(3), md5 auth"
	DEFVAL { noAuth }
    ::= { saRgRipBase 8 }

saRgRipAuthSimplePassword OBJECT-TYPE
    SYNTAX     OCTET STRING
    MAX-ACCESS read-write
    STATUS     current
    DESCRIPTION
        "Simple password when auth type is 2"
    ::= { saRgRipBase 9 }
	


-- ===========================
-- MoCA specific configuration
-- ===========================

saRgMocaExtSpecific OBJECT IDENTIFIER ::= { saRg 7 }

saRgMocaExtBase OBJECT IDENTIFIER ::= { saRgMocaExtSpecific 1 }

saRgMocaExtProvisioning OBJECT IDENTIFIER ::= { saRgMocaExtSpecific 2 }

saRgMocaExtProvFilename OBJECT-TYPE
    SYNTAX SnmpAdminString
    MAX-ACCESS read-write
    STATUS current
    DESCRIPTION
        " Specifies the filename for extender provisioning.
         The string is sent in DHCP OFFER and ACK as boot file to the extender.
         If not set, boot file option is empty."
    DEFVAL { "" }
    ::= { saRgMocaExtProvisioning 1 }

saRgMocaExtProvServerType OBJECT-TYPE
    SYNTAX InetAddressType
    MAX-ACCESS read-write
    STATUS current
    DESCRIPTION
        "Specifies the type for IP address for extender provisioning"
    DEFVAL { ipv4 }
    ::= { saRgMocaExtProvisioning 2 }

saRgMocaExtProvServer OBJECT-TYPE
    SYNTAX InetAddress
    MAX-ACCESS read-write
    STATUS current
    DESCRIPTION
        " Specifies the IP address for extender provisioning.
         The address is sent in DHCP OFFER and ACK as next server to the extender.
         If not set, the next server field is empty."
    DEFVAL  { '00000000'h } -- 0.0.0.0
    ::= { saRgMocaExtProvisioning 3 }

    
-- ==================================
-- Wifi Hotspot Specific Information
-- ==================================

saRgWifiHotspotMib OBJECT IDENTIFIER ::= { saRg 13 }

saRgWifiHotspotBase OBJECT IDENTIFIER ::= { saRgWifiHotspotMib 1 }

saRgWifiHotspotEnabled OBJECT-TYPE     
    SYNTAX      TruthValue
    MAX-ACCESS  read-write
    STATUS      current
    DESCRIPTION
        "Enables or disable Wifi Hotspot support in the device."
   ::= { saRgWifiHotspotBase 1 }

saRgWifiHotspotTable OBJECT-TYPE
    SYNTAX      SEQUENCE OF SaRgWifiHotspotEntry
    MAX-ACCESS  not-accessible
    STATUS      current
    DESCRIPTION
        "A table used to configure settings related to Wi-fi Hotspot." 
    ::= { saRgWifiHotspotBase 2 }         
    
saRgWifiHotspotEntry OBJECT-TYPE
    SYNTAX      SaRgWifiHotspotEntry
    MAX-ACCESS  not-accessible
    STATUS      current
    DESCRIPTION
         "An entry defining the Wi-fi hotspot characteristics of an 
          individual Wi-Fi network interface."
    INDEX   { saRgWifiHotspotIf }
    ::= { saRgWifiHotspotTable 1 }

SaRgWifiHotspotEntry ::= 
    SEQUENCE    {
        saRgWifiHotspotInstance              Unsigned32,
        saRgWifiHotspotIf                    INTEGER,
        saRgWifiHotspotMode                  INTEGER,
        saRgWifiHotspotCpeIdleTimeout        Unsigned32,
        saRgWifiHotspotCpeSessionTimeout     Unsigned32,
        saRgWifiHotspotRadiusAccAddressType  InetAddressType,
        saRgWifiHotspotRadiusAccAddress      InetAddress,
        saRgWifiHotspotRadiusAccPort         InetPortNumber,
        saRgWifiHotspotRadiusAccKey          DisplayString,
        saRgWifiHotspotPacketFilterMask      Unsigned32,
        saRgWifiHotspotInsertDhcpOptionsMask Unsigned32, 
        saRgWifiHotspotRowStatus             RowStatus
    }
   

saRgWifiHotspotInstance    OBJECT-TYPE
    SYNTAX      Unsigned32 
    MAX-ACCESS  not-accessible
    STATUS      current
    DESCRIPTION
        "The key for a unique instance of this object."
    ::= { saRgWifiHotspotEntry 1 }

saRgWifiHotspotIf OBJECT-TYPE
    SYNTAX      INTEGER {
                        wifi1-0(1),
                        wifi1-1(2),
                        wifi1-2(3),
                        wifi1-3(4),
                        wifi1-4(5),
                        wifi1-5(6),
                        wifi1-6(7),
                        wifi1-7(8),
                        wifi2-0(9),
                        wifi2-1(10),
                        wifi2-2(11),
                        wifi2-3(12),
                        wifi2-4(13),
                        wifi2-5(14),
                        wifi2-6(15),
                        wifi2-7(16)
        }
    MAX-ACCESS  read-create
    STATUS      current
    DESCRIPTION
        "Wi-fi network interface."
    ::= { saRgWifiHotspotEntry 2 }

saRgWifiHotspotMode OBJECT-TYPE
    SYNTAX      INTEGER {
                disable(1),
                enableBridge(2),
                enableL2oGre(3)
    }
    MAX-ACCESS  read-create
    STATUS      current
    DESCRIPTION
        "Wi-fi Hotsot mode:
         enableBridge - Wi-Fi traffic will be bridged
         enableL2oGre - Wi-Fi traffic will be sent over GRE tunnel.
                        GRE Tunnel should be configured and enabled."
    ::= { saRgWifiHotspotEntry 3 }

saRgWifiHotspotCpeIdleTimeout OBJECT-TYPE
    SYNTAX      Unsigned32
    MAX-ACCESS  read-create
    STATUS      current
    DESCRIPTION
        "CPE inactivity/idle timeout in seconds which will trigger disconnect.
         Value of 0 will disable inactivity tracking."
    ::= { saRgWifiHotspotEntry 4 }

saRgWifiHotspotCpeSessionTimeout OBJECT-TYPE
    SYNTAX      Unsigned32
    MAX-ACCESS  read-create
    STATUS      current
    DESCRIPTION
        "CPE maximum session duration timeout in seconds. 
         Value of 0 will disable tracking session duration."
    ::= { saRgWifiHotspotEntry 5 }

saRgWifiHotspotRadiusAccAddressType OBJECT-TYPE
    SYNTAX      InetAddressType
    MAX-ACCESS  read-create
    STATUS      current
    DESCRIPTION
        "The type of internet address used for saRgWifiHotspotRadiusAccAddress."
    ::= { saRgWifiHotspotEntry 6 }
    
saRgWifiHotspotRadiusAccAddress OBJECT-TYPE
    SYNTAX      InetAddress
    MAX-ACCESS  read-create
    STATUS      current
    DESCRIPTION
        "The internet address of the RADIUS Accounting server for this service set."
    ::= { saRgWifiHotspotEntry 7 }
  
saRgWifiHotspotRadiusAccPort OBJECT-TYPE
    SYNTAX      InetPortNumber
    MAX-ACCESS  read-create
    STATUS      current
    DESCRIPTION
        "The UDP port used to communicate with the RADIUS Accounting server. 
         Default value set to 1813."      
    DEFVAL { 1813 }
    ::= { saRgWifiHotspotEntry 8 }
    
saRgWifiHotspotRadiusAccKey OBJECT-TYPE
    SYNTAX      DisplayString
    MAX-ACCESS  read-create
    STATUS      current
    DESCRIPTION
        "The RADIUS Accounting server shared security key."
    ::= { saRgWifiHotspotEntry 9 }

saRgWifiHotspotPacketFilterMask OBJECT-TYPE
    SYNTAX      Unsigned32
    MAX-ACCESS  read-create
    STATUS      current
    DESCRIPTION
        "Bit mask for limiting traffic to certain packet types.
         Possible value:
         11111111 11111111 11111111 11111111: Allow All traffic
         xxxxxxxx xxxxxxxx xxxxxxxx xxxxxxx1: Allow IPv4 (0x0800) packets
         xxxxxxxx xxxxxxxx xxxxxxxx xxxxxx1x: Allow IPv6 (0x86dd) packets
         xxxxxxxx xxxxxxxx xxxxxxxx xxxxx1xx: Allow IPx  (0x8137) packets
         xxxxxxxx xxxxxxxx xxxxxxxx xxxx1xxx: Allow ARP  (0x0806) packets
         xxxxxxxx xxxxxxxx xxxxxxxx xxx1xxxx: Allow RARP (0x8035) packets
         xxxxxxxx xxxxxxxx xxxxxxxx xx1xxxxx: Allow VLAN (0x8100) packets
         "
    ::= { saRgWifiHotspotEntry 10 }

saRgWifiHotspotInsertDhcpOptionsMask OBJECT-TYPE
    SYNTAX      Unsigned32
    MAX-ACCESS  read-create
    STATUS      current
    DESCRIPTION
        "Bit mask for inserting DHCP options in DHCP Discover/Request packet from 
         connected wifi client device.
         Possible value:
         0x1: Insert DHCP relay agent option 82.
              circuit-id sub-option: AP-MAC-ADDRESS;SSID-NAME;SSID-TYPE
         0x2: Insert DHCP relay agent option 82.
              remote-id  sub-option: String containing MAC address of connected 
                                     wifi client device in the format XX:XX:XX:XX:XX:XX.
         0x4: Insert/Modify DHCP option 60 with string containing SSID Name."
    ::= { saRgWifiHotspotEntry 11 }

saRgWifiHotspotRowStatus OBJECT-TYPE
    SYNTAX RowStatus
    MAX-ACCESS read-create
    STATUS current
    DESCRIPTION
        "The RowStatus interlock for the creation and deletion
        can be modified at any time while the row is active(1)."
    ::= { saRgWifiHotspotEntry 12 }

saRgWifiHotspotAutRateLimit OBJECT-TYPE     
    SYNTAX      Unsigned32
    MAX-ACCESS  read-write
    STATUS      current
    DESCRIPTION
        "Authentication rate limit in messages per second. If client exceeds
         this limit, authentication from the client is ignored for 
         saRgWifiHotspotAutDenialTimeout."
   ::= { saRgWifiHotspotBase 3 }

saRgWifiHotspotAutDenialTimeout OBJECT-TYPE     
    SYNTAX      Unsigned32
    MAX-ACCESS  read-write
    STATUS      current
    DESCRIPTION
        "Timeout in seconds during which authentication from a client is ignored
         once authentication message rate exceeds saRgWifiHotspotAutRateLimit."
   ::= { saRgWifiHotspotBase 4 }

saRgWifiHotspotRadiusOrigIf OBJECT-TYPE
    SYNTAX      INTEGER {
                eRouter(1),
                cm(2)
        }
    MAX-ACCESS  read-write
    STATUS      current
    DESCRIPTION
        "Originating interface of radius authentication and accounting traffic."
    ::= { saRgWifiHotspotBase 5 }

saRgWifiHotspotIgnoreMaxCpeSetting OBJECT-TYPE     
    SYNTAX      TruthValue
    MAX-ACCESS  read-write
    STATUS      current
    DESCRIPTION
        "This setting is applicable for wifi hotspot bridged mode.
         When set to true(1), clients connected through the hotspot wifi will not be 
         counted when enforcing the 'Maximum CPE devices' on DOCSIS."
   ::= { saRgWifiHotspotBase 6 }  

-- ====================================================
-- L2oGRE tunnel for Wifi Hotspot specific information
-- ====================================================
       
saRgL2ogreMib OBJECT IDENTIFIER ::= { saRg 14 }
  
saRgL2ogreBase OBJECT IDENTIFIER ::= { saRgL2ogreMib 1 }

saRgL2ogreEnabled OBJECT-TYPE     
    SYNTAX      TruthValue
    MAX-ACCESS  read-write
    STATUS      current
    DESCRIPTION
        "Enables or disable GRE Tunnel support in the device."  
    DEFVAL { false }
   ::= { saRgL2ogreBase 1 }

saRgL2ogrePriRemoteAddressType OBJECT-TYPE
    SYNTAX      InetAddressType
    MAX-ACCESS  read-write
    STATUS      current
    DESCRIPTION
        "The IP address type (ipv4, ipv6 or dns) of primary remote  
         endpoint of the GRE tunnel."
    DEFVAL { ipv4 }
    ::= { saRgL2ogreBase 2 }

saRgL2ogrePriRemoteAddress OBJECT-TYPE
    SYNTAX      InetAddress
    MAX-ACCESS  read-write
    STATUS      current
    DESCRIPTION
        "IP address or FQDN of primary remote endpoint of the GRE tunnel."
    ::= { saRgL2ogreBase 3 }

saRgL2ogreSecRemoteAddressType OBJECT-TYPE
    SYNTAX      InetAddressType
    MAX-ACCESS  read-write
    STATUS      current
    DESCRIPTION
        "The IP address type (ipv4, ipv6 or dns) of secondary remote 
         endpoint of the GRE tunnel."
    DEFVAL { ipv4 }
    ::= { saRgL2ogreBase 4 }

saRgL2ogreSecRemoteAddress OBJECT-TYPE
    SYNTAX      InetAddress
    MAX-ACCESS  read-write
    STATUS      current
    DESCRIPTION
        "IP address or FQDN of secondary remote endpoint of the GRE tunnel."
    ::= { saRgL2ogreBase 5 }

saRgL2ogreDSCP OBJECT-TYPE
    SYNTAX      Integer32 (0..63)
    MAX-ACCESS  read-write
    STATUS      current
    DESCRIPTION
        "The method is used to set the high 6 bits of TOS in the 
         IPv4 header or traffic class in IPv6 header."
    ::= { saRgL2ogreBase 6 }

saRgL2ogreKeepAliveMode OBJECT-TYPE
    SYNTAX      INTEGER {
                disabled(1), 
                ping(2),
                ping-noswitchover(3) 
    }
    MAX-ACCESS  read-write
    STATUS      current
    DESCRIPTION
        "Keepalive modes for failover mechanism.
         ping - Use ICMP pings within tunnel as a keepalive messages."
    ::= { saRgL2ogreBase 7 }

saRgL2ogreKeepAliveCount OBJECT-TYPE
    SYNTAX      Integer32  
    MAX-ACCESS  read-write
    STATUS      current
    DESCRIPTION
        "Number of keep-alive messages sent at regular interval."
    ::= { saRgL2ogreBase 8 }

saRgL2ogreKeepAliveInterval OBJECT-TYPE
    SYNTAX      Integer32  
    MAX-ACCESS  read-write
    STATUS      current
    DESCRIPTION
        "Interval in seconds between keep-alive messages."
    ::= { saRgL2ogreBase 9 }

saRgL2ogreKeepAliveFailureThreshold OBJECT-TYPE
    SYNTAX      Integer32  
    MAX-ACCESS  read-write
    STATUS      current
    DESCRIPTION
        "Number of keep-alive failures that will cause fail-over."
    ::= { saRgL2ogreBase 10 }

saRgL2ogreStatsTable OBJECT-TYPE
    SYNTAX      SEQUENCE OF SaRgL2ogreStatsEntry
    MAX-ACCESS  not-accessible
    STATUS      current
    DESCRIPTION
        "This table provides statistical information of GRE tunnel." 
    ::= { saRgL2ogreBase 11 }

saRgL2ogreStatsEntry OBJECT-TYPE
    SYNTAX      SaRgL2ogreStatsEntry
    MAX-ACCESS  not-accessible
    STATUS      current
    DESCRIPTION
        "This table provides statistical information of GRE tunnel." 
    INDEX { saRgL2ogreStatsIndex }
    ::= { saRgL2ogreStatsTable 1 }

SaRgL2ogreStatsEntry ::= SEQUENCE {
    saRgL2ogreStatsIndex                    Integer32,
    saRgL2ogreStatsBytesSent                Counter64,
    saRgL2ogreStatsBytesReceived            Counter64,
    saRgL2ogreStatsPacketsSent              Counter64,
    saRgL2ogreStatsPacketsReceived          Counter64,
    saRgL2ogreStatsDiscardPacketsReceived   Counter64,
    saRgL2ogreStatsErrorPacketsReceived     Counter64,
    saRgL2ogreStatsKeepAliveSent            Counter64,
    saRgL2ogreStatsKeepAliveReceived        Counter64,
    saRgL2ogreStatsRowStatus                RowStatus
}

saRgL2ogreStatsIndex OBJECT-TYPE
    SYNTAX      Integer32 (1..256) 
    MAX-ACCESS  not-accessible
    STATUS      current
    DESCRIPTION
        "Table index"
    ::= { saRgL2ogreStatsEntry 1 }

saRgL2ogreStatsBytesSent OBJECT-TYPE
    SYNTAX      Counter64 
    MAX-ACCESS  read-only
    STATUS      current
    DESCRIPTION
        "Number bytes sent."
    ::= { saRgL2ogreStatsEntry 2 }

saRgL2ogreStatsBytesReceived OBJECT-TYPE
    SYNTAX      Counter64 
    MAX-ACCESS  read-only
    STATUS      current
    DESCRIPTION
        "Number bytes received."
    ::= { saRgL2ogreStatsEntry 3 }

saRgL2ogreStatsPacketsSent OBJECT-TYPE
    SYNTAX      Counter64 
    MAX-ACCESS  read-only
    STATUS      current
    DESCRIPTION
        "Number packets sent."
    ::= { saRgL2ogreStatsEntry 4 }

saRgL2ogreStatsPacketsReceived OBJECT-TYPE
    SYNTAX      Counter64 
    MAX-ACCESS  read-only
    STATUS      current
    DESCRIPTION
        "Number packets received."
    ::= { saRgL2ogreStatsEntry 5 }

saRgL2ogreStatsDiscardPacketsReceived OBJECT-TYPE
    SYNTAX      Counter64 
    MAX-ACCESS  read-only
    STATUS      current
    DESCRIPTION
        "Number packets received that were discarded.
         Because source network interface is down."
    ::= { saRgL2ogreStatsEntry 6 }

saRgL2ogreStatsErrorPacketsReceived OBJECT-TYPE
    SYNTAX      Counter64 
    MAX-ACCESS  read-only
    STATUS      current
    DESCRIPTION
        "Number packets received that were in error.
         Because tunnel packets are not correct type.
         Eg. Received IP packet instead of L2 packets."
    ::= { saRgL2ogreStatsEntry 7 }

saRgL2ogreStatsKeepAliveSent OBJECT-TYPE
    SYNTAX      Counter64 
    MAX-ACCESS  read-only
    STATUS      current
    DESCRIPTION
        "Number keepalive packets sent."
    ::= { saRgL2ogreStatsEntry 8 }

saRgL2ogreStatsKeepAliveReceived OBJECT-TYPE
    SYNTAX      Counter64 
    MAX-ACCESS  read-only
    STATUS      current
    DESCRIPTION
        "Number keepalive packets received."
    ::= { saRgL2ogreStatsEntry 9 }

saRgL2ogreSourceIfTable OBJECT-TYPE
    SYNTAX      SEQUENCE OF SaRgL2ogreSourceIfEntry
    MAX-ACCESS  not-accessible
    STATUS      current
    DESCRIPTION
        "This table contains information specific to network source interface 
         whose traffic is mapped into GRE tunnel." 
    ::= { saRgL2ogreBase 12 }

saRgL2ogreSourceIfEntry OBJECT-TYPE
    SYNTAX      SaRgL2ogreSourceIfEntry
    MAX-ACCESS  not-accessible
    STATUS      current
    DESCRIPTION
        "List of individual source interface entries mapped into GRE tunnel."
    INDEX { saRgL2ogreSourceIfInstance }
    ::= { saRgL2ogreSourceIfTable 1 }

SaRgL2ogreSourceIfEntry ::= SEQUENCE {
    saRgL2ogreSourceIfInstance           Unsigned32,
    saRgL2ogreSourceIf                   INTEGER,
    saRgL2ogreSourceIfEnabled            TruthValue,
    saRgL2ogreSourceIfVlanTag            Integer32,
    saRgL2ogreSourceIfMplsHeader         Integer32,
    saRgL2ogreSourceIfRowStatus          RowStatus
}

saRgL2ogreSourceIfInstance    OBJECT-TYPE
    SYNTAX      Unsigned32 
    MAX-ACCESS  not-accessible
    STATUS      current
    DESCRIPTION
        "The key for a unique instance of this object."
    ::= {saRgL2ogreSourceIfEntry 1 }

saRgL2ogreSourceIf OBJECT-TYPE
    SYNTAX      INTEGER {
                        wifi1-0(1),
                        wifi1-1(2),
                        wifi1-2(3),
                        wifi1-3(4),
                        wifi1-4(5),
                        wifi1-5(6),
                        wifi1-6(7),
                        wifi1-7(8),
                        wifi2-0(9),
                        wifi2-1(10),
                        wifi2-2(11),
                        wifi2-3(12),
                        wifi2-4(13),
                        wifi2-5(14),
                        wifi2-6(15),
                        wifi2-7(16)
        }
    MAX-ACCESS  read-create
    STATUS      current
    DESCRIPTION
        "Source interface whose traffic will be pass through GRE tunnel."
    ::= { saRgL2ogreSourceIfEntry 2 }

saRgL2ogreSourceIfEnabled OBJECT-TYPE     
    SYNTAX      TruthValue
    MAX-ACCESS  read-create
    STATUS      current
    DESCRIPTION
        "Enables or disable mapping traffic from network interface into GRE tunnel."
   ::= { saRgL2ogreSourceIfEntry 3 }

saRgL2ogreSourceIfVlanTag OBJECT-TYPE
    SYNTAX      Integer32  
    MAX-ACCESS  read-create
    STATUS      current
    DESCRIPTION
        "Add VLAN tag consists of 16bit of Tag Protocol Identifier (TPID)
         and 16 bit of Tag Control Identifier (TCI).
         Value of 0 will disable adding VLAN tag.
         Tag Protocol Identifier (TPID) should set to 0x8100."
    ::= { saRgL2ogreSourceIfEntry 4 }

saRgL2ogreSourceIfMplsHeader OBJECT-TYPE
    SYNTAX      Integer32   
    MAX-ACCESS  read-create
    STATUS      current
    DESCRIPTION
        "MPLS Header. Value of 0 will disable adding MPLS Header."
    ::= { saRgL2ogreSourceIfEntry 5 }

saRgL2ogreSourceIfRowStatus OBJECT-TYPE
    SYNTAX      RowStatus
    MAX-ACCESS  read-create
    STATUS      current
    DESCRIPTION
        "The RowStatus interlock for the creation and deletion of a table entry."
    ::= { saRgL2ogreSourceIfEntry 6 }

saRgL2ogreOrigIf OBJECT-TYPE
    SYNTAX      INTEGER {
                eRouter(1)
               }
    MAX-ACCESS  read-write
    STATUS      current
    DESCRIPTION
        "Originating Interface of GRE tunnel."
    ::= { saRgL2ogreBase 13 }

saRgL2ogreConcentratorServiceName OBJECT-TYPE
    SYNTAX      DisplayString
    MAX-ACCESS  read-write
    STATUS      current
    DESCRIPTION
        "FQDN of GRE tunnel concentrator/gw service. 
         If this is set then, DNS Query of type SRV will be used for discovering 
         FQDN of primary and secondary remote endpoint of GRE tunnel."
    ::= { saRgL2ogreBase 14 }

saRgL2ogreDnsResolverRetryTimerMin OBJECT-TYPE
    SYNTAX      Unsigned32
    MAX-ACCESS  read-write
    STATUS      current
    DESCRIPTION
        "Minimum timeout interval in seconds before retrying DNS query."
    ::= { saRgL2ogreBase 15 }

saRgL2ogreDnsResolverRetryTimerMax OBJECT-TYPE
    SYNTAX      Unsigned32
    MAX-ACCESS  read-write
    STATUS      current
    DESCRIPTION
        "Maximum timeout interval in seconds before retrying DNS query."
    ::= { saRgL2ogreBase 16 }

saRgL2ogreKeepAliveFailureInterval OBJECT-TYPE
    SYNTAX      Integer32
    MAX-ACCESS  read-write
    STATUS      current
    DESCRIPTION
        "Configured interval between pings for WLAN GW when disabled due to both WLAN GWs failing."
    ::= { saRgL2ogreBase 17 }

saRgL2ogreKeepAliveReattemptInterval OBJECT-TYPE
    SYNTAX      Integer32
    MAX-ACCESS  read-write
    STATUS      current
    DESCRIPTION
        "Configured interval to reattempt connection to a primary WLAN GW even when secondary WLAN GW is available and clients are connected."
    ::= { saRgL2ogreBase 18 }


-- ====================================================
-- Network Extender Status MIB
-- ====================================================

saRgNetworkExtenders OBJECT IDENTIFIER ::= { saRg 16 }

saRgNetworkExtenderTable  OBJECT-TYPE
    SYNTAX      SEQUENCE OF SaRgNetworkExtenderEntry
    MAX-ACCESS  not-accessible
    STATUS      current
    DESCRIPTION
        "Multiple Attached Network Extender Table. Maximum of 8 Entries"

    ::= { saRgNetworkExtenders 1 }

saRgNetworkExtenderEntry OBJECT-TYPE
    SYNTAX      SaRgNetworkExtenderEntry
    MAX-ACCESS  not-accessible
    STATUS      current
    DESCRIPTION
        "A row in the table which represents information about attached Network Extender."
    INDEX   { saRgNetworkExtenderIndex }
    ::= { saRgNetworkExtenderTable 1 }

SaRgNetworkExtenderEntry ::= SEQUENCE {
      saRgNetworkExtenderIndex                INTEGER,
      saRgNetworkExtenderIpAddress            IpAddress,
      saRgNetworkExtenderDeviceName           OCTET STRING,
      saRgNetworkExtenderVenderName           OCTET STRING,
      saRgNetworkExtenderModelNumber          OCTET STRING,
      saRgNetworkExtenderFirmwareVersion      OCTET STRING
    }

saRgNetworkExtenderIndex OBJECT-TYPE
    SYNTAX      INTEGER (1..8)
    MAX-ACCESS  not-accessible
    STATUS      current
    DESCRIPTION
        "The index of the the table.  Up to 8 connected devices supported"
    ::= { saRgNetworkExtenderEntry 1 }

saRgNetworkExtenderIpAddress OBJECT-TYPE
    SYNTAX      IpAddress
    MAX-ACCESS  read-only
    STATUS      current
    DESCRIPTION
        "The IP Address of the Device"
    ::= { saRgNetworkExtenderEntry 2 }

saRgNetworkExtenderDeviceName OBJECT-TYPE
    SYNTAX      OCTET STRING (SIZE(0..32))
    MAX-ACCESS  read-only
    STATUS      current
    DESCRIPTION
        "The Name of the Device as returned by HNAP"
    ::= { saRgNetworkExtenderEntry 3 }

saRgNetworkExtenderVenderName OBJECT-TYPE
    SYNTAX      OCTET STRING (SIZE(0..32))
    MAX-ACCESS  read-only
    STATUS      current
    DESCRIPTION
        "The Vender Name as returned by HNAP"
    ::= { saRgNetworkExtenderEntry 4 }

saRgNetworkExtenderModelNumber OBJECT-TYPE
    SYNTAX      OCTET STRING (SIZE(0..32))
    MAX-ACCESS  read-only
    STATUS      current
    DESCRIPTION
        "The Model Number of the Device as returned by HNAP"
    ::= { saRgNetworkExtenderEntry 5 }

saRgNetworkExtenderFirmwareVersion OBJECT-TYPE
    SYNTAX      OCTET STRING (SIZE(0..32))
    MAX-ACCESS  read-only
    STATUS      current
    DESCRIPTION
        "The Firmware version of the Device as returned by HNAP"
    ::= { saRgNetworkExtenderEntry 6 }

-- ====================================================
-- Network Extender Radio Status Table
-- ====================================================

saRgNetworkExtenderRadioTable  OBJECT-TYPE
    SYNTAX      SEQUENCE OF SaRgNetworkExtenderRadioEntry
    MAX-ACCESS  not-accessible
    STATUS      current
    DESCRIPTION
        "Attached Network Extender Radio Table. Maximum of 32 entries (per extender).
        If the attached device has no radios/SSID, this table will be empty"
    ::= { saRgNetworkExtenders 2 }

saRgNetworkExtenderRadioEntry OBJECT-TYPE
    SYNTAX      SaRgNetworkExtenderRadioEntry
    MAX-ACCESS  not-accessible
    STATUS      current
    DESCRIPTION
        "A row in the table for Network Extender attached WiFi Radios."
    INDEX       {   saRgNetworkExtenderIndex,
                                saRgNetworkExtenderRadioIndex }
    ::= { saRgNetworkExtenderRadioTable 1 }

SaRgNetworkExtenderRadioEntry ::= SEQUENCE {
        saRgNetworkExtenderRadioIndex           INTEGER,
        saRgNetworkExtenderRadioSSID            OCTET STRING,
        saRgNetworkExtenderRadioBSSID           PhysAddress,
        saRgNetworkExtenderRadioChannel         OCTET STRING,
        saRgNetworkExtenderRadioMode            OCTET STRING
    }

saRgNetworkExtenderRadioIndex OBJECT-TYPE
    SYNTAX      INTEGER (1..32)
    MAX-ACCESS  not-accessible
    STATUS      current
    DESCRIPTION
        "The index of the radio/SSID. Up to 32 SSIDs supported"
    ::= { saRgNetworkExtenderRadioEntry 1 }

saRgNetworkExtenderRadioSSID OBJECT-TYPE
    SYNTAX      OCTET STRING (SIZE(0..32))
    MAX-ACCESS  read-only
    STATUS      current
    DESCRIPTION
        "The SSID of the radio as by HNAP"
    ::= { saRgNetworkExtenderRadioEntry 2 }

saRgNetworkExtenderRadioBSSID OBJECT-TYPE
    SYNTAX      PhysAddress
    MAX-ACCESS  read-only
    STATUS      current
    DESCRIPTION
        "The BSSID as reported by HNAP"
    ::= { saRgNetworkExtenderRadioEntry 3 }

saRgNetworkExtenderRadioChannel OBJECT-TYPE
    SYNTAX      OCTET STRING (SIZE(0..32))
    MAX-ACCESS  read-only
    STATUS      current
    DESCRIPTION
        "Returns the Primary Radio Channel Number as reported by HNAP"
    ::= { saRgNetworkExtenderRadioEntry 4 }

saRgNetworkExtenderRadioMode OBJECT-TYPE
    SYNTAX      OCTET STRING (SIZE(0..32))
    MAX-ACCESS  read-only
    STATUS      current
    DESCRIPTION
        "Returns the Radio Operational Mode as reported by HNAP"
    ::= { saRgNetworkExtenderRadioEntry 5 }

-- ====================================================
-- Network Extender Connected Client Table
-- ====================================================
saRgNetworkExtenderClientTable  OBJECT-TYPE
    SYNTAX      SEQUENCE OF SaRgNetworkExtenderClientEntry
    MAX-ACCESS  not-accessible
    STATUS      current
    DESCRIPTION
        "Attached Network Extender Client Table. Maximum of 64 Entries per Extender"
    ::= { saRgNetworkExtenders 3 }

saRgNetworkExtenderClientEntry OBJECT-TYPE
    SYNTAX      SaRgNetworkExtenderClientEntry
    MAX-ACCESS  not-accessible
    STATUS      current
    DESCRIPTION
        "A row in the table denoting Network Extender Clients."
    INDEX       {   saRgNetworkExtenderIndex,
                    saRgNetworkExtenderClientIndex }
    ::= { saRgNetworkExtenderClientTable  1 }

SaRgNetworkExtenderClientEntry ::= SEQUENCE {
         saRgNetworkExtenderClientIndex          INTEGER,
         saRgNetworkExtenderClientMAC            PhysAddress,
         saRgNetworkExtenderClientInterface      OCTET STRING
    }

saRgNetworkExtenderClientIndex OBJECT-TYPE
    SYNTAX      INTEGER (1..64)
    MAX-ACCESS  not-accessible
    STATUS      current
    DESCRIPTION
        "The index of the Client."
    ::= { saRgNetworkExtenderClientEntry 1 }


saRgNetworkExtenderClientMAC OBJECT-TYPE
    SYNTAX      PhysAddress
    MAX-ACCESS  read-only
    STATUS      current
    DESCRIPTION
        "Returns the client's MAC as reported by HNAP"
    ::= { saRgNetworkExtenderClientEntry 2 }

saRgNetworkExtenderClientInterface OBJECT-TYPE
    SYNTAX      OCTET STRING (SIZE(0..32))
    MAX-ACCESS  read-only
    STATUS      current
    DESCRIPTION
        "Returns the client's connected interface per HNAP.   Wifi-2.4, Wifi-5.0, Ethernet, etc"
    ::= { saRgNetworkExtenderClientEntry 3 }
  
END
