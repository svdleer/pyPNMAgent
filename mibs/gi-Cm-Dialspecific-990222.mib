CM-DIALSPECIFIC-MIB DEFINITIONS ::= BEGIN

IMPORTS 
        OBJECT-TYPE,
	MODULE-IDENTITY,
	enterprises
               FROM SNMPv2-SMI
        DisplayString
               FROM SNMPv2-TC ;

 
cmDialSpecific MODULE-IDENTITY
LAST-UPDATED "9902221130Z"
ORGANIZATION "General Instrument"
CONTACT-INFO "Thomas Beifuss
Postal: 6450 Sequence Dr.
San Diego, CA 92121
Tel: +1 619 404-2643
Fax: +1 619 404-3480
E-mail: tbeifuss@gi.com"

DESCRIPTION
"This module defines proprietary MIB variables to support the
 dialing features of gi cable modems."
::= {	enterprises
	gi(1166)  
	giproducts(1)
	cm(19)
        8
     }

cmDialSpecificObjects OBJECT IDENTIFIER ::= { cmDialSpecific 1 }
	
cmDialSpecificDialMode OBJECT-TYPE
        SYNTAX    INTEGER
        {
          autoDial(0),
          manualDial(1)
        }
        MAX-ACCESS  read-write
        STATUS      current
        DESCRIPTION
          "This variable controls whether dialing is done automatically
           or is user initiated."
        REFERENCE   ""
    ::= { cmDialSpecificObjects 1 }

cmDialSpecificDialingPrefix1 OBJECT-TYPE
        SYNTAX DisplayString (SIZE(1..20))
        MAX-ACCESS  read-write
        STATUS      current
        DESCRIPTION
          "A string which is sent to the telephone line before the
           actual phone number.  An example of this is the practice
           of dialing 9 to reach an outside line"
        REFERENCE   ""
    ::= { cmDialSpecificObjects 2 }
cmDialSpecificDialingPrefix2 OBJECT-TYPE
        SYNTAX DisplayString (SIZE(1..20))
        MAX-ACCESS  read-write
        STATUS      current
        DESCRIPTION
          "A string which is sent to the telephone line before the
           actual phone number.  An example of this is the practice
           of dialing 9 to reach an outside line"
        REFERENCE   ""
    ::= { cmDialSpecificObjects 3 }
cmDialSpecificDialingPrefix3 OBJECT-TYPE
        SYNTAX DisplayString (SIZE(1..20))
        MAX-ACCESS  read-write
        STATUS      current
        DESCRIPTION
          "A string which is sent to the telephone line before the
           actual phone number.  An example of this is the practice
           of dialing 9 to reach an outside line"
        REFERENCE   ""
    ::= { cmDialSpecificObjects 4 }
cmDialSpecificModemCommand OBJECT-TYPE
        SYNTAX DisplayString (SIZE(1..64))
        MAX-ACCESS  read-write
        STATUS      current
        DESCRIPTION
          "A string which is sent to the modem before dialing.
           An example of this is the Hayes AT Command set"
        REFERENCE   ""
    ::= { cmDialSpecificObjects 5 }
cmDialSpecificModemTimeout OBJECT-TYPE
	SYNTAX INTEGER (10..255)
	MAX-ACCESS read-write
	STATUS	   current
        DESCRIPTION
          "Timeout value for connecting with telco modem"
     ::= { cmDialSpecificObjects 6 }
cmDialSpecificCountryProfile OBJECT-TYPE
	SYNTAX INTEGER 
	MAX-ACCESS read-write
	STATUS	   current
        DESCRIPTION
          "The country code to be used by the telco modem.
           For the 4100D the following country codes are available:
           australiaItu(9),
           austriaItu(10),
           belgiumItu(15),
           brazilItu(22),
           chinaItu(38),
           denmarkItu(49),
           finlandItu(60),
           franceItu(61),
           germanyItu(66),
           greeceItu(70),
           indiaItu(83),
           irelandItu(87),
           italyItu(89),
           japanItu(0),
           koreaItu(97),
           malaysiaItu(108),
           mexicoItu(115),
           netherlandsItu(123),
           norwayItu(130),
           polandItu(138),
           portugalItu(139),
           singaporeItu(156),
           southAfricaItu(159),
           spainItu(160),
           swedenItu(165),
           switzerlandItu(166),
           taiwanItu(254),
           unitedKingdomItu(180),
           unitedStatesItu(181)

           for the 3100D the following country codes are available:
           austria(1),
           belgium(2),
           denmark(3),
           finland(4),
           france(5),
           germany(6),
           ireland(7),
           italy(8),
           netherlands(10),
           norway(11),
           portugal(12),
           spain(13),
           sweden(14),
           switzerland(15),
           unitedKingdom(16),
           greece(17),
           unitedStates(22),
           australia(40),
           japan(43),
           taiwan(46),
           singapore(47) "          
     ::= { cmDialSpecificObjects 7 }

END
