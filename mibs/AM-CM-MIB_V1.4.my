--
-- AM-CM-MIB_V1.4.my
-- MIB generated by MG-SOFT Visual MIB Builder Version 2.1 Build 199
-- Friday, October 22, 2010 at 18:08:49
--

	AM-CM-MIB DEFINITIONS ::= BEGIN

		IMPORTS 
			amCableModem, amCMCommon, amAlphaCM			
				FROM AM-CMROOT-MIB			
			OBJECT-TYPE			
				FROM RFC-1212;
	
	
--
-- Node definitions
--
	
		amSingleIPEnable OBJECT-TYPE
			SYNTAX INTEGER
				{
				enable(1),
				disable(2)
				}
			ACCESS read-write
			STATUS mandatory
			DESCRIPTION
				"Enables or Disables Single IP Solution. If Single IP is not enabled CM will 
				function as a normal cable modem. Default value is Enabled. 
				The value is saved in nonvolatile memory."
			::= { amAlphaCM 1 }
		
		amProxyQueueTimeout OBJECT-TYPE
			SYNTAX INTEGER (1..2147483647)
			ACCESS read-write
			STATUS mandatory
			DESCRIPTION
				"This parameter shows the amount of time in which a request is stored in 
				the queue of Proxy agent. Duration in seconds. 
				The value is saved in nonvolatile memory."
			::= { amAlphaCM 2 }
		
		amProxyDsmRespTimeout OBJECT-TYPE
			SYNTAX INTEGER (1..2147483647)
			ACCESS read-write
			STATUS mandatory
			DESCRIPTION
				"This parameter shows the amount of time in which a DSM request should
				wait for the response in Proxy task. Duration in seconds. 
				The value is saved in nonvolatile memory."
			::= { amAlphaCM 3 }
		
		amBpiManager OBJECT IDENTIFIER ::= { amCableModem 3 }
		
		amCmCertificateManager OBJECT IDENTIFIER ::= { amBpiManager 1 }
		
		amCmCertificateUpgrade OBJECT-TYPE
			SYNTAX INTEGER
				{
				ignoreUpgrade(1),
				verifyAndUpgrade(2)
				}
			ACCESS read-write
			STATUS optional
			DESCRIPTION
				"Triggers CM Certificate upgrade"
			DEFVAL { 1 }
			::= { amCmCertificateManager 1 }
		
		amCmCertificateStatus OBJECT-TYPE
			SYNTAX INTEGER
				{
				ok(1),
				keyExtensionError(2)
				}
			ACCESS read-write
			STATUS optional
			DESCRIPTION
				"Displays the status of CM Certificate"
			DEFVAL { 1 }
			::= { amCmCertificateManager 2 }
		
	
	END

--
-- AM-CM-MIB_V1.4.my
--
