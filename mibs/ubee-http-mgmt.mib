--**************************************************************************
--    Description:
--
--		private MIB for runtime Ubee management
--		
--**************************************************************************
--    Revision History:
--
--**************************************************************************

UBEE-HTTP-MGMT-MIB DEFINITIONS ::= BEGIN

IMPORTS
    MODULE-IDENTITY,
    OBJECT-TYPE,
    IpAddress
        FROM SNMPv2-SMI
    DisplayString,
    TruthValue
        FROM SNMPv2-TC
    cableDataMgmtBase
        FROM UBEE-CABLEDATA-MGMT-MIB;
                
httpMgmt MODULE-IDENTITY
    LAST-UPDATED "201209120000Z"
    ORGANIZATION "Ubee Interactive Corporation"
    CONTACT-INFO
        "	Ubee Interactive Global Headquarters

        Postal: 6F-9, No.38, Taiyuan St.
        		Jhubei City Hsinchu County 302
        		Taiwan, R.O.C.

           Tel: +886-3-560-0010

        E-mail: asupport@ubeeinteractive.com"
    DESCRIPTION
        "Ubee proprietary MIB for runtime management and configuration
         of objects related to HTTP."
    ::= { cableDataMgmtBase 3 }
    
httpAdminId OBJECT-TYPE
    SYNTAX      DisplayString
    MAX-ACCESS  read-write
    STATUS      current
    DESCRIPTION
        "Controls and reflects the user name for admin level HTTP priveleges."
    DEFVAL { "" }
    ::= { httpMgmt 1 }

httpAdminPassword OBJECT-TYPE
    SYNTAX      DisplayString
    MAX-ACCESS  read-write
    STATUS      current
    DESCRIPTION
        "Controls and reflects the password for admin level HTTP priveleges."
    DEFVAL { "" }
    ::= { httpMgmt 2 }
    
httpUserId OBJECT-TYPE
    SYNTAX      DisplayString
    MAX-ACCESS  read-write
    STATUS      current
    DESCRIPTION
        "Controls and reflects the user name for user level HTTP priveleges."
    DEFVAL { "" }
    ::= { httpMgmt 3 }

httpUserPassword OBJECT-TYPE
    SYNTAX      DisplayString
    MAX-ACCESS  read-write
    STATUS      current
    DESCRIPTION
        "Controls and reflects the password for user level HTTP priveleges."
    DEFVAL { "" }
    ::= { httpMgmt 4 }

httpIpStackInterfaces OBJECT-TYPE
    SYNTAX      BITS {
                interface1(0),
                interface2(1),
                interface3(2),
                interface4(3),
                interface5(4),
                interface6(5),
                interface7(6),
                interface8(7)
    }
    MAX-ACCESS  read-write
    STATUS      current
    DESCRIPTION
        "Controls and reflects the IP stack interfaces on which an HTTP server
         is active.  By default, the HTTP server is enabled only on the private
         IP stack interface."
    ::= { httpMgmt 5 }

httpAdvancedAccessEnabled OBJECT-TYPE
    SYNTAX      BITS {
                interface1(0),
                interface2(1),
                interface3(2),
                interface4(3),
                interface5(4),
                interface6(5),
                interface7(6),
                interface8(7)
    }
    MAX-ACCESS  read-write
    STATUS      current
    DESCRIPTION
        "Controls and reflects the IP stack interfaces on which advanced
        access is allowed.  By default, advanced access is allowed only on
        remote stack interfaces."
    ::= { httpMgmt 6 }

httpPasswordOfTheDaySeed OBJECT-TYPE
    SYNTAX      DisplayString
    MAX-ACCESS  read-write
    STATUS      current
    DESCRIPTION
        "Controls and reflects the seed used to generate the password of the day."
    DEFVAL { "" }
    ::= { httpMgmt 7 }


httpLoginTimeout OBJECT-TYPE
    SYNTAX      Unsigned32
    UNITS       "seconds"
    MAX-ACCESS  read-write
    STATUS      current
    DESCRIPTION
        "Controls the timeout of the webpage login in seconds."
    DEFVAL { 0 }
    ::= { httpMgmt 8 }

httpWanAccessTimeout OBJECT-TYPE
    SYNTAX      INTEGER (0..86400)
    UNITS       "seconds"
    MAX-ACCESS  read-write
    STATUS      current
    DESCRIPTION
        "This object controls the length of time after which HTTP access
         via the WAN interface will be terminated if no HTTP activity via the
         WAN interface is detected within this period.  If set to a value of 0, 
         there will be no such timeout in effect.

         The timer begins running when the HTTP server starts.  After the number 
         of seconds specified by this object has elapsed, if no http traffic
         has been detected via the WAN interface, a filter will be created which
         drops all HTTP traffic destined to any of the device's IP addresses 
         which arrives via the WAN interface.

         If any HTTP activity via the WAN interface is detected during the 
         period of time alloted by this object, the timer will be reset.

         Setting this object to any value will cause the timer to be reset."
    DEFVAL { 0 }
    ::= { httpMgmt 9 }

END
