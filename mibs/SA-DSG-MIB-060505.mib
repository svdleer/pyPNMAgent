--
-- SA-DSG-MIB.mib
-- MIB generated by MG-SOFT Visual MIB Builder Version 4.0 Build 349
-- Sunday, June 05, 2005 at 15:10:07
--

-- Revision 1 : Initial
-- Date: Thursday, December 09, 2004 at 10:06:58
-- Comment:
-- Initial Release
-- 
	SA-DSG-MIB DEFINITIONS ::= BEGIN
 
		IMPORTS
			saDsgMib			
				FROM SA-DBDSGEN-MIB			
			saModules			
				FROM SCIATL-COMMON-MIB			
			OBJECT-GROUP			
				FROM SNMPv2-CONF			
			Integer32, Unsigned32, Counter32, OBJECT-TYPE, MODULE-IDENTITY, 
			OBJECT-IDENTITY			
				FROM SNMPv2-SMI			
			TruthValue, PhysAddress			
				FROM SNMPv2-TC;
	
	
-- Scientific-Atlanta Proprietary Information
-- 
-- Copyright 2005 Scientific-Atlanta, Inc.
-- 
-- All rights reserved.
-- 
--  
-- 
-- Unauthorized copying and distribution are prohibited.  
-- 
-- No part of this MIB may be reprinted, reproduced or utilized
-- 
-- in any form or by any electronic, mechanical, or other means, now known or
-- 
-- hereafter invented, including photocopying and recording, or using any
-- 
-- information storage and retrieval system, without permission in writing
-- 
-- from Scientific-Atlanta, Inc.
-- 
		-- 1.3.6.1.4.1.1429.7.1.25
		saDsgMibModule MODULE-IDENTITY 
			LAST-UPDATED "200506051507Z"		-- June 05, 2005 at 15:07 GMT
			ORGANIZATION 
				"Scientific-Atlanta"
			CONTACT-INFO 
				"DBDS Software Engineering & Architecture
				Scientific-Atlanta
				5030 Sugarloaf Parkway
				Lawrenceville, GA 30044
				"
			DESCRIPTION 
				"The Scientific-Atlanta proprietary MIB for DOCSIS Settop Gateway information.
				
				PRELIMINARY FOR INTERNAL REVIEW ONLY!"
			REVISION "200506051508Z"		-- June 05, 2005 at 15:08 GMT
			DESCRIPTION 
				"Added OBJECT GROUPs;
				Modified saDsgCcMode"
			REVISION "200412091006Z"		-- December 09, 2004 at 10:06 GMT
			DESCRIPTION 
				"Initial Release"
			::= { saModules 25 }

		
	
	
--
-- Node definitions
--
	
		-- 1.3.6.1.4.1.1429.9.1.15.1
		saDsgConf OBJECT-IDENTITY
			STATUS current
			DESCRIPTION 
				"Conformance"
			::= { saDsgMib 1 }

		
		-- 1.3.6.1.4.1.1429.9.1.15.1.1
		saDsgGroups OBJECT-IDENTITY
			STATUS current
			DESCRIPTION 
				"Object Groups of the SA-DSG-MIB"
			::= { saDsgConf 1 }

		
		-- 1.3.6.1.4.1.1429.9.1.15.1.1.1
		saDsgCcTableGroup OBJECT-GROUP
			OBJECTS { saDsgCcMode, saDsgCcState }
			STATUS current
			DESCRIPTION 
				"A group for the saDsgCcDcdTable."
			::= { saDsgGroups 1 }

		
		-- 1.3.6.1.4.1.1429.9.1.15.1.1.2
		saDsgCcDcdOpCccTableGroup OBJECT-GROUP
			OBJECTS { saDsgCcDcdOpCcc }
			STATUS current
			DESCRIPTION 
				"A group for the saDsgCcDcdOpCccTable"
			::= { saDsgGroups 2 }

		
		-- 1.3.6.1.4.1.1429.9.1.15.1.1.3
		saDsgCcDcdFragsInTableGroup OBJECT-GROUP
			OBJECTS { saDsgCcDcdFragsIn }
			STATUS current
			DESCRIPTION 
				"A group for the saDsgCcDcdFragsInTable."
			::= { saDsgGroups 3 }

		
		-- 1.3.6.1.4.1.1429.9.1.15.1.1.4
		saDsgCcCachedModIdTableGroup OBJECT-GROUP
			OBJECTS { saDsgCcCachedModId, saDsgCcCachedModIdValid }
			STATUS current
			DESCRIPTION 
				"A group for the saDsgCcCachedModIdTable"
			::= { saDsgGroups 4 }

		
		-- 1.3.6.1.4.1.1429.9.1.15.1.1.5
		saDsgCcCachedUcidTableGroup OBJECT-GROUP
			OBJECTS { saDsgCcCachedUcidValid, saDsgCcCachedUcid }
			STATUS current
			DESCRIPTION 
				"A group for the saDsgCcCachedUcidTable"
			::= { saDsgGroups 5 }

		
		-- 1.3.6.1.4.1.1429.9.1.15.1.1.6
		saDsgCcMacAddrListTableGroup OBJECT-GROUP
			OBJECTS { saDsgCcMacAddrListIndex, saDsgCcMacAddrListAddr }
			STATUS current
			DESCRIPTION 
				"A group for the saDsgCcMacAddrListTable"
			::= { saDsgGroups 6 }

		
		-- 1.3.6.1.4.1.1429.9.1.15.1.2
		saDsgCompls OBJECT-IDENTITY
			STATUS current
			DESCRIPTION 
				"Compliances of the SA-DSG-MIB"
			::= { saDsgConf 2 }

		
		-- 1.3.6.1.4.1.1429.9.1.15.2
		saDsgObjs OBJECT-IDENTITY
			STATUS current
			DESCRIPTION 
				"The MIB Objects defined for the SA-DSG-MIB module."
			::= { saDsgMib 2 }

		
		-- 1.3.6.1.4.1.1429.9.1.15.2.1
		saDsgCc OBJECT-IDENTITY
			STATUS current
			DESCRIPTION 
				"Information pertaining to DSG Client Controllers"
			::= { saDsgObjs 1 }

		
		-- 1.3.6.1.4.1.1429.9.1.15.2.1.1
		saDsgCcTable OBJECT-TYPE
			SYNTAX SEQUENCE OF SaDsgCcEntry
			MAX-ACCESS not-accessible
			STATUS current
			DESCRIPTION
				"This table represents information for each DSG-CC.
				
				An entry exists for each DSG-CC reported by the agent. If only one
				DSG-CC is supported, then it must have saDsgCcIndex value of 1.	"
			::= { saDsgCc 1 }

		
		-- 1.3.6.1.4.1.1429.9.1.15.2.1.1.1
		saDsgCcEntry OBJECT-TYPE
			SYNTAX SaDsgCcEntry
			MAX-ACCESS not-accessible
			STATUS current
			DESCRIPTION
				"An entry in the table."
			INDEX { saDsgCcIndex }
			::= { saDsgCcTable 1 }

		
		SaDsgCcEntry ::=
			SEQUENCE { 
				saDsgCcIndex
					Integer32,
				saDsgCcMode
					INTEGER,
				saDsgCcState
					INTEGER
			 }

		-- 1.3.6.1.4.1.1429.9.1.15.2.1.1.1.1
		saDsgCcIndex OBJECT-TYPE
			SYNTAX Integer32 (1..2147483647)
			MAX-ACCESS not-accessible
			STATUS current
			DESCRIPTION
				"A unique number for each DSG-CC instance.
				
				The value for each DSG-CC must remain constant atleast from one re-initialization of 
				the entity's network management system to the next re-initialization.
				
				If only one DSG-CC is supported, then it must have saDsgCcIndex value of 1."
			::= { saDsgCcEntry 1 }

		
		-- 1.3.6.1.4.1.1429.9.1.15.2.1.1.1.2
		saDsgCcMode OBJECT-TYPE
			SYNTAX INTEGER
				{
				disabled(1),
				saBasic(2),
				basic(3),
				advanced(4),
				standalone(5),
				dcdBasic(6)
				}
			MAX-ACCESS read-only
			STATUS current
			DESCRIPTION
				"The mode of the DSG-CC:
				
				disabled   = The DSG-CC is not operating
				saBasic    = S-A Basic DSG Mode
				basic      = DSG Basic Mode
				advanced   = DSG Advanced Mode
				standalone = DOCSIS without DSG
				dcdBasic   = DSG Basic Mode with certain provisioning accomplished by 
				             a DCD delivered through proprietary means  
				
				 "
			::= { saDsgCcEntry 2 }

		
		-- 1.3.6.1.4.1.1429.9.1.15.2.1.1.1.3
		saDsgCcState OBJECT-TYPE
			SYNTAX INTEGER
				{
				na(1),
				stopped(2),
				dsEval(3),
				brSel(4),
				cacheCWt(5),
				cachedOp(6),
				noUcidM(7),
				twoWay(8)
				}
			MAX-ACCESS read-only
			STATUS current
			DESCRIPTION
				"The state of the DSG-CC.
				
				na       = Not applicable
				stopped  = Stopped
				dsEval   = Downstream Evaluation and Search
				brSel    = Bridge Selection
				cacheCWt = Cache Confirm Wait
				cachedOp = Cached Operation
				noUcidM  = No UCID Match
				twoWay   = 2Way
				"
			::= { saDsgCcEntry 3 }

		
		-- 1.3.6.1.4.1.1429.9.1.15.2.1.2
		saDsgCcDcdOpCccTable OBJECT-TYPE
			SYNTAX SEQUENCE OF SaDsgCcDcdOpCccEntry
			MAX-ACCESS not-accessible
			STATUS current
			DESCRIPTION
				"This table provides the DCD Change Config Count number currently being used by each DSG-CC
				for operation. 
				
				An entry exists for each DSG-CC reported by the agent."
			::= { saDsgCc 2 }

		
		-- 1.3.6.1.4.1.1429.9.1.15.2.1.2.1
		saDsgCcDcdOpCccEntry OBJECT-TYPE
			SYNTAX SaDsgCcDcdOpCccEntry
			MAX-ACCESS not-accessible
			STATUS current
			DESCRIPTION
				"An entry in the table."
			AUGMENTS { saDsgCcEntry }
			::= { saDsgCcDcdOpCccTable 1 }

		
		SaDsgCcDcdOpCccEntry ::=
			SEQUENCE { 
				saDsgCcDcdOpCcc
					Integer32
			 }

		-- 1.3.6.1.4.1.1429.9.1.15.2.1.2.1.1
		saDsgCcDcdOpCcc OBJECT-TYPE
			SYNTAX Integer32 (-1 | 0..255)
			MAX-ACCESS read-only
			STATUS current
			DESCRIPTION
				"The DCD Change Config Count number currently being used by the DSG-CC for operation.
				If no DCD is currently being used, then this object has a (-1) value."
			::= { saDsgCcDcdOpCccEntry 1 }

		
		-- 1.3.6.1.4.1.1429.9.1.15.2.1.3
		saDsgCcDcdFragsInTable OBJECT-TYPE
			SYNTAX SEQUENCE OF SaDsgCcDcdFragsInEntry
			MAX-ACCESS not-accessible
			STATUS current
			DESCRIPTION
				"This table provides the count of DCD fragments received by each DSG-CC.
				"
			::= { saDsgCc 3 }

		
		-- 1.3.6.1.4.1.1429.9.1.15.2.1.3.1
		saDsgCcDcdFragsInEntry OBJECT-TYPE
			SYNTAX SaDsgCcDcdFragsInEntry
			MAX-ACCESS not-accessible
			STATUS current
			DESCRIPTION
				"An entry in the table."
			AUGMENTS { saDsgCcEntry }
			::= { saDsgCcDcdFragsInTable 1 }

		
		SaDsgCcDcdFragsInEntry ::=
			SEQUENCE { 
				saDsgCcDcdFragsIn
					Counter32
			 }

		-- 1.3.6.1.4.1.1429.9.1.15.2.1.3.1.1
		saDsgCcDcdFragsIn OBJECT-TYPE
			SYNTAX Counter32
			MAX-ACCESS read-only
			STATUS current
			DESCRIPTION
				"The count of DCD fragments received by the DSG-CC since agent initialization.
				"
			::= { saDsgCcDcdFragsInEntry 1 }

		
		-- 1.3.6.1.4.1.1429.9.1.15.2.1.4
		saDsgCcCachedModIdTable OBJECT-TYPE
			SYNTAX SEQUENCE OF SaDsgCcCachedModIdEntry
			MAX-ACCESS not-accessible
			STATUS current
			DESCRIPTION
				"This table provides the current value of the cached Mod ID for each DSG-CC.
				"
			::= { saDsgCc 4 }

		
		-- 1.3.6.1.4.1.1429.9.1.15.2.1.4.1
		saDsgCcCachedModIdEntry OBJECT-TYPE
			SYNTAX SaDsgCcCachedModIdEntry
			MAX-ACCESS not-accessible
			STATUS current
			DESCRIPTION
				"An entry in the table."
			AUGMENTS { saDsgCcEntry }
			::= { saDsgCcCachedModIdTable 1 }

		
		SaDsgCcCachedModIdEntry ::=
			SEQUENCE { 
				saDsgCcCachedModIdValid
					TruthValue,
				saDsgCcCachedModId
					Unsigned32
			 }

		-- 1.3.6.1.4.1.1429.9.1.15.2.1.4.1.1
		saDsgCcCachedModIdValid OBJECT-TYPE
			SYNTAX TruthValue
			MAX-ACCESS read-only
			STATUS current
			DESCRIPTION
				"Indicates if the value in saDsgCcCachedModId is valid."
			::= { saDsgCcCachedModIdEntry 1 }

		
		-- 1.3.6.1.4.1.1429.9.1.15.2.1.4.1.2
		saDsgCcCachedModId OBJECT-TYPE
			SYNTAX Unsigned32
			MAX-ACCESS read-only
			STATUS current
			DESCRIPTION
				"The current value of the cached Mod ID for the DSG-CC.
				This object is only valid if saDsgCcCachedModIdValid is true.
				"
			::= { saDsgCcCachedModIdEntry 2 }

		
		-- 1.3.6.1.4.1.1429.9.1.15.2.1.5
		saDsgCcCachedUcidTable OBJECT-TYPE
			SYNTAX SEQUENCE OF SaDsgCcCachedUcidEntry
			MAX-ACCESS not-accessible
			STATUS current
			DESCRIPTION
				"This table provides the current value of the cached UCID for each DSG-CC.
				"
			::= { saDsgCc 5 }

		
		-- 1.3.6.1.4.1.1429.9.1.15.2.1.5.1
		saDsgCcCachedUcidEntry OBJECT-TYPE
			SYNTAX SaDsgCcCachedUcidEntry
			MAX-ACCESS not-accessible
			STATUS current
			DESCRIPTION
				"An entry in the table."
			AUGMENTS { saDsgCcEntry }
			::= { saDsgCcCachedUcidTable 1 }

		
		SaDsgCcCachedUcidEntry ::=
			SEQUENCE { 
				saDsgCcCachedUcidValid
					TruthValue,
				saDsgCcCachedUcid
					Integer32
			 }

		-- 1.3.6.1.4.1.1429.9.1.15.2.1.5.1.1
		saDsgCcCachedUcidValid OBJECT-TYPE
			SYNTAX TruthValue
			MAX-ACCESS read-only
			STATUS current
			DESCRIPTION
				"Indicates if the value in saDsgCcCachedUCID is valid."
			::= { saDsgCcCachedUcidEntry 1 }

		
		-- 1.3.6.1.4.1.1429.9.1.15.2.1.5.1.2
		saDsgCcCachedUcid OBJECT-TYPE
			SYNTAX Integer32
			MAX-ACCESS read-only
			STATUS current
			DESCRIPTION
				"The current value of the cached UCID for the DSG-CC.
				This object is only valid if saDsgCcCachedUcidValid is true.
				"
			::= { saDsgCcCachedUcidEntry 2 }

		
		-- 1.3.6.1.4.1.1429.9.1.15.2.1.6
		saDsgCcMacAddrListTable OBJECT-TYPE
			SYNTAX SEQUENCE OF SaDsgCcMacAddrListEntry
			MAX-ACCESS not-accessible
			STATUS current
			DESCRIPTION
				"A list of Basic Mode DSG MAC Addresses for each DSG-CC."
			::= { saDsgCc 6 }

		
		-- 1.3.6.1.4.1.1429.9.1.15.2.1.6.1
		saDsgCcMacAddrListEntry OBJECT-TYPE
			SYNTAX SaDsgCcMacAddrListEntry
			MAX-ACCESS not-accessible
			STATUS current
			DESCRIPTION
				"An entry in the table."
			INDEX { saDsgCcIndex, saDsgCcMacAddrListIndex }
			::= { saDsgCcMacAddrListTable 1 }

		
		SaDsgCcMacAddrListEntry ::=
			SEQUENCE { 
				saDsgCcMacAddrListIndex
					Integer32,
				saDsgCcMacAddrListAddr
					PhysAddress
			 }

		-- 1.3.6.1.4.1.1429.9.1.15.2.1.6.1.1
		saDsgCcMacAddrListIndex OBJECT-TYPE
			SYNTAX Integer32 (1..2147483647)
			MAX-ACCESS read-only
			STATUS current
			DESCRIPTION
				"A unique value for each entry in the list of Basic Mode DSG MAC Addresses for the DSG-CC."
			::= { saDsgCcMacAddrListEntry 1 }

		
		-- 1.3.6.1.4.1.1429.9.1.15.2.1.6.1.2
		saDsgCcMacAddrListAddr OBJECT-TYPE
			SYNTAX PhysAddress
			MAX-ACCESS read-only
			STATUS current
			DESCRIPTION
				"A DSG MAC Address used to recognize DSG tunnel data."
			::= { saDsgCcMacAddrListEntry 2 }

		
		-- 1.3.6.1.4.1.1429.9.1.15.3
		saDsgEvents OBJECT-IDENTITY
			STATUS current
			DESCRIPTION 
				"Events associated with the SA-DSG-MIB."
			::= { saDsgMib 3 }

		
		-- 1.3.6.1.4.1.1429.9.1.15.3.0
		saDsgEventsV2 OBJECT-IDENTITY
			STATUS current
			DESCRIPTION 
				"Dummy node under which all events must be defined. 
				This is required for SNMP v1/v2 compatability."
			::= { saDsgEvents 0 }

		
	
	END

--
-- SA-DSG-MIB.mib
--
