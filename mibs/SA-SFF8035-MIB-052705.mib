--
-- SA-SFF8035-MIB.mib
-- MIB generated by MG-SOFT Visual MIB Builder Version 4.0 Build 349
-- Friday, May 27, 2005 at 10:59:36
--

	SA-SFF8035-MIB DEFINITIONS ::= BEGIN
 
		IMPORTS
			saSff8035Mib			
				FROM SA-DBDSGEN-MIB			
			saModules			
				FROM SCIATL-COMMON-MIB			
			OBJECT-GROUP			
				FROM SNMPv2-CONF			
			Integer32, OBJECT-TYPE, MODULE-IDENTITY, OBJECT-IDENTITY			
				FROM SNMPv2-SMI;
	
	
-- Scientific-Atlanta Proprietary Information
-- 
-- Copyright 2005 Scientific-Atlanta, Inc.
-- 
-- All rights reserved.
-- 
--  
-- 
-- Unauthorized copying and distribution are prohibited.  
-- 
-- No part of this MIB may be reprinted, reproduced or utilized
-- 
-- in any form or by any electronic, mechanical, or other means, now known or
-- 
-- hereafter invented, including photocopying and recording, or using any
-- 
-- information storage and retrieval system, without permission in writing
-- 
-- from Scientific-Atlanta, Inc.
-- 
		-- 1.3.6.1.4.1.1429.7.1.29
		saSff8035MibModule MODULE-IDENTITY 
			LAST-UPDATED "200505271100Z"		-- May 27, 2005 at 11:00 GMT
			ORGANIZATION 
				"Scientific-Atlanta, Inc."
			CONTACT-INFO 
				"DBDS Software Engineering & Architecture
				Scientific-Atlanta
				5030 Sugarloaf Parkway
				Lawrencville, GA 30044
				"
			DESCRIPTION 
				"The Scientific-Atlanta MIB module for tracking SFF-8035 related information.
				
				
				PRELIMINARY FOR REVIEW PURPOSES ONLY"
			::= { saModules 29 }

		
	
--
-- Node definitions
--
	
		-- 1.3.6.1.4.1.1429.9.1.17.1
		saSff8035Conf OBJECT-IDENTITY
			STATUS current
			DESCRIPTION 
				"Conformance"
			::= { saSff8035Mib 1 }

		
		-- 1.3.6.1.4.1.1429.9.1.17.1.1
		saSff8035Groups OBJECT-IDENTITY
			STATUS current
			DESCRIPTION 
				"Object groups for the SA-SFF8035-MIB"
			::= { saSff8035Conf 1 }

		
		-- 1.3.6.1.4.1.1429.9.1.17.1.1.1
		saSmartStatusTableGroup OBJECT-GROUP
			OBJECTS { saSmartStatusExecStatus, saSmartStatusCmdErrCode, saSmartStatusStatus, saSmartStatusHrDeviceIndex }
			STATUS current
			DESCRIPTION 
				"Group for saSmartStatusTable"
			::= { saSff8035Groups 1 }

		
		-- 1.3.6.1.4.1.1429.9.1.17.1.1.2
		saSmartAttrTableGroup OBJECT-GROUP
			OBJECTS { saSmartAttrDeviceAtrribute }
			STATUS current
			DESCRIPTION 
				"Group for saSmartAttrTable"
			::= { saSff8035Groups 2 }

		
		-- 1.3.6.1.4.1.1429.9.1.17.1.2
		saSff8035Compls OBJECT-IDENTITY
			STATUS current
			DESCRIPTION 
				"Compliance descriptions for the SA-SFF8035-MIB."
			::= { saSff8035Conf 2 }

		
		-- 1.3.6.1.4.1.1429.9.1.17.2
		saSFF8035Objs OBJECT-IDENTITY
			STATUS current
			DESCRIPTION 
				"The objects of the SA-SFF8035-MIB module."
			::= { saSff8035Mib 2 }

		
		-- 1.3.6.1.4.1.1429.9.1.17.2.1
		saSmartStatus OBJECT-IDENTITY
			STATUS current
			DESCRIPTION 
				"SMART Status Information"
			::= { saSFF8035Objs 1 }

		
		-- 1.3.6.1.4.1.1429.9.1.17.2.1.1
		saSmartStatusTable OBJECT-TYPE
			SYNTAX SEQUENCE OF SaSmartStatusEntry
			MAX-ACCESS not-accessible
			STATUS current
			DESCRIPTION
				"This table represents the SMART status information available
				from the host. An entry exists for each SMART drive reported by
				the host.
				
				If an entry has a corresponding entry in the hrDeviceTable from
				HOST-RESOURCES-MIB, then saSmartHrDeviceIndex provides the index
				of the related entry in hrDeviceTable."
			REFERENCE
				"SFF-8035i"
			::= { saSmartStatus 1 }

		
		-- 1.3.6.1.4.1.1429.9.1.17.2.1.1.1
		saSmartStatusEntry OBJECT-TYPE
			SYNTAX SaSmartStatusEntry
			MAX-ACCESS not-accessible
			STATUS current
			DESCRIPTION
				"A row in the table."
			INDEX { saSmartStatusDriveIndex }
			::= { saSmartStatusTable 1 }

		
		SaSmartStatusEntry ::=
			SEQUENCE { 
				saSmartStatusDriveIndex
					Integer32,
				saSmartStatusExecStatus
					INTEGER,
				saSmartStatusCmdErrCode
					OCTET STRING,
				saSmartStatusStatus
					INTEGER,
				saSmartStatusHrDeviceIndex
					Integer32
			 }

		-- 1.3.6.1.4.1.1429.9.1.17.2.1.1.1.1
		saSmartStatusDriveIndex OBJECT-TYPE
			SYNTAX Integer32 (1..2147483647)
			MAX-ACCESS not-accessible
			STATUS current
			DESCRIPTION
				"Description."
			REFERENCE
				"A unique value for each entry in the table.
				"
			::= { saSmartStatusEntry 1 }

		
		-- 1.3.6.1.4.1.1429.9.1.17.2.1.1.1.2
		saSmartStatusExecStatus OBJECT-TYPE
			SYNTAX INTEGER
				{
				notRun(0),
				completeCmdOk(1),
				completeCmdErr(2),
				incompleteTimedOut(3)
				}
			MAX-ACCESS read-only
			STATUS current
			DESCRIPTION
				"SMART test execution status:
				notRun          = The test was not run 
				completeCmdOk   = Completed with no command error
				completedCmdErr = Completed with command error; see smartStatusCmdErrCode 
				incompleteTimedOut = The test started but did not finish because it timed out
				"
			::= { saSmartStatusEntry 2 }

		
		-- 1.3.6.1.4.1.1429.9.1.17.2.1.1.1.3
		saSmartStatusCmdErrCode OBJECT-TYPE
			SYNTAX OCTET STRING
			MAX-ACCESS read-only
			STATUS current
			DESCRIPTION
				"If failure reported by saSmartStatusExecStatus, then this reports
				a more detailed failure code reflecting the ATA/ATAPI-5 defined
				error register.
				
				If no error is being reported, this value is zero (0)."
			REFERENCE
				"ATA/ATAPI-5 Specification - Error Register"
			::= { saSmartStatusEntry 3 }

		
		-- 1.3.6.1.4.1.1429.9.1.17.2.1.1.1.4
		saSmartStatusStatus OBJECT-TYPE
			SYNTAX INTEGER
				{
				notReported(0),
				thresholdOk(1),
				thresholdExceeded(2)
				}
			MAX-ACCESS read-only
			STATUS current
			DESCRIPTION
				"SMART Status - The results of testing if any thresholds have been exceeded.
				
				notReported = Not reported because either the test was not run, or 
				the device does not support this feature
				
				thresholdOk = Thresholds Not Exceeded
				
				thresholdExceeded = Threshold Exceeded
				
				"
			REFERENCE
				"SFF-8035 SMART STATUS Definition"
			::= { saSmartStatusEntry 4 }

		
		-- 1.3.6.1.4.1.1429.9.1.17.2.1.1.1.5
		saSmartStatusHrDeviceIndex OBJECT-TYPE
			SYNTAX Integer32
			MAX-ACCESS read-only
			STATUS current
			DESCRIPTION
				"Index value of the corresponding entry in hrDeviceTable
				 in HOST-RESOURCES-MIB; 0 otherwise"
			::= { saSmartStatusEntry 5 }

		
		-- 1.3.6.1.4.1.1429.9.1.17.2.1.2
		saSmartAttrTable OBJECT-TYPE
			SYNTAX SEQUENCE OF SaSmartAttrEntry
			MAX-ACCESS not-accessible
			STATUS current
			DESCRIPTION
				"SMART Device Attributes Table - This table provides the SMART 
				attributes from each drive. For each supported drive, one or
				more attributes are listed in this table.
				
				For example, the second attribute of the first 
				drive is accessed as saSmartAttrDeviceAttribute.1.2"
			::= { saSmartStatus 2 }

		
		-- 1.3.6.1.4.1.1429.9.1.17.2.1.2.1
		saSmartAttrEntry OBJECT-TYPE
			SYNTAX SaSmartAttrEntry
			MAX-ACCESS not-accessible
			STATUS current
			DESCRIPTION
				"A row in the table."
			INDEX { saSmartStatusDriveIndex, saSmartAttrIndex }
			::= { saSmartAttrTable 1 }

		
		SaSmartAttrEntry ::=
			SEQUENCE { 
				saSmartAttrIndex
					Integer32,
				saSmartAttrDeviceAtrribute
					OCTET STRING
			 }

		-- 1.3.6.1.4.1.1429.9.1.17.2.1.2.1.1
		saSmartAttrIndex OBJECT-TYPE
			SYNTAX Integer32 (1..2147483647)
			MAX-ACCESS not-accessible
			STATUS current
			DESCRIPTION
				"Unique value for each SMART device attribute reported 
				for a drive. For example, the second attribute of the first 
				drive is accessed as saSmartAttrDeviceAttribute.1.2"
			::= { saSmartAttrEntry 1 }

		
		-- 1.3.6.1.4.1.1429.9.1.17.2.1.2.1.2
		saSmartAttrDeviceAtrribute OBJECT-TYPE
			SYNTAX OCTET STRING
			MAX-ACCESS read-only
			STATUS current
			DESCRIPTION
				"SMART attribute as defined in SFF-8035 
				Individual Attribute Data Structure section."
			::= { saSmartAttrEntry 2 }

		
	
	END

--
-- SA-SFF8035-MIB.mib
--
