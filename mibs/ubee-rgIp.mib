UBEE-RG-IP-MIB DEFINITIONS ::= BEGIN
IMPORTS
   MODULE-IDENTITY,
   OBJECT-TYPE,
   Integer32,
   Unsigned32,
   TimeTicks,
   NOTIFICATION-TYPE    FROM SNMPv2-SMI

   TruthValue,
   PhysAddress,
   DateAndTime,
   TimeStamp,
   RowStatus                FROM SNMPv2-TC

   SnmpAdminString      FROM SNMP-FRAMEWORK-MIB

   OBJECT-GROUP,
   MODULE-COMPLIANCE,
   NOTIFICATION-GROUP   FROM SNMPv2-CONF

   ifIndex                  FROM IF-MIB
    
   InetAddressType,
   InetAddress          FROM INET-ADDRESS-MIB
                                       
   residentialGatewayMgmt     FROM UBEE-RG-MGMT-MIB
   IANAifType           FROM IANAifType-MIB;     

   
rgIpMib MODULE-IDENTITY
    LAST-UPDATED "201104280000Z"
    ORGANIZATION "Ubee Interactive Corporation"
    CONTACT-INFO
        "	Ubee Interactive Global Headquarters

        Postal: 6F-9, No.38, Taiyuan St.
        		Jhubei City Hsinchu County 302
        		Taiwan, R.O.C.

           Tel: +886-3-560-0010

        E-mail: asupport@ubeeinteractive.com"
    DESCRIPTION
        "Ubee cabledata private MIB for programming Rg Network interface information"
   	::= { residentialGatewayMgmt 2 }


-- Textual Conventions

rgIpRipSettings       OBJECT IDENTIFIER ::= { rgIpMib 2 }
rgIpLanAddr           OBJECT IDENTIFIER ::= { rgIpMib 3 }
rgIpDnsServer         OBJECT IDENTIFIER ::= { rgIpMib 4 }
rgIpDhcpServer        OBJECT IDENTIFIER ::= { rgIpMib 5 }
rgIpRoute             OBJECT IDENTIFIER ::= { rgIpMib 6 }
rgIpNat               OBJECT IDENTIFIER ::= { rgIpMib 7 }


--
-- The following group describes the base objects in the rgIP Mib.
-- These are device based parameters. 
--

rgIpNetworkSettingsCommit  	OBJECT-TYPE
    SYNTAX      		TruthValue
    MAX-ACCESS  		read-write
    STATUS      		current
    DESCRIPTION
        "Commit all the parameters that have been entered within the Rg Ip MIB."
    ::= { rgIpMib 1 }

--
-- The following group describes the rip setting objects in the rgIp MIB.
-- These are device based parameters. 
--
rgIpRipEnable	OBJECT-TYPE
	SYNTAX			TruthValue
	MAX-ACCESS		read-write
	STATUS			current
	DESCRIPTION
	    "Setting this object to true(1) causes the device to enable RIP"
	::= { rgIpRipSettings 1 }

rgIpRipMd5AuthEnable	OBJECT-TYPE
	SYNTAX			TruthValue
	MAX-ACCESS		read-write
	STATUS			current
	DESCRIPTION
	    "Setting this object to true(1) causes the device to enable md5 auth"
	::= { rgIpRipSettings 2 }

rgIpRipMd5KeyId	OBJECT-TYPE
	SYNTAX			INTEGER
	MAX-ACCESS		read-write
	STATUS			current
	DESCRIPTION
	    "Key ID value for Md5 auth"
	::= { rgIpRipSettings 3 }

rgIpRipMd5KeyValue OBJECT-TYPE
	SYNTAX 			OCTET STRING (SIZE(0|20))
	MAX-ACCESS 		read-write
	STATUS 			current
	DESCRIPTION
        "MD5 Key Value"
	::= { rgIpRipSettings 4 }

rgIpRipInterval	OBJECT-TYPE
	SYNTAX			INTEGER  (10..600)
	MAX-ACCESS		read-write
	STATUS			current
	DESCRIPTION
	    "Interval in Seconds for the Rip Reporting interval."
	::= { rgIpRipSettings 5 }

  rgIpRipDestIpAddressType OBJECT-TYPE
      SYNTAX      InetAddressType
      MAX-ACCESS  read-write
      STATUS      current
      DESCRIPTION
          "The type of IP address assigned to the rgIpRipDestIpAddress."
      DEFVAL { ipv4 }
      ::= { rgIpRipSettings 6 }
  
  rgIpRipDestIpAddress OBJECT-TYPE
      SYNTAX      InetAddress
      MAX-ACCESS  read-write
      STATUS      current
      DESCRIPTION 
          "Defines the Rip unicast destinatino IP Address for Rip Reports. If this value
		  returns 0.0.0.0 then this is the default multicast IP address in the RFC (224.0.0.9)"
      ::= { rgIpRipSettings 7 }
  


rgIpPrimaryLANIfBridgeMode  	OBJECT-TYPE
    SYNTAX      		TruthValue
    MAX-ACCESS  		read-write
    STATUS      		current
    DESCRIPTION
        "Sets the Primary LAN Interfaces into bridged mode (true), or out of bridged mode (false). 
		This includes BOTH Wifi cards if applicable.
		This object does not need the rgIpNetworkSettingsCommit and will cause the device to reset if 
		changing from FALSE to TRUE, or TRUE to FALSE."
    ::= { rgIpMib 8 }

  --
  --	The following group defines the RG LAN Address definitions 
  --
  --==============================================================
  --
  --  		rgIpLanAddrTable Table
  --
  --  The rgIpLanAddrTable contains a list of the CPE devices that have  
  --  connected to the device from the LAN. The list has the necessary 
  --  information that ties the IP address to the ClientID and HostName. 
  --  Also the create and expire time of the lease that was given to the 
  --  LAN CPE device.
  --
  --==============================================================
  
  rgIpLanAddrTable OBJECT-TYPE
      SYNTAX      SEQUENCE OF RgIpLanAddrBaseEntry
      MAX-ACCESS  not-accessible
      STATUS      current
      DESCRIPTION
              "Table of CPE devices on the LAN"
      ::= { rgIpLanAddr 1 }
  
  rgIpLanAddrBaseEntry OBJECT-TYPE
      SYNTAX      RgIpLanAddrBaseEntry
      MAX-ACCESS  not-accessible
      STATUS      current
      DESCRIPTION
              "Entry value containing the information of the CPE device on the LAN"
      INDEX { ifIndex, rgIpLanAddrIpType, rgIpLanAddrIp  }
      ::= { rgIpLanAddrTable 1 }
  
  RgIpLanAddrBaseEntry ::= 
      SEQUENCE { 
  			  rgIpLanAddrIpType 			InetAddressType,
  			  rgIpLanAddrIp 				InetAddress,
              rgIpLanAddrClientID      		OCTET STRING,
  			  rgIpLanAddrLeaseCreateTime    DateAndTime,
  	          rgIpLanAddrLeaseExpireTime    DateAndTime,
  			  rgIpLanAddrHostName           SnmpAdminString
               }
  
  rgIpLanAddrIpType OBJECT-TYPE
      SYNTAX      InetAddressType
      MAX-ACCESS  not-accessible
      STATUS      current
      DESCRIPTION
          "The type of IP address assigned to the LAN IP Device
  	    in the LAN-Trans Realm."
      ::= { rgIpLanAddrBaseEntry 1 }
  
  rgIpLanAddrIp OBJECT-TYPE
      SYNTAX      InetAddress
      MAX-ACCESS  not-accessible
      STATUS      current
      DESCRIPTION 
          "The address assigned to the LAN IP Device."
      ::= { rgIpLanAddrBaseEntry 2 }
  
  rgIpLanAddrClientID OBJECT-TYPE
	  SYNTAX OCTET STRING (SIZE (1..80))
      MAX-ACCESS  read-only
      STATUS      current
      DESCRIPTION
          "The client's (i.e., LAN IP Device's) hardware address as
          indicated in the chaddr field of its DHCP REQUEST message.
          There is a one-to-one relationship between the hardware
          address and the LAN IP Device. "
      ::= { rgIpLanAddrBaseEntry 3 }
  
  rgIpLanAddrLeaseCreateTime OBJECT-TYPE
      SYNTAX      DateAndTime
      MAX-ACCESS  read-only
      STATUS      current
      DESCRIPTION
          "This is the date and time when the LAN IP lease was
		  created."
      ::= { rgIpLanAddrBaseEntry 4 }
  
  rgIpLanAddrLeaseExpireTime OBJECT-TYPE
      SYNTAX      DateAndTime
      MAX-ACCESS  read-only
      STATUS      current
      DESCRIPTION
          "This is the date and time when the LAN IP address lease
          will expire."
      ::= { rgIpLanAddrBaseEntry 5 }
  
  rgIpLanAddrHostName OBJECT-TYPE
      SYNTAX      SnmpAdminString(SIZE(0..80))
      MAX-ACCESS  read-only
      STATUS      current
      DESCRIPTION
         "This is the Host Name of the LAN IP address, based on DCHP 
         option 12."
      ::= { rgIpLanAddrBaseEntry 6 }

  rgIpDnsServerTable		OBJECT-TYPE
     	SYNTAX SEQUENCE OF RgIpDnsServerEntry
     	MAX-ACCESS 		not-accessible
      STATUS          current
     	DESCRIPTION
        	"This table contains the information for the DNS entries."
     	::= { rgIpDnsServer 1 }
  
  
  rgIpDnsServerEntry      OBJECT-TYPE
      SYNTAX         		RgIpDnsServerEntry
      MAX-ACCESS         	not-accessible
      STATUS  			current
      DESCRIPTION             
          "The table that describes the DNS PROFILE."
      INDEX { rgIpDnsServerOrder } 
      ::= { rgIpDnsServerTable 1 }
  
  RgIpDnsServerEntry ::= SEQUENCE {
      rgIpDnsServerOrder           INTEGER,
      rgIpDnsServerIpType          InetAddressType,
      rgIpDnsServerIp              InetAddress,
      rgIpDnsServerRowStatus 	   RowStatus
  
      }
  
  rgIpDnsServerOrder 	OBJECT-TYPE
      SYNTAX       		INTEGER (1..65535)
      MAX-ACCESS      	not-accessible
      STATUS      		current
      	DESCRIPTION             
              "Integer index into the rg IP DNS table"
      	::= { rgIpDnsServerEntry 1 }
  
  rgIpDnsServerIpType OBJECT-TYPE
      SYNTAX InetAddressType
      MAX-ACCESS read-create
      STATUS current
      DESCRIPTION
          "The type of InetAddress for rgIpDnsServerIp."
      DEFVAL { ipv4 }
      ::= { rgIpDnsServerEntry 2 }
  
  rgIpDnsServerIp OBJECT-TYPE
      SYNTAX InetAddress
      MAX-ACCESS read-create
      STATUS current
      DESCRIPTION
          "The DNS IP address  ."
      ::= { rgIpDnsServerEntry 3 }
  
  rgIpDnsServerRowStatus OBJECT-TYPE
      SYNTAX RowStatus
      MAX-ACCESS read-create
      STATUS current
      DESCRIPTION
          "The RowStatus interlock for the creation and deletion
          of a rgIpDnsServerTable entry. Any writable
          object in each row of the rgIpDnsServerTable
          can be modified at any time while the row is active(1)."
      ::= { rgIpDnsServerEntry 4}
  
  
  
  
  rgIpDhcpServerTable OBJECT-TYPE
      SYNTAX      SEQUENCE OF RgIpDhcpServerEntry
      MAX-ACCESS  not-accessible
      STATUS      current
      DESCRIPTION
              "Table contains DHCP information for a specific Network."
      ::= { rgIpDhcpServer 1 }
  
  rgIpDhcpServerEntry OBJECT-TYPE
      SYNTAX      RgIpDhcpServerEntry
      MAX-ACCESS  not-accessible
      STATUS      current
      DESCRIPTION
              "Entry value containing all necessary information to create
			  a DHCP pool for a Network"
      INDEX { ifIndex}
      ::= { rgIpDhcpServerTable 1 }
  
  RgIpDhcpServerEntry ::= 
      SEQUENCE { 
  			  rgIpDhcpServerLanPoolStartType 		InetAddressType,
  			  rgIpDhcpServerLanPoolStart 			InetAddress,
  			  rgIpDhcpServerLanPoolEndType 			InetAddressType,
  			  rgIpDhcpServerLanPoolEnd 				InetAddress,
                rgIpDhcpServerLeaseTime      			Unsigned32,
  			  rgIpDhcpServerRowStatus    			RowStatus
               }
  
  rgIpDhcpServerLanPoolStartType OBJECT-TYPE
      SYNTAX      InetAddressType
      MAX-ACCESS  read-create
      STATUS      current
      DESCRIPTION
          "Ip Address Type of the Start of the Network Pool."
      DEFVAL { ipv4 }
      ::= { rgIpDhcpServerEntry 1 }
  
  rgIpDhcpServerLanPoolStart OBJECT-TYPE
      SYNTAX      InetAddress
      MAX-ACCESS  read-create
      STATUS      current
      DESCRIPTION 
  		"Ip Address of the Start of the Network Pool."
      ::= { rgIpDhcpServerEntry 2 }
  
  rgIpDhcpServerLanPoolEndType OBJECT-TYPE
      SYNTAX      InetAddressType
      MAX-ACCESS  read-create
      STATUS      current
      DESCRIPTION
          "Ip Address Type of the End of the Network Pool."
      DEFVAL { ipv4 }
      ::= { rgIpDhcpServerEntry 3 }
  
  rgIpDhcpServerLanPoolEnd OBJECT-TYPE
      SYNTAX      InetAddress
      MAX-ACCESS  read-create
      STATUS      current
      DESCRIPTION 
  		"Ip Address of the End of the Network Pool."
      ::= { rgIpDhcpServerEntry 4 }
  
  
  rgIpDhcpServerLeaseTime OBJECT-TYPE
      SYNTAX      Unsigned32 (1..4294967295)
      UNITS       "seconds"
      MAX-ACCESS  read-create
      STATUS      current
      DESCRIPTION
              "Lease Time for the Network Pool"
      DEFVAL { 3600 }
      ::= { rgIpDhcpServerEntry 5 }
  
  rgIpDhcpServerRowStatus OBJECT-TYPE
      SYNTAX RowStatus
      MAX-ACCESS read-create
      STATUS current
      DESCRIPTION
          "The RowStatus interlock for the creation and deletion
          can be modified at any time while the row is active(1)."
      ::= { rgIpDhcpServerEntry 6}
  
  
  
  
  
  rgIpRouteTable OBJECT-TYPE
      SYNTAX      SEQUENCE OF RgIpRouteEntry
      MAX-ACCESS  not-accessible
      STATUS      current
      DESCRIPTION
              "Table containing information for the Network	definition."
      ::= { rgIpRoute 1 }
  
  rgIpRouteEntry OBJECT-TYPE
      SYNTAX      RgIpRouteEntry
      MAX-ACCESS  not-accessible
      STATUS      current
      DESCRIPTION
              "Entry containing all the information about the Network definition."
      INDEX { ifIndex}
      ::= { rgIpRouteTable 1 }
  
  RgIpRouteEntry ::= 
      SEQUENCE { 
  			  rgIpRouteMode 					INTEGER,
  			  rgIpRouteNetworkNumberType 		InetAddressType,
  			  rgIpRouteNetworkNumber 		InetAddress,
  			  rgIpRouteSubnetMaskType 		InetAddressType,
  			  rgIpRouteSubnetMask 			InetAddress,
  			  rgIpRouteGatewayIpType 		InetAddressType,
  			  rgIpRouteGatewayIp 			InetAddress,
                          rgIpRouteTypeOfService      		INTEGER,
                          rgIpRouteFirewallEnable      		TruthValue,
  			  rgIpRouteRowStatus    		RowStatus,
                          rgIpRouteUpnpIgdEnable      		TruthValue
               }
  
  rgIpRouteMode OBJECT-TYPE
      SYNTAX	INTEGER {
      	napt(1),        -- NAT with Port Translation Mode
      	bridged (2),    -- Passthrough/Bridging Mode
        routeddhcp(3),  -- routed_dhcp
        routedstatic(4) -- routed_static
      }
      MAX-ACCESS  read-create
      STATUS      current
      DESCRIPTION
  			"The specifies the Type of network that is being defined."
      DEFVAL { napt }
      ::= { rgIpRouteEntry 1 }
  
  rgIpRouteNetworkNumberType OBJECT-TYPE
      SYNTAX      InetAddressType
      MAX-ACCESS  read-create
      STATUS      current
      DESCRIPTION
          "Ip Address Type of the Network Number for a specific Network."
      DEFVAL { ipv4 }
      ::= { rgIpRouteEntry 2 }
  
  rgIpRouteNetworkNumber OBJECT-TYPE
      SYNTAX      InetAddress
      MAX-ACCESS  read-create
      STATUS      current
      DESCRIPTION 
          "Ip Address of the Network Number for a specific Network."
      ::= { rgIpRouteEntry 3 }
  
  rgIpRouteSubnetMaskType OBJECT-TYPE
      SYNTAX      InetAddressType
      MAX-ACCESS  read-create
      STATUS      current
      DESCRIPTION
          "Ip Address Type of the SubnetMask for a specific Network."
      DEFVAL { ipv4 }
      ::= { rgIpRouteEntry 4 }
  
  rgIpRouteSubnetMask OBJECT-TYPE
      SYNTAX      InetAddress
      MAX-ACCESS  read-create
      STATUS      current
      DESCRIPTION 
          "Ip Address of the SubnetMask for a specific Network."
      ::= { rgIpRouteEntry 5 }
  
  
  rgIpRouteGatewayIpType OBJECT-TYPE
      SYNTAX      InetAddressType
      MAX-ACCESS  read-create
      STATUS      current
      DESCRIPTION
          "Ip Address Type of the Gateway for a specific Network."
      DEFVAL { ipv4 }
      ::= { rgIpRouteEntry 6 }
  
  rgIpRouteGatewayIp OBJECT-TYPE
      SYNTAX      InetAddress
      MAX-ACCESS  read-create
      STATUS      current
      DESCRIPTION 
          "Ip Address of the Gateway for a specific Network."
      ::= { rgIpRouteEntry 7 }
  
  
  rgIpRouteTypeOfService OBJECT-TYPE
      SYNTAX      INTEGER (0..255)
      MAX-ACCESS  read-create
      STATUS      current
      DESCRIPTION
              "Byte value to be used for the override TOS field for all IP packets on this BSS. 
			  A value of 0 means dont override, where any other value will be used to override."
      DEFVAL { 0 }
      ::= { rgIpRouteEntry 8 }
  
  rgIpRouteFirewallEnable OBJECT-TYPE
      SYNTAX      TruthValue 
      MAX-ACCESS  read-create
      STATUS      current
      DESCRIPTION
              "Enabled/Disable Firewall for specific Network"
      DEFVAL { true }
      ::= { rgIpRouteEntry 9 }

  rgIpRouteRowStatus OBJECT-TYPE
      SYNTAX RowStatus
      MAX-ACCESS read-create
      STATUS current
      DESCRIPTION
          "The RowStatus interlock for the creation and deletion
          can be modified at any time while the row is active(1)."
      ::= { rgIpRouteEntry 10}


  rgIpRouteUpnpIgdEnable OBJECT-TYPE
      SYNTAX      TruthValue 
      MAX-ACCESS  read-create
      STATUS      current
      DESCRIPTION
              "Enabled/Disable UPnP (IGD) for specific Network"
      DEFVAL { true }
      ::= { rgIpRouteEntry 11 }
  
  

rgIpNatAlgsEnabled OBJECT-TYPE
    SYNTAX      BITS {
                        rsvp(0),       -- US/DS; IP 46
                        ftp(1),        -- US/DS; TCP 21
                        tftp(2),       -- US; UDP 17
                        kerb88(3),     -- US; UDP 88
                        netBiosDgm(4), -- US; UDP 138
                        ike(5),        -- US/DS; UDP 500
                        rtsp(6),       -- US/DS; TCP 554
                        kerb1293(7),   -- US; UDP 1293
                        h225(8),       -- US/DS; TCP 1720
                        pptp(9),       -- US/DS; TCP 1723
                        msn(10),       -- US/DS; TCP 1863
                        sip(11),       -- US; UDP 5060
                        icq(12),       -- US; TCP 5190
                        irc666x(13),   -- US; TCP 6661..6669
                        icqTalk(14),   -- US/DS; UDP 6701
                        net2Phone(15), -- US/DS; UDP 6801
                        irc7000(16),   -- US; TCP 7000
                        irc8000(17)    -- US; TCP 8000
                     }
    MAX-ACCESS  read-write
    STATUS      current
    DESCRIPTION
         "Specifies which NAT application layer gateway supplements are enabled
          on this device.  The default value for this object is for all ALG's
          to be enabled."
    ::= { rgIpNat 1 }

END
