--
-- SA-DBDSPROD-MIB.my
-- MIB generated by MG-SOFT Visual MIB Builder Version 4.0 Build 349
-- Monday, September 12, 2005 at 10:05:31
--

--  SA-DBDSPROD-MIB.my
-- MIB generated by MG-SOFT Visual MIB Builder Version 4.0 Build 349
-- Thursday, January 27, 2005 at 12:03:38
-- 
--  SA-DBDSPROD-MIB.my
-- MIB generated by MG-SOFT Visual MIB Builder Version 4.0 Build 349
-- Tuesday, October 28, 2003 at 10:21:33
-- 
-- Revision 1 : DBDS Products MIB Module Initial
-- Date: Wednesday, May 07, 2003 at 14:23:14
-- Comment:
-- Initial revision.
-- 
-- Revision 2 : Revision 2
-- Date: Monday, October 27, 2003 at 14:03:52
-- Comment:
-- Added the following nodes to
-- saDBDS: saDncsMib, saDncsNmiMib,
-- and saXdcMib.
-- 

	SA-DBDSPROD-MIB DEFINITIONS ::= BEGIN
 
		IMPORTS
			saDBDS, saModules			
				FROM SCIATL-COMMON-MIB			
			MODULE-IDENTITY, OBJECT-IDENTITY			
				FROM SNMPv2-SMI;
	
	
--   1.3.6.1.4.1.1429.7.1.1
-- October 27, 2003 at 14:03 GMT
-- October 27, 2003 at 14:03 GMT
-- May 07, 2003 at 14:23 GMT
-- 1.3.6.1.4.1.1429.7.1.1
-- October 27, 2003 at 14:03 GMT
-- May 07, 2003 at 14:23 GMT
-- October 27, 2003 at 14:03 GMT
		-- 1.3.6.1.4.1.1429.7.1.1
		saDbdsProdMibModule MODULE-IDENTITY 
			LAST-UPDATED "200310271403Z"		-- October 27, 2003 at 14:03 GMT
			ORGANIZATION 
				"Scientific-Atlanta"
			CONTACT-INFO 
				"Ray Killick"
			DESCRIPTION 
				"The initial revision of this MIB module."
			REVISION "200310271403Z"		-- October 27, 2003 at 14:03 GMT
			DESCRIPTION 
				"Added the following nodes to
				saDBDS: saDncsMib, saDncsNmiMib,
				and saXdcMib."
			REVISION "200305071423Z"		-- May 07, 2003 at 14:23 GMT
			DESCRIPTION 
				"Initial revision."
			::= { saModules 1 }

		
	
--
-- Node definitions
--
	
--  Node definitions
-- 
-- Node definitions
-- 
-- 1.3.6.1.4.1.1429.5.1.1
-- 1.3.6.1.4.1.1429.5.1.1
		-- 1.3.6.1.4.1.1429.5.1.1
		saDhctMib OBJECT-IDENTITY
			STATUS current
			DESCRIPTION 
				"The DHCT MIB node."
			::= { saDBDS 1 }

		
--   1.3.6.1.4.1.1429.5.1.2
-- 1.3.6.1.4.1.1429.5.1.2
		-- 1.3.6.1.4.1.1429.5.1.2
		saMrdvrAppMib OBJECT-IDENTITY
			STATUS current
			DESCRIPTION 
				"The MR-DVR Application MIB node."
			::= { saDBDS 2 }

		
--   1.3.6.1.4.1.1429.5.1.3
-- 1.3.6.1.4.1.1429.5.1.3
		-- 1.3.6.1.4.1.1429.5.1.3
		saDncsMib OBJECT-IDENTITY
			STATUS current
			DESCRIPTION 
				"The new DNCS MIB node."
			::= { saDBDS 3 }

		
--   1.3.6.1.4.1.1429.5.1.4
-- 1.3.6.1.4.1.1429.5.1.4
		-- 1.3.6.1.4.1.1429.5.1.4
		saDncsNmiMib OBJECT-IDENTITY
			STATUS current
			DESCRIPTION 
				"The NMI MIB node. The NMI resides on the DNCS
				and translates events (alarms and provisioning
				events) into traps that can be understood by
				an SNMP NMS application."
			::= { saDBDS 4 }

		
--   1.3.6.1.4.1.1429.5.1.5
-- 1.3.6.1.4.1.1429.5.1.5
		-- 1.3.6.1.4.1.1429.5.1.5
		saXdcMib OBJECT-IDENTITY
			STATUS current
			DESCRIPTION 
				"The XDC MIB node."
			::= { saDBDS 5 }

		
--  1.3.6.1.4.1.1429.5.1.6
		-- 1.3.6.1.4.1.1429.5.1.6
		saPcgMib OBJECT-IDENTITY
			STATUS current
			DESCRIPTION 
				"The PowerKEY CAS Gateway (PCG) node."
			::= { saDBDS 6 }

		
--  1.3.6.1.4.1.1429.5.1.7
		-- 1.3.6.1.4.1.1429.5.1.7
		saNetcryptBeMib OBJECT-IDENTITY
			STATUS current
			DESCRIPTION 
				"The Netcrypt Bulk Encryptor (BE) MIB node."
			::= { saDBDS 7 }

		
--  1.3.6.1.4.1.1429.5.1.8
		-- 1.3.6.1.4.1.1429.5.1.8
		saPointerMib OBJECT-IDENTITY
			STATUS current
			DESCRIPTION 
				"The SciCare Pointer product MIB node."
			::= { saDBDS 8 }

		
-- The S-A MIB for the TestRunner application.
		-- 1.3.6.1.4.1.1429.5.1.9
		saNagraLoaderMib OBJECT-IDENTITY
			STATUS current
			DESCRIPTION 
				"The Nagra Loader MIB."
			::= { saDBDS 9 }

		
		-- 1.3.6.1.4.1.1429.5.1.10
		saDhct OBJECT-IDENTITY
			STATUS current
			DESCRIPTION 
				"Additional MIB modules for the DHCT are 
				placed under this node."
			::= { saDBDS 10 }

		
		-- 1.3.6.1.4.1.1429.5.1.10.1
		saHddTestMib OBJECT-IDENTITY
			STATUS current
			DESCRIPTION 
				"The S-A MIB for certain hard drive tests."
			::= { saDhct 1 }

		
		-- 1.3.6.1.4.1.1429.5.1.10.2
		saScreenCleanMib OBJECT-IDENTITY
			STATUS current
			DESCRIPTION 
				"The S-A MIB for Screen and Clean."
			::= { saDhct 2 }

		
		-- 1.3.6.1.4.1.1429.5.1.10.3
		saJclExtStbCmMib OBJECT-IDENTITY
			STATUS current
			DESCRIPTION 
				"The S-A MIB for the JCL STB CM Extended MIB"
			::= { saDhct 3 }

		
		-- 1.3.6.1.4.1.1429.5.1.11
		saSdbServerMib OBJECT-IDENTITY
			STATUS current
			DESCRIPTION 
				"The SDB Server MIB node."
			::= { saDBDS 11 }

		
		-- 1.3.6.1.4.1.1429.5.1.12
		saRetrieverMib OBJECT-IDENTITY
			STATUS current
			DESCRIPTION 
				"The MIB node for the S-A Retriever product."
			::= { saDBDS 12 }

		
	
	END

--
-- SA-DBDSPROD-MIB.my
--
