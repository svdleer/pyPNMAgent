--
-- SA-QAMTX-MIB.mib
-- MIB generated by MG-SOFT Visual MIB Builder Version 4.0 Build 349
-- Wednesday, February 02, 2005 at 11:00:37
--

	SA-QAMTX-MIB DEFINITIONS ::= BEGIN
 
		IMPORTS
			saQamtxMib			
				FROM SA-DBDSGEN-MIB			
			saModules			
				FROM SCIATL-COMMON-MIB			
			OBJECT-GROUP, MODULE-COMPLIANCE			
				FROM SNMPv2-CONF			
			Integer32, Unsigned32, OBJECT-TYPE, MODULE-IDENTITY, OBJECT-IDENTITY			
				FROM SNMPv2-SMI			
			TruthValue			
				FROM SNMPv2-TC;
	
	
		-- 1.3.6.1.4.1.1429.7.1.1
		saQamtxMibModule MODULE-IDENTITY 
			LAST-UPDATED "200307221313Z"		-- July 22, 2003 at 13:13 GMT
			ORGANIZATION 
				"Scientific-Atlanta"
			CONTACT-INFO 
				"DBDS Software Engineering & Architecture
				Scientific-Atlanta
				5030 Sugarloaf Parkway
				Lawrencville, GA 30044
				"
			DESCRIPTION 
				"The Scientific-Atlanta MIB module for QAM Transmitters and Receivers.
				
				This MIB module Copyright 2003-2005 Scientific-Atlanta
				
				
				THIS VERSION IS PRELIMINARY FOR REVIEW PURPOSES ONLY!
				"
			REVISION "200502021059Z"		-- February 02, 2005 at 10:59 GMT
			DESCRIPTION 
				"Updated with additional QAM Receiver objects."
			::= { saModules 1 }

		
	
--
-- Type definitions
--
	
		ModulationModeType ::= INTEGER
			{
			analog(0),
			qam16(1),
			qam32(2),
			qam64(3),
			qam128(4),
			qam256(5),
			invalid(6)
			}

		SaQamDisplayIndicator ::= INTEGER
			{
			na(1),
			red(2),
			amber(3),
			green(4)
			}

	
	
--
-- Node definitions
--
	
		-- 1.3.6.1.4.1.1429.9.1.8.1
		saQamtxConf OBJECT-IDENTITY
			STATUS current
			DESCRIPTION 
				"Conformance"
			::= { saQamtxMib 1 }

		
		-- 1.3.6.1.4.1.1429.9.1.8.1.1
		saQamtxGroups OBJECT-IDENTITY
			STATUS current
			DESCRIPTION 
				"Object Groups of the SA-QAMTX-MIB"
			::= { saQamtxConf 1 }

		
		-- 1.3.6.1.4.1.1429.9.1.8.1.1.1
		saQamtxOperationalGroup OBJECT-GROUP
			OBJECTS { saQamtxOpIndex, saQamtxOpEnabled, saQamtxOpPowerLevel, saQamtxOpFrequency, saQamtxOpModulationMode, 
				saQamtxOpSymbolRate }
			STATUS current
			DESCRIPTION 
				"A group of operational parameters for a QAM transmitter."
			::= { saQamtxGroups 1 }

		
		-- 1.3.6.1.4.1.1429.9.1.8.1.2
		saQamtxCompls OBJECT-IDENTITY
			STATUS current
			DESCRIPTION 
				"Compliances of the SA-QAMTX-MIB"
			::= { saQamtxConf 2 }

		
		-- 1.3.6.1.4.1.1429.9.1.8.1.2.1
		saQamtxBasicCompliance MODULE-COMPLIANCE
			STATUS current
			DESCRIPTION 
				"All conforming implementation should provide this basic
				level of functionality."
			MODULE -- this module
				MANDATORY-GROUPS { saQamtxOperationalGroup }
			::= { saQamtxCompls 1 }

		
		-- 1.3.6.1.4.1.1429.9.1.8.2
		saQamtxObjs OBJECT-IDENTITY
			STATUS current
			DESCRIPTION 
				"The MIB Objects defined for the SA-QAMTX-MIB module."
			::= { saQamtxMib 2 }

		
		-- 1.3.6.1.4.1.1429.9.1.8.2.1
		saQamtxOperational OBJECT-IDENTITY
			STATUS current
			DESCRIPTION 
				"Current transmitter parameters being used."
			::= { saQamtxObjs 1 }

		
		-- 1.3.6.1.4.1.1429.9.1.8.2.1.1
		saQamtxOpTable OBJECT-TYPE
			SYNTAX SEQUENCE OF SaQamtxOpEntry
			MAX-ACCESS not-accessible
			STATUS current
			DESCRIPTION
				"A table of values currently being used by QAM transmitters on this station."
			::= { saQamtxOperational 1 }

		
		-- 1.3.6.1.4.1.1429.9.1.8.2.1.1.1
		saQamtxOpEntry OBJECT-TYPE
			SYNTAX SaQamtxOpEntry
			MAX-ACCESS not-accessible
			STATUS current
			DESCRIPTION
				"An entry in the table. Each QAM transmitter resource must be represented in the table. 
				The value of saQamtxOpIndex must always correspond to the same resource."
			INDEX { saQamtxOpIndex }
			::= { saQamtxOpTable 1 }

		
		SaQamtxOpEntry ::=
			SEQUENCE { 
				saQamtxOpIndex
					Unsigned32,
				saQamtxOpEnabled
					INTEGER,
				saQamtxOpPowerLevel
					Integer32,
				saQamtxOpFrequency
					Unsigned32,
				saQamtxOpModulationMode
					ModulationModeType,
				saQamtxOpSymbolRate
					Unsigned32
			 }

		-- 1.3.6.1.4.1.1429.9.1.8.2.1.1.1.1
		saQamtxOpIndex OBJECT-TYPE
			SYNTAX Unsigned32
			MAX-ACCESS read-only
			STATUS current
			DESCRIPTION
				"A unique value for each entry in the table. Corresponds to the
				transmitter resource being utilized. This must always correspond to
				the same transmitter resource."
			::= { saQamtxOpEntry 1 }

		
		-- 1.3.6.1.4.1.1429.9.1.8.2.1.1.1.2
		saQamtxOpEnabled OBJECT-TYPE
			SYNTAX INTEGER
				{
				off(0),
				on(1)
				}
			MAX-ACCESS read-only
			STATUS current
			DESCRIPTION
				"Indicates the stat of this QAM transmitter.
				
				off = the transmitter is not enabled
				on  = the transmitter is enabled"
			::= { saQamtxOpEntry 2 }

		
		-- 1.3.6.1.4.1.1429.9.1.8.2.1.1.1.3
		saQamtxOpPowerLevel OBJECT-TYPE
			SYNTAX Integer32
			UNITS "dBmv"
			MAX-ACCESS read-only
			STATUS current
			DESCRIPTION
				"The current output power level in dBmv units.
				"
			::= { saQamtxOpEntry 3 }

		
		-- 1.3.6.1.4.1.1429.9.1.8.2.1.1.1.4
		saQamtxOpFrequency OBJECT-TYPE
			SYNTAX Unsigned32
			UNITS "Hz"
			MAX-ACCESS read-only
			STATUS current
			DESCRIPTION
				"The current Frequency in Hz.
				"
			::= { saQamtxOpEntry 4 }

		
		-- 1.3.6.1.4.1.1429.9.1.8.2.1.1.1.5
		saQamtxOpModulationMode OBJECT-TYPE
			SYNTAX ModulationModeType
			MAX-ACCESS read-only
			STATUS current
			DESCRIPTION
				"The current modulation mode.
				"
			::= { saQamtxOpEntry 5 }

		
		-- 1.3.6.1.4.1.1429.9.1.8.2.1.1.1.6
		saQamtxOpSymbolRate OBJECT-TYPE
			SYNTAX Unsigned32
			UNITS "Hz"
			MAX-ACCESS read-only
			STATUS current
			DESCRIPTION
				"The output symbol rate expressed in Hz.
				"
			::= { saQamtxOpEntry 6 }

		
		-- 1.3.6.1.4.1.1429.9.1.8.2.2
		saQamrxOperational OBJECT-IDENTITY
			STATUS current
			DESCRIPTION 
				"Current receiver parameters being used."
			::= { saQamtxObjs 2 }

		
		-- 1.3.6.1.4.1.1429.9.1.8.2.2.1
		saQamrxOpTable OBJECT-TYPE
			SYNTAX SEQUENCE OF SaQamrxOpEntry
			MAX-ACCESS not-accessible
			STATUS current
			DESCRIPTION
				"A table of values currently being used by QAM 
				receivers on this station."
			::= { saQamrxOperational 1 }

		
		-- 1.3.6.1.4.1.1429.9.1.8.2.2.1.1
		saQamrxOpEntry OBJECT-TYPE
			SYNTAX SaQamrxOpEntry
			MAX-ACCESS not-accessible
			STATUS current
			DESCRIPTION
				"An entry in the table."
			INDEX { saQamrxOpIndex }
			::= { saQamrxOpTable 1 }

		
		SaQamrxOpEntry ::=
			SEQUENCE { 
				saQamrxOpIndex
					Integer32,
				saQamrxOpLocked
					TruthValue,
				saQamrxOpFrequency
					Unsigned32,
				saQamrxOpModulationMode
					ModulationModeType
			 }

		-- 1.3.6.1.4.1.1429.9.1.8.2.2.1.1.1
		saQamrxOpIndex OBJECT-TYPE
			SYNTAX Integer32 (1..2147483647)
			MAX-ACCESS not-accessible
			STATUS current
			DESCRIPTION
				"A unique value for each entry in the table. Corresponds to the receiver resource being utilized. This must always correspond to the same transmitter resource.
				
				If this device is represented in hrDeviceTable, then 
				the saQamRxOpIndex must match hrDeviceIndex
				for the coresponding entry.
				"
			::= { saQamrxOpEntry 1 }

		
		-- 1.3.6.1.4.1.1429.9.1.8.2.2.1.1.2
		saQamrxOpLocked OBJECT-TYPE
			SYNTAX TruthValue
			MAX-ACCESS read-only
			STATUS current
			DESCRIPTION
				"Indicates if the receiver is locked to a frequency."
			::= { saQamrxOpEntry 2 }

		
		-- 1.3.6.1.4.1.1429.9.1.8.2.2.1.1.3
		saQamrxOpFrequency OBJECT-TYPE
			SYNTAX Unsigned32
			MAX-ACCESS read-only
			STATUS current
			DESCRIPTION
				"The frequency (in HZ) to which the receiver is locked
				or is attempting to acquire. If the tuner is not in use, 
				then this value is zero."
			::= { saQamrxOpEntry 3 }

		
		-- 1.3.6.1.4.1.1429.9.1.8.2.2.1.1.4
		saQamrxOpModulationMode OBJECT-TYPE
			SYNTAX ModulationModeType
			MAX-ACCESS read-only
			STATUS current
			DESCRIPTION
				"The modulation mode currently being used by the
				receiver."
			::= { saQamrxOpEntry 4 }

		
		-- 1.3.6.1.4.1.1429.9.1.8.2.2.2
		saQamrxOpBerTable OBJECT-TYPE
			SYNTAX SEQUENCE OF SaQamrxOpBerEntry
			MAX-ACCESS not-accessible
			STATUS current
			DESCRIPTION
				"A table of Pre-Corrected Bit Error Rates for QAM Receivers."
			::= { saQamrxOperational 2 }

		
		-- 1.3.6.1.4.1.1429.9.1.8.2.2.2.1
		saQamrxOpBerEntry OBJECT-TYPE
			SYNTAX SaQamrxOpBerEntry
			MAX-ACCESS not-accessible
			STATUS current
			DESCRIPTION
				"A row in the table."
			AUGMENTS { saQamrxOpEntry }
			::= { saQamrxOpBerTable 1 }

		
		SaQamrxOpBerEntry ::=
			SEQUENCE { 
				saQamrxOpBerBer
					Integer32
			 }

		-- 1.3.6.1.4.1.1429.9.1.8.2.2.2.1.1
		saQamrxOpBerBer OBJECT-TYPE
			SYNTAX Integer32
			MAX-ACCESS read-only
			STATUS current
			DESCRIPTION
				"Pre-Corrected Bit Error Rate x 10^(-12)"
			::= { saQamrxOpBerEntry 1 }

		
		-- 1.3.6.1.4.1.1429.9.1.8.2.2.3
		saQamrxStatsPreCorBytesTable OBJECT-TYPE
			SYNTAX SEQUENCE OF SaQamrxStatsPreCorBytesEntry
			MAX-ACCESS not-accessible
			STATUS current
			DESCRIPTION
				"The number of pre-corrected bytes received since
				lock was achieved."
			::= { saQamrxOperational 3 }

		
		-- 1.3.6.1.4.1.1429.9.1.8.2.2.3.1
		saQamrxStatsPreCorBytesEntry OBJECT-TYPE
			SYNTAX SaQamrxStatsPreCorBytesEntry
			MAX-ACCESS not-accessible
			STATUS current
			DESCRIPTION
				"A row in the table."
			AUGMENTS { saQamrxOpEntry }
			::= { saQamrxStatsPreCorBytesTable 1 }

		
		SaQamrxStatsPreCorBytesEntry ::=
			SEQUENCE { 
				saQamrxStatsPreCorBytes
					Integer32
			 }

		-- 1.3.6.1.4.1.1429.9.1.8.2.2.3.1.1
		saQamrxStatsPreCorBytes OBJECT-TYPE
			SYNTAX Integer32
			MAX-ACCESS read-only
			STATUS current
			DESCRIPTION
				"The number of pre-corrected bytes received since
				lock was achieved."
			::= { saQamrxStatsPreCorBytesEntry 1 }

		
		-- 1.3.6.1.4.1.1429.9.1.8.2.2.4
		saQamrxStatsCorrectedBitsTable OBJECT-TYPE
			SYNTAX SEQUENCE OF SaQamrxStatsCorrectedBitsEntry
			MAX-ACCESS not-accessible
			STATUS current
			DESCRIPTION
				"The number of post-corrected bits received since
				lock was achieved."
			::= { saQamrxOperational 4 }

		
		-- 1.3.6.1.4.1.1429.9.1.8.2.2.4.1
		saQamrxStatsCorrectedBitsEntry OBJECT-TYPE
			SYNTAX SaQamrxStatsCorrectedBitsEntry
			MAX-ACCESS not-accessible
			STATUS current
			DESCRIPTION
				"A row in the table."
			AUGMENTS { saQamrxOpEntry }
			::= { saQamrxStatsCorrectedBitsTable 1 }

		
		SaQamrxStatsCorrectedBitsEntry ::=
			SEQUENCE { 
				saQamrxStatsCorrectedBits
					Integer32
			 }

		-- 1.3.6.1.4.1.1429.9.1.8.2.2.4.1.1
		saQamrxStatsCorrectedBits OBJECT-TYPE
			SYNTAX Integer32
			MAX-ACCESS read-only
			STATUS current
			DESCRIPTION
				"The number of post-corrected bits received since
				lock was achieved."
			::= { saQamrxStatsCorrectedBitsEntry 1 }

		
		-- 1.3.6.1.4.1.1429.9.1.8.2.2.5
		saQamrxStatsCorrectedBlocksTable OBJECT-TYPE
			SYNTAX SEQUENCE OF SaQamrxStatsCorrectedBlocksEntry
			MAX-ACCESS not-accessible
			STATUS current
			DESCRIPTION
				"The number of post-corrected blocks received since
				lock was achieved."
			::= { saQamrxOperational 5 }

		
		-- 1.3.6.1.4.1.1429.9.1.8.2.2.5.1
		saQamrxStatsCorrectedBlocksEntry OBJECT-TYPE
			SYNTAX SaQamrxStatsCorrectedBlocksEntry
			MAX-ACCESS not-accessible
			STATUS current
			DESCRIPTION
				"A row in the table."
			AUGMENTS { saQamrxOpEntry }
			::= { saQamrxStatsCorrectedBlocksTable 1 }

		
		SaQamrxStatsCorrectedBlocksEntry ::=
			SEQUENCE { 
				saQamrxStatsCorrectedBlocks
					Integer32
			 }

		-- 1.3.6.1.4.1.1429.9.1.8.2.2.5.1.1
		saQamrxStatsCorrectedBlocks OBJECT-TYPE
			SYNTAX Integer32
			MAX-ACCESS read-only
			STATUS current
			DESCRIPTION
				"The number of post-corrected blocks received since
				lock was achieved."
			::= { saQamrxStatsCorrectedBlocksEntry 1 }

		
		-- 1.3.6.1.4.1.1429.9.1.8.2.2.6
		saQamrxOpSymbolRateTable OBJECT-TYPE
			SYNTAX SEQUENCE OF SaQamrxOpSymbolRateEntry
			MAX-ACCESS not-accessible
			STATUS current
			DESCRIPTION
				"The symbol rate."
			::= { saQamrxOperational 6 }

		
		-- 1.3.6.1.4.1.1429.9.1.8.2.2.6.1
		saQamrxOpSymbolRateEntry OBJECT-TYPE
			SYNTAX SaQamrxOpSymbolRateEntry
			MAX-ACCESS not-accessible
			STATUS current
			DESCRIPTION
				"A row in the table."
			AUGMENTS { saQamrxOpEntry }
			::= { saQamrxOpSymbolRateTable 1 }

		
		SaQamrxOpSymbolRateEntry ::=
			SEQUENCE { 
				saQamrxOpSymbolRate
					Integer32
			 }

		-- 1.3.6.1.4.1.1429.9.1.8.2.2.6.1.1
		saQamrxOpSymbolRate OBJECT-TYPE
			SYNTAX Integer32
			UNITS "symbols/second"
			MAX-ACCESS read-only
			STATUS current
			DESCRIPTION
				"The symbol rate."
			::= { saQamrxOpSymbolRateEntry 1 }

		
		-- 1.3.6.1.4.1.1429.9.1.8.2.2.7
		saQamrxOpAgcIfTable OBJECT-TYPE
			SYNTAX SEQUENCE OF SaQamrxOpAgcIfEntry
			MAX-ACCESS not-accessible
			STATUS current
			DESCRIPTION
				"The AGC-IF."
			::= { saQamrxOperational 7 }

		
		-- 1.3.6.1.4.1.1429.9.1.8.2.2.7.1
		saQamrxOpAgcIfEntry OBJECT-TYPE
			SYNTAX SaQamrxOpAgcIfEntry
			MAX-ACCESS not-accessible
			STATUS current
			DESCRIPTION
				"A row in the table."
			AUGMENTS { saQamrxOpEntry }
			::= { saQamrxOpAgcIfTable 1 }

		
		SaQamrxOpAgcIfEntry ::=
			SEQUENCE { 
				saQamrxOpAgcIf
					Integer32
			 }

		-- 1.3.6.1.4.1.1429.9.1.8.2.2.7.1.1
		saQamrxOpAgcIf OBJECT-TYPE
			SYNTAX Integer32
			UNITS "percent"
			MAX-ACCESS read-only
			STATUS current
			DESCRIPTION
				"The AGC-IF."
			::= { saQamrxOpAgcIfEntry 1 }

		
		-- 1.3.6.1.4.1.1429.9.1.8.2.2.8
		saQamrxStatsRcvdPowerTable OBJECT-TYPE
			SYNTAX SEQUENCE OF SaQamrxStatsRcvdPowerEntry
			MAX-ACCESS not-accessible
			STATUS current
			DESCRIPTION
				"Received Power."
			::= { saQamrxOperational 8 }

		
		-- 1.3.6.1.4.1.1429.9.1.8.2.2.8.1
		saQamrxStatsRcvdPowerEntry OBJECT-TYPE
			SYNTAX SaQamrxStatsRcvdPowerEntry
			MAX-ACCESS not-accessible
			STATUS current
			DESCRIPTION
				"A row in the table."
			AUGMENTS { saQamrxOpEntry }
			::= { saQamrxStatsRcvdPowerTable 1 }

		
		SaQamrxStatsRcvdPowerEntry ::=
			SEQUENCE { 
				saQamrxStatsRcvdPower
					Integer32
			 }

		-- 1.3.6.1.4.1.1429.9.1.8.2.2.8.1.1
		saQamrxStatsRcvdPower OBJECT-TYPE
			SYNTAX Integer32
			MAX-ACCESS read-only
			STATUS current
			DESCRIPTION
				"Received Power."
			::= { saQamrxStatsRcvdPowerEntry 1 }

		
		-- 1.3.6.1.4.1.1429.9.1.8.2.2.9
		saQamrxStatsMerTable OBJECT-TYPE
			SYNTAX SEQUENCE OF SaQamrxStatsMerEntry
			MAX-ACCESS not-accessible
			STATUS current
			DESCRIPTION
				"Estimated MER."
			::= { saQamrxOperational 9 }

		
		-- 1.3.6.1.4.1.1429.9.1.8.2.2.9.1
		saQamrxStatsMerEntry OBJECT-TYPE
			SYNTAX SaQamrxStatsMerEntry
			MAX-ACCESS not-accessible
			STATUS current
			DESCRIPTION
				"A row in the table."
			AUGMENTS { saQamrxOpEntry }
			::= { saQamrxStatsMerTable 1 }

		
		SaQamrxStatsMerEntry ::=
			SEQUENCE { 
				saQamrxStatsMer
					Integer32,
				saQamrxStatsMerIndicator
					SaQamDisplayIndicator
			 }

		-- 1.3.6.1.4.1.1429.9.1.8.2.2.9.1.1
		saQamrxStatsMer OBJECT-TYPE
			SYNTAX Integer32
			UNITS "0.1 dB"
			MAX-ACCESS read-only
			STATUS current
			DESCRIPTION
				"Estimated MER."
			::= { saQamrxStatsMerEntry 1 }

		
		-- 1.3.6.1.4.1.1429.9.1.8.2.2.9.1.2
		saQamrxStatsMerIndicator OBJECT-TYPE
			SYNTAX SaQamDisplayIndicator
			MAX-ACCESS read-only
			STATUS current
			DESCRIPTION
				"Estmated MER Indicator."
			::= { saQamrxStatsMerEntry 2 }

		
		-- 1.3.6.1.4.1.1429.9.1.8.2.2.10
		saQamrxStatsPostCorBerTable OBJECT-TYPE
			SYNTAX SEQUENCE OF SaQamrxStatsPostCorBerEntry
			MAX-ACCESS not-accessible
			STATUS current
			DESCRIPTION
				"A table of Post-Corrected Bit Error Rates for QAM Receivers."
			::= { saQamrxOperational 10 }

		
		-- 1.3.6.1.4.1.1429.9.1.8.2.2.10.1
		saQamrxStatsPostCorBerEntry OBJECT-TYPE
			SYNTAX SaQamrxStatsPostCorBerEntry
			MAX-ACCESS not-accessible
			STATUS current
			DESCRIPTION
				"A row in the table."
			AUGMENTS { saQamrxOpEntry }
			::= { saQamrxStatsPostCorBerTable 1 }

		
		SaQamrxStatsPostCorBerEntry ::=
			SEQUENCE { 
				saQamrxStatsPostCorBer
					Integer32,
				saQamrxStatsPostCorBerIndicator
					SaQamDisplayIndicator
			 }

		-- 1.3.6.1.4.1.1429.9.1.8.2.2.10.1.1
		saQamrxStatsPostCorBer OBJECT-TYPE
			SYNTAX Integer32
			MAX-ACCESS read-only
			STATUS current
			DESCRIPTION
				"Post-corrected Bit Error Rate x 10^(-12)"
			::= { saQamrxStatsPostCorBerEntry 1 }

		
		-- 1.3.6.1.4.1.1429.9.1.8.2.2.10.1.2
		saQamrxStatsPostCorBerIndicator OBJECT-TYPE
			SYNTAX SaQamDisplayIndicator
			MAX-ACCESS read-only
			STATUS current
			DESCRIPTION
				"Post-Corrected BER Indicator"
			::= { saQamrxStatsPostCorBerEntry 2 }

		
		-- 1.3.6.1.4.1.1429.9.1.8.2.2.11
		saQamrxOpBerIndicatorTable OBJECT-TYPE
			SYNTAX SEQUENCE OF SaQamrxOpBerIndicatorEntry
			MAX-ACCESS not-accessible
			STATUS current
			DESCRIPTION
				"A table of Pre-Corrected BER Indicators"
			::= { saQamrxOperational 11 }

		
		-- 1.3.6.1.4.1.1429.9.1.8.2.2.11.1
		saQamrxOpBerIndicatorEntry OBJECT-TYPE
			SYNTAX SaQamrxOpBerIndicatorEntry
			MAX-ACCESS not-accessible
			STATUS current
			DESCRIPTION
				"A row in the table."
			AUGMENTS { saQamrxOpEntry }
			::= { saQamrxOpBerIndicatorTable 1 }

		
		SaQamrxOpBerIndicatorEntry ::=
			SEQUENCE { 
				saQamrxOpBerIndicator
					SaQamDisplayIndicator
			 }

		-- 1.3.6.1.4.1.1429.9.1.8.2.2.11.1.1
		saQamrxOpBerIndicator OBJECT-TYPE
			SYNTAX SaQamDisplayIndicator
			MAX-ACCESS read-only
			STATUS current
			DESCRIPTION
				"Pre-Corrected BER Indicator"
			::= { saQamrxOpBerIndicatorEntry 1 }

		
		-- 1.3.6.1.4.1.1429.9.1.8.2.2.12
		saQamrxOpCarrierOffsetTable OBJECT-TYPE
			SYNTAX SEQUENCE OF SaQamrxOpCarrierOffsetEntry
			MAX-ACCESS not-accessible
			STATUS current
			DESCRIPTION
				"The Carrier Offset."
			::= { saQamrxOperational 12 }

		
		-- 1.3.6.1.4.1.1429.9.1.8.2.2.12.1
		saQamrxOpCarrierOffsetEntry OBJECT-TYPE
			SYNTAX SaQamrxOpCarrierOffsetEntry
			MAX-ACCESS not-accessible
			STATUS current
			DESCRIPTION
				"A row in the table."
			AUGMENTS { saQamrxOpEntry }
			::= { saQamrxOpCarrierOffsetTable 1 }

		
		SaQamrxOpCarrierOffsetEntry ::=
			SEQUENCE { 
				saQamrxOpCarrierOffset
					Integer32
			 }

		-- 1.3.6.1.4.1.1429.9.1.8.2.2.12.1.1
		saQamrxOpCarrierOffset OBJECT-TYPE
			SYNTAX Integer32
			UNITS "Hertz"
			MAX-ACCESS read-only
			STATUS current
			DESCRIPTION
				"The carrier offset"
			::= { saQamrxOpCarrierOffsetEntry 1 }

		
		-- 1.3.6.1.4.1.1429.9.1.8.3
		saQamtxEvents OBJECT-IDENTITY
			STATUS current
			DESCRIPTION 
				"Events associated with the SA-QAMTX-MIB."
			::= { saQamtxMib 3 }

		
		-- 1.3.6.1.4.1.1429.9.1.8.3.0
		saQamtxEventsV2 OBJECT-IDENTITY
			STATUS current
			DESCRIPTION 
				"Dummy node under which all events must be defined. 
				This is required for SNMP v1/v2 compatability."
			::= { saQamtxEvents 0 }

		
	
	END

--
-- SA-QAMTX-MIB.mib
--
