--
-- AM-CMROOT-MIB.my
-- MIB generated by MG-SOFT Visual MIB Builder Version 2.1 Build 199
-- Friday, October 22, 2010 at 17:31:16
--

	AM-CMROOT-MIB DEFINITIONS ::= BEGIN

		IMPORTS 
			enterprises			
				FROM RFC1155-SMI;
	
	
--
-- Node definitions
--
	
		am OBJECT IDENTIFIER ::= { enterprises 2183 }
		
		products OBJECT IDENTIFIER ::= { am 1 }
		
		amCableModem OBJECT IDENTIFIER ::= { products 1 }
		
		amCMCommon OBJECT IDENTIFIER ::= { amCableModem 1 }
		
		amAlphaCM OBJECT IDENTIFIER ::= { amCableModem 2 }
		
		amBpiManager OBJECT IDENTIFIER ::= { amCableModem 3 }
		
	
	END

--
-- AM-CMROOT-MIB.my
--
