NLS-BBNSTATE-MIB DEFINITIONS ::= BEGIN

-- Version 1.1
-- LAST-UPDATED "970624 1000Z"
-- ORGANIZATION "General Instrument Corporation"
-- CONTACT-INFO "Scott Sellers
--		 Copyright 1997, General Instrument Corporation
--		 GI Communications Division 
--		 2200 Byberry Road
--		 Hatboro, PA 19040
--	
--		 Tel: +1 215 773 8525
--		 Fax: +1 215 773 8536
--		 Email: ssellers@gic.gi.com"
--
-- DESCRIPTION  "The MIB module for the NLS BBN common state objects.
--		 The MIB Tree for is shown below."
--	

    IMPORTS
    
        bbnState        FROM NLS-BBNIDENT-MIB
        OBJECT-TYPE     FROM RFC-1212;
                

--  MIB Tree
--
--  The following diagram defining the objects in this MIB is for
--  reference purposes only.
--
--    nlsbbn
--        |
--        +..bbnIdent
--        |
--        .
--        .
--        .
--        |
--        |         
--        +..bbnState
--        |    |
--        |    +..unitAdministrativeState
--        |    |
--        |    +..unitOperationalState
--        |    |
--        |    +..unitUsageState
--        |    |
--        |    +..unitProceduralStatus
--        |    |
--        |    +..unitAlarmStatus
--        |    |
--        |    +..unitAvailabilityStatus
--        |    |
--        |    +..unitControlStatus
--        |    |
--        |    +..unitStandbyStatus
--        |    |
--        |    +..unitUnknownStatus
--        |    |
--        |    +..unitTestStatus
--        |
--        +..bbnTraps
--        |
--        |

-- The State/Status Group.
--
--   State/status refers to the state/status of the computing/network
--   element on which the SNMP agent is running. If the agent is a
--   proxy agent, the state group does not relate to the state/status
--   of the elements being proxied. The state/status group also does
--   not directly relate to the state/status of the components of the
--   network element such as CCAs.
--
--   The state/status uf individual unit components, CCAs, etc. and
--   the state/status of proxied elements should be defined using
--   subsets of the variables/values defined here.
--
--   The state group is mandatory for all SNMP managed GI network
--   elements although different agents may shoose to support
--   only a subset of the group as best suited for the application.
--   If a state variable is not supported by an agent, the agent
--   will return the error code noSuchName. However, the 
--   state group should be the only group defining the state/status
--   of the entire network element being managed. GI defined MIB should
--   avoid using any other variables to define the state of the entire 
--   network element.
-- 
--   Defined state/status variables and values and state transitions
--   correspond to the ITU-T X.700 series standardsare and are
--   as defined in ISO/IEC 10164-2. The defined include:
--
--       - the administrative state
--       - the operational state
--       - the usage state
--       - the procedural status
--       - the alarm status
--       - the availability status
--       - the control status
--       - the standy status
--       - the unknown status

unitAdministrativeState  OBJECT-TYPE
                SYNTAX  INTEGER
                        {
                         locked         (1),
                         unlocked       (2),
                         shuttingDown   (3)
                        }
--      MAX-ACCESS  read-write
--      STATUS      current
                ACCESS  read-write
                STATUS  mandatory
                DESCRIPTION "This state should be always supported.
                     The current Adminsitrative state of the unit is defined
		     in ISO/IEC 10164-2."
                REFERENCE   " -- "
        ::= { bbnState 1 }

unitOperationalState  OBJECT-TYPE
                SYNTAX  INTEGER
                        {
                          enabled    (1),
                          disabled   (2)
                        }
--      MAX-ACCESS  read-only
--      STATUS      current
                ACCESS  read-only
                STATUS  mandatory
                DESCRIPTION "The current Operational state of the unit as
		     defined in ISO/IEC 10164-2"
                REFERENCE   " -- "
        ::= { bbnState 2 }
        
unitUsageState  OBJECT-TYPE
                SYNTAX  INTEGER
                        {
                         idle     (1),
                         active   (2),
                         busy     (3)
                        }
--      MAX-ACCESS  read-only
--      STATUS      current
                ACCESS  read-only
                STATUS  mandatory
                DESCRIPTION "The current Usage state of the unit as defined in
                     ISO/IEC 10164-2"
                REFERENCE   " -- "
        ::= { bbnState 3 }
    
unitProceduralStatus  OBJECT-TYPE
                SYNTAX  INTEGER
                        {
                         initializationRequired   (1),
                         notInitialized           (2),
                         initializing             (3),
                         reporting                (4),
                         terminating              (5),
                         ready                    (6)
                        }
--      MAX-ACCESS  read-write
--      STATUS      current
                ACCESS  read-write
                STATUS  mandatory
                DESCRIPTION "This state should be always supported.
                     This object controls the Procedural status 
                     as defined in ISO/IEC 10164-2 and state-machine"
                REFERENCE   " -- "
        ::= { bbnState 4 }        

unitAlarmStatus  OBJECT-TYPE
                SYNTAX  INTEGER
                        {
                         ok                 (1),
                         undetermined       (2),
                         warning            (3),
                         minor              (4),
                         major              (5),
                         critical           (6)
                        }
--      MAX-ACCESS  read-write
--      STATUS      current
                ACCESS  read-write
                STATUS  mandatory
                DESCRIPTION "This state should be always supported.
                     This object defines the Alarm status
                     as defined in ISO/IEC 10164-2 and state-machine"
                REFERENCE   " -- "
        ::= { bbnState 5 }        

unitAvailabilityStatus  OBJECT-TYPE
                SYNTAX  INTEGER
                        {
                         inTest         (1),
                         failed         (2),
                         powerOff       (3),
                         offLine        (4),
                         offDuty        (5),
                         dependency     (6),
                         degraded       (7),
                         notInstalled   (8),
                         logFull        (9),
                         available      (10)
                        }
--      MAX-ACCESS  read-only
--      STATUS      current
                ACCESS  read-only
                STATUS  mandatory
                DESCRIPTION "This object controls the Availability status
                     as defined in ISO/IEC 10164-2 and state-machine"
                REFERENCE   " -- "
        ::= { bbnState 6 }        

unitControlStatus  OBJECT-TYPE
                SYNTAX  INTEGER
                        {
                         subjectToTest    (32767),
                         partLocked       (1),
                         reservedToTest   (2),
                         suspended        (3),
                         free             (4)
                        }
--      MAX-ACCESS  read-write
--      STATUS      current
                ACCESS  read-write
                STATUS  mandatory
                DESCRIPTION "This object controls the Control status
                     as defined in ISO/IEC 10164-2 and state-machine"
                REFERENCE   " -- "
        ::= { bbnState 7 }        

unitStandbyStatus  OBJECT-TYPE
                SYNTAX  INTEGER
                        {
                         hotStandby         (1),
                         coldStandby        (2),
                         providingService   (3)
                        }
--      MAX-ACCESS  read-only
--      STATUS      current
                ACCESS  read-only
                STATUS  mandatory
                DESCRIPTION "This object controls the Standby status
                     as defined in ISO/IEC 10164-2 and state-machine"
                REFERENCE   " -- "
        ::= { bbnState 8 }        

unitUnknownStatus  OBJECT-TYPE
                SYNTAX  INTEGER
                        {
                         true(1),
                         false(2)
                        }
--      MAX-ACCESS  read-write
--      STATUS      current
                ACCESS  read-write
                STATUS  mandatory
                DESCRIPTION "This object defines the unknown status
                     as defined in ISO/IEC 10164-2 and state-machine"
                REFERENCE   " -- "
        ::= { bbnState 9 }        

END
