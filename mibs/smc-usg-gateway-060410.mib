SMC-USG-GATEWAY-MIB DEFINITIONS ::= BEGIN
    IMPORTS
        MODULE-IDENTITY,
        OBJECT-TYPE,
        NOTIFICATION-TYPE,
        Integer32,
        IpAddress,
        enterprises                     FROM SNMPv2-SMI

        InetAddress                     FROM INET-ADDRESS-MIB

        MODULE-COMPLIANCE,
        OBJECT-GROUP                    FROM SNMPv2-CONF

        MacAddress,
        RowStatus,
        TruthValue,
        DisplayString                   FROM SNMPv2-TC;

    smcNetworks    OBJECT IDENTIFIER ::= { enterprises 202 }
    smcCableModem  OBJECT IDENTIFIER ::= { smcNetworks 80  }

smcUsgGateway MODULE-IDENTITY
    LAST-UPDATED "201006041534Z" -- Fri Jun  4 15:34:49 2010
    ORGANIZATION "SMC Networks, Inc."
    CONTACT-INFO
        "Linmei Shu
         SMC Networks Inc
         11940 Jollyville Road STE-220N
         Austin, TX 78759
         USA
         Phone: +1 512 249 9515 ext. 101
         E-mail: linmei.shu@smc.com"
    DESCRIPTION
       "The MIB module to describe the SMC product USG gateway control functions."

    REVISION "201006041534Z"
    DESCRIPTION
        "MIB generated by auto-generator based on templates"

    ::= { smcCableModem 7 }

-- ++++++++++++++++++++++++++++++++++++++++++++++++++++++++++++++

    wrls OBJECT IDENTIFIER ::= { smcUsgGateway 1 }

        wrlsVapTable OBJECT-TYPE
            SYNTAX       SEQUENCE OF WrlsVapEntry
            MAX-ACCESS   not-accessible 
            STATUS       current
            DESCRIPTION 
                "wireless vap table"
            ::= { wrls 1 }

        wrlsVapEntry OBJECT-TYPE
            SYNTAX       WrlsVapEntry
            MAX-ACCESS   not-accessible 
            STATUS       current
            DESCRIPTION 
                "Entry of table wrlsVap"
            INDEX        { wrlsVapIndex }
            ::= { wrlsVapTable 1 }

        WrlsVapEntry ::=
        SEQUENCE {
                wrlsVapIndex                                     Integer32,
                wrlsVapRowStatus                                 RowStatus,
                wrlsVapVapId                                     INTEGER,
                wrlsVapFrequencyBand                             INTEGER,
                wrlsVapAdminStatus                               INTEGER,
                wrlsVapSsidName                                  DisplayString,
                wrlsVapBroadcastSsid                             INTEGER,
                wrlsVapVlanId                                    Integer32,
                wrlsVapBridging                                  INTEGER,
                wrlsVapWmm                                       INTEGER,
                wrlsVapWifi802dot1xKeyrenewal                    Integer32,
                wrlsVapScrty                                     INTEGER,
                wrlsVapScrtyWepLength                            INTEGER,
                wrlsVapScrtyWepLength64WepKey                    DisplayString,
                wrlsVapScrtyWepLength128WepKey                   DisplayString,
                wrlsVapScrtyWpapskTkipWpapsktkipKey              DisplayString,
                wrlsVapScrtyWpapskAesWpapskaesKey                DisplayString,
                wrlsVapScrtyWpa2pskTkipWpa2tkipKey               DisplayString,
                wrlsVapScrtyWpa2pskAesWpa2aesKey                 DisplayString
        }

        wrlsVapIndex OBJECT-TYPE
            SYNTAX       Integer32
            MAX-ACCESS   read-only
            STATUS       current
            DESCRIPTION 
                "Index of wrlsVapEntry."
            ::= { wrlsVapEntry 1 }

        wrlsVapRowStatus OBJECT-TYPE
            SYNTAX       RowStatus
            MAX-ACCESS   read-create
            STATUS       current
            DESCRIPTION 
                "The status of this conceptual row.
                 Set createAndGo(4) or createAndWait(5) to create a row in this table.
                 Set destroy(6) to delete all of the instances associated with an existing
                 conceptual row."
            ::= { wrlsVapEntry 2 }

        wrlsVapVapId OBJECT-TYPE
            SYNTAX       INTEGER {
                hotspot(1),
                public(2),
                subscriber(3)
            }
            MAX-ACCESS   read-create
            STATUS       current
            DESCRIPTION 
                "vap id for configuration update on vap table"
            ::= { wrlsVapEntry 3 }

        wrlsVapFrequencyBand OBJECT-TYPE
            SYNTAX       INTEGER {
                s2dot4G(1),
                s5G(2),
                s2dot4G-5G(3),
                none(4)
            }
            MAX-ACCESS   read-create
            STATUS       current
            DESCRIPTION 
                "configure the activation of frequency band"
            ::= { wrlsVapEntry 4 }

        wrlsVapAdminStatus OBJECT-TYPE
            SYNTAX       INTEGER {
                enable(1),
                disable(2)
            }
            MAX-ACCESS   read-create
            STATUS       current
            DESCRIPTION 
                "configure the activation of a vap"
            ::= { wrlsVapEntry 5 }

        wrlsVapSsidName OBJECT-TYPE
            SYNTAX       DisplayString
            MAX-ACCESS   read-create
            STATUS       current
            DESCRIPTION 
                "wireless network name ssid"
            ::= { wrlsVapEntry 6 }

        wrlsVapBroadcastSsid OBJECT-TYPE
            SYNTAX       INTEGER {
                enable(1),
                disable(2)
            }
            MAX-ACCESS   read-create
            STATUS       current
            DESCRIPTION 
                "configure the hidden capacity of a vap"
            ::= { wrlsVapEntry 7 }

        wrlsVapVlanId OBJECT-TYPE
            SYNTAX       Integer32
            MAX-ACCESS   read-create
            STATUS       current
            DESCRIPTION 
                "configure vlan id for this vap"
            ::= { wrlsVapEntry 8 }

        wrlsVapBridging OBJECT-TYPE
            SYNTAX       INTEGER {
                enable(1),
                disable(2)
            }
            MAX-ACCESS   read-create
            STATUS       current
            DESCRIPTION 
                "configure the bridge mode of a vap"
            ::= { wrlsVapEntry 9 }

        wrlsVapWmm OBJECT-TYPE
            SYNTAX       INTEGER {
                enable(1),
                disable(2)
            }
            MAX-ACCESS   read-create
            STATUS       current
            DESCRIPTION 
                "configure the wmm mode of a vap"
            ::= { wrlsVapEntry 10 }

        wrlsVapWifi802dot1xKeyrenewal OBJECT-TYPE
            SYNTAX       Integer32
            MAX-ACCESS   read-create
            STATUS       current
            DESCRIPTION 
                "wpa key renewal interval, in the range of {0, 3600} sec, where
                 0 means disable"
            ::= { wrlsVapEntry 11 }

        wrlsVapScrty OBJECT-TYPE
            SYNTAX       INTEGER {
                none(1),
                wep(2),
                wpapsk-tkip(3),
                wpapsk-aes(4),
                wpa2psk-tkip(5),
                wpa2psk-aes(6)
            }
            MAX-ACCESS   read-create
            STATUS       current
            DESCRIPTION 
                "set security mode: none/wep/wpapsk_tkip/wpapsk_aes/wpa2psk-tkip/wpa2psk-aes"
            ::= { wrlsVapEntry 12 }

        wrlsVapScrtyWepLength OBJECT-TYPE
            SYNTAX       INTEGER {
                s64(1),
                s128(2)
            }
            MAX-ACCESS   read-create
            STATUS       current
            DESCRIPTION 
                "set wep key length"
            ::= { wrlsVapEntry 13 }

        wrlsVapScrtyWepLength64WepKey OBJECT-TYPE
            SYNTAX       DisplayString
            MAX-ACCESS   read-create
            STATUS       current
            DESCRIPTION 
                "wep key1 value, with default key type: ascii or hex, key length:
                 64bits (5 or 10 chars)"
            ::= { wrlsVapEntry 14 }

        wrlsVapScrtyWepLength128WepKey OBJECT-TYPE
            SYNTAX       DisplayString
            MAX-ACCESS   read-create
            STATUS       current
            DESCRIPTION 
                "wep key1 value, with default key type: ascii or hex, key length:
                 128bits (13 or 26 chars)"
            ::= { wrlsVapEntry 15 }

        wrlsVapScrtyWpapskTkipWpapsktkipKey OBJECT-TYPE
            SYNTAX       DisplayString
            MAX-ACCESS   read-create
            STATUS       current
            DESCRIPTION 
                "wpa pre-shared key value, with key type: ascii or hex, key length
                 {8, 63} or 64"
            ::= { wrlsVapEntry 16 }

        wrlsVapScrtyWpapskAesWpapskaesKey OBJECT-TYPE
            SYNTAX       DisplayString
            MAX-ACCESS   read-create
            STATUS       current
            DESCRIPTION 
                "wpa pre-shared key value, with key type: ascii or hex, key length
                 {8, 63} or 64"
            ::= { wrlsVapEntry 17 }

        wrlsVapScrtyWpa2pskTkipWpa2tkipKey OBJECT-TYPE
            SYNTAX       DisplayString
            MAX-ACCESS   read-create
            STATUS       current
            DESCRIPTION 
                "wpa pre-shared key value, with key type: ascii or hex, key length
                 {8, 63} or 64"
            ::= { wrlsVapEntry 18 }

        wrlsVapScrtyWpa2pskAesWpa2aesKey OBJECT-TYPE
            SYNTAX       DisplayString
            MAX-ACCESS   read-create
            STATUS       current
            DESCRIPTION 
                "wpa pre-shared key value, with key type: ascii or hex, key length
                 {8, 63} or 64"
            ::= { wrlsVapEntry 19 }

        wrlsRadioTable OBJECT-TYPE
            SYNTAX       SEQUENCE OF WrlsRadioEntry
            MAX-ACCESS   not-accessible 
            STATUS       current
            DESCRIPTION 
                "wireless radio submenu, specify radio index, radio mode and auto
                 channel option"
            ::= { wrls 2 }

        wrlsRadioEntry OBJECT-TYPE
            SYNTAX       WrlsRadioEntry
            MAX-ACCESS   not-accessible 
            STATUS       current
            DESCRIPTION 
                "Entry of table wrlsRadio"
            INDEX        { wrlsRadioIndex }
            ::= { wrlsRadioTable 1 }

        WrlsRadioEntry ::=
        SEQUENCE {
                wrlsRadioIndex                                   Integer32,
                wrlsRadioRowStatus                               RowStatus,
                wrlsRadioRadio                                   Integer32,
                wrlsRadioMode                                    INTEGER,
                wrlsRadioAutoChannel                             INTEGER,
                wrlsRadioAutoChannelDsblChannel                  Integer32,
                wrlsRadioThroughputMode                          INTEGER,
                wrlsRadioShortguardInterval                      INTEGER
        }

        wrlsRadioIndex OBJECT-TYPE
            SYNTAX       Integer32
            MAX-ACCESS   read-only
            STATUS       current
            DESCRIPTION 
                "Index of wrlsRadioEntry."
            ::= { wrlsRadioEntry 1 }

        wrlsRadioRowStatus OBJECT-TYPE
            SYNTAX       RowStatus
            MAX-ACCESS   read-create
            STATUS       current
            DESCRIPTION 
                "The status of this conceptual row.
                 Set createAndGo(4) or createAndWait(5) to create a row in this table.
                 Set destroy(6) to delete all of the instances associated with an existing
                 conceptual row."
            ::= { wrlsRadioEntry 2 }

        wrlsRadioRadio OBJECT-TYPE
            SYNTAX       Integer32
            MAX-ACCESS   read-create
            STATUS       current
            DESCRIPTION 
                "radio index - 0 [2.4g] / 1 [5g]"
            ::= { wrlsRadioEntry 3 }

        wrlsRadioMode OBJECT-TYPE
            SYNTAX       INTEGER {
                s11na(1),
                s11n(2),
                s11bgn(3),
                s11ng(4)
            }
            MAX-ACCESS   read-create
            STATUS       current
            DESCRIPTION 
                "select mode type: radio 0 [2.4g] {11ng, 11bgn, 11n}; radio 1
                 [5g] {11na, 11n}"
            ::= { wrlsRadioEntry 4 }

        wrlsRadioAutoChannel OBJECT-TYPE
            SYNTAX       INTEGER {
                enable(1),
                disable(2)
            }
            MAX-ACCESS   read-create
            STATUS       current
            DESCRIPTION 
                "configure the activation of auto channel, if auto channel is
                 off, specify the channel"
            ::= { wrlsRadioEntry 5 }

        wrlsRadioAutoChannelDsblChannel OBJECT-TYPE
            SYNTAX       Integer32
            MAX-ACCESS   read-create
            STATUS       current
            DESCRIPTION 
                "wireless transmit channel 802.11b/g: 1~11  802.11a: 36~165 depends
                 on country region setting"
            ::= { wrlsRadioEntry 6 }

        wrlsRadioThroughputMode OBJECT-TYPE
            SYNTAX       INTEGER {
                ht20(1),
                ht40plus(2),
                ht40minus(3)
            }
            MAX-ACCESS   read-create
            STATUS       current
            DESCRIPTION 
                "configure the high throughput mode"
            ::= { wrlsRadioEntry 7 }

        wrlsRadioShortguardInterval OBJECT-TYPE
            SYNTAX       INTEGER {
                enable(1),
                disable(2)
            }
            MAX-ACCESS   read-create
            STATUS       current
            DESCRIPTION 
                "configure the short guard interval"
            ::= { wrlsRadioEntry 8 }

        wrlsSystem OBJECT IDENTIFIER ::= { wrls 3 }

            wrlsSystemReset OBJECT-TYPE
                SYNTAX       INTEGER {
                    enable(1),
                    disable(2)
                }
                MAX-ACCESS   read-write
                STATUS       current
                DESCRIPTION 
                    "reset wifi router"
                ::= { wrlsSystem 1 }

            wrlsSystemAdminStatus OBJECT-TYPE
                SYNTAX       INTEGER {
                    enable(1),
                    disable(2)
                }
                MAX-ACCESS   read-write
                STATUS       current
                DESCRIPTION 
                    "configure the activation of wifi service"
                ::= { wrlsSystem 2 }

            wrlsSystemRadiusip1 OBJECT-TYPE
                SYNTAX       InetAddress
                MAX-ACCESS   read-write
                STATUS       current
                DESCRIPTION 
                    "configure the ip address of radius server 1"
                ::= { wrlsSystem 3 }

            wrlsSystemRadiusport1 OBJECT-TYPE
                SYNTAX       Integer32
                MAX-ACCESS   read-write
                STATUS       current
                DESCRIPTION 
                    "configure the port number of radius server 1, within {1024, 65535},
                     usually at 1813"
                ::= { wrlsSystem 4 }

            wrlsSystemRadiussecret1 OBJECT-TYPE
                SYNTAX       DisplayString
                MAX-ACCESS   read-write
                STATUS       current
                DESCRIPTION 
                    "configure the secret key passphrase of radius server 1"
                ::= { wrlsSystem 5 }

            wrlsSystemRadiusip2 OBJECT-TYPE
                SYNTAX       InetAddress
                MAX-ACCESS   read-write
                STATUS       current
                DESCRIPTION 
                    "configure the ip address of radius server 2"
                ::= { wrlsSystem 6 }

            wrlsSystemRadiusport2 OBJECT-TYPE
                SYNTAX       Integer32
                MAX-ACCESS   read-write
                STATUS       current
                DESCRIPTION 
                    "configure the port number of radius server 2, within {1024, 65535},
                     usually at 1814"
                ::= { wrlsSystem 7 }

            wrlsSystemRadiussecret2 OBJECT-TYPE
                SYNTAX       DisplayString
                MAX-ACCESS   read-write
                STATUS       current
                DESCRIPTION 
                    "configure the secret key passphrase of radius server 2"
                ::= { wrlsSystem 8 }

            wrlsSystemRestoreWifi OBJECT-TYPE
                SYNTAX       INTEGER {
                    enable(1),
                    disable(2)
                }
                MAX-ACCESS   read-write
                STATUS       current
                DESCRIPTION 
                    "restore vap[home network] to default value"
                ::= { wrlsSystem 9 }

        wrlsShowinfo OBJECT IDENTIFIER ::= { wrls 4 }

            wrlsShowinfoStationTable OBJECT-TYPE
                SYNTAX       SEQUENCE OF WrlsShowinfoStationEntry
                MAX-ACCESS   not-accessible 
                STATUS       current
                DESCRIPTION 
                    "show information on connected station to specified ssid, given
                     vap index"
                ::= { wrlsShowinfo 1 }

            wrlsShowinfoStationEntry OBJECT-TYPE
                SYNTAX       WrlsShowinfoStationEntry
                MAX-ACCESS   not-accessible 
                STATUS       current
                DESCRIPTION 
                    "Entry of table wrlsShowinfoStation"
                INDEX        { wrlsShowinfoStationIndex }
                ::= { wrlsShowinfoStationTable 1 }

            WrlsShowinfoStationEntry ::=
            SEQUENCE {
                    wrlsShowinfoStationIndex                         Integer32,
                    wrlsShowinfoStationVapId                         INTEGER,
                    wrlsShowinfoStationStatus                        DisplayString
            }

            wrlsShowinfoStationIndex OBJECT-TYPE
                SYNTAX       Integer32
                MAX-ACCESS   read-only
                STATUS       current
                DESCRIPTION 
                    "Index of wrlsShowinfoStationEntry."
                ::= { wrlsShowinfoStationEntry 1 }

            wrlsShowinfoStationVapId OBJECT-TYPE
                SYNTAX       INTEGER {
                    home(1),
                    hotspot(2),
                    public(3),
                    subscriber(4)
                }
                MAX-ACCESS   read-only
                STATUS       current
                DESCRIPTION 
                    "vap id for configuration update on vap table"
                ::= { wrlsShowinfoStationEntry 2 }

            wrlsShowinfoStationStatus OBJECT-TYPE
                SYNTAX       DisplayString
                MAX-ACCESS   read-only
                STATUS       current
                DESCRIPTION 
                    "get the list of the connected stations to the specified vap"
                ::= { wrlsShowinfoStationEntry 3 }

            wrlsShowinfoVapTable OBJECT-TYPE
                SYNTAX       SEQUENCE OF WrlsShowinfoVapEntry
                MAX-ACCESS   not-accessible 
                STATUS       current
                DESCRIPTION 
                    "show information on vap, given vap index"
                ::= { wrlsShowinfo 2 }

            wrlsShowinfoVapEntry OBJECT-TYPE
                SYNTAX       WrlsShowinfoVapEntry
                MAX-ACCESS   not-accessible 
                STATUS       current
                DESCRIPTION 
                    "Entry of table wrlsShowinfoVap"
                INDEX        { wrlsShowinfoVapIndex }
                ::= { wrlsShowinfoVapTable 1 }

            WrlsShowinfoVapEntry ::=
            SEQUENCE {
                    wrlsShowinfoVapIndex                             Integer32,
                    wrlsShowinfoVapVapId                             INTEGER,
                    wrlsShowinfoVapClientNum                         DisplayString,
                    wrlsShowinfoVapMacAddr                           DisplayString
            }

            wrlsShowinfoVapIndex OBJECT-TYPE
                SYNTAX       Integer32
                MAX-ACCESS   read-only
                STATUS       current
                DESCRIPTION 
                    "Index of wrlsShowinfoVapEntry."
                ::= { wrlsShowinfoVapEntry 1 }

            wrlsShowinfoVapVapId OBJECT-TYPE
                SYNTAX       INTEGER {
                    home(1),
                    hotspot(2),
                    public(3),
                    subscriber(4)
                }
                MAX-ACCESS   read-only
                STATUS       current
                DESCRIPTION 
                    "vap id for configuration update on vap table"
                ::= { wrlsShowinfoVapEntry 2 }

            wrlsShowinfoVapClientNum OBJECT-TYPE
                SYNTAX       DisplayString
                MAX-ACCESS   read-only
                STATUS       current
                DESCRIPTION 
                    "get the number of connected stations to the specified vap"
                ::= { wrlsShowinfoVapEntry 3 }

            wrlsShowinfoVapMacAddr OBJECT-TYPE
                SYNTAX       DisplayString
                MAX-ACCESS   read-only
                STATUS       current
                DESCRIPTION 
                    "get the corresponding mac address of the specified vap"
                ::= { wrlsShowinfoVapEntry 4 }

            wrlsShowinfoRadioTable OBJECT-TYPE
                SYNTAX       SEQUENCE OF WrlsShowinfoRadioEntry
                MAX-ACCESS   not-accessible 
                STATUS       current
                DESCRIPTION 
                    "show information on wireless network, including supported channels,
                     wide channels, etc"
                ::= { wrlsShowinfo 3 }

            wrlsShowinfoRadioEntry OBJECT-TYPE
                SYNTAX       WrlsShowinfoRadioEntry
                MAX-ACCESS   not-accessible 
                STATUS       current
                DESCRIPTION 
                    "Entry of table wrlsShowinfoRadio"
                INDEX        { wrlsShowinfoRadioIndex }
                ::= { wrlsShowinfoRadioTable 1 }

            WrlsShowinfoRadioEntry ::=
            SEQUENCE {
                    wrlsShowinfoRadioIndex                           Integer32,
                    wrlsShowinfoRadioRadio                           Integer32,
                    wrlsShowinfoRadioCurrentChannel                  DisplayString,
                    wrlsShowinfoRadioSecondaryChannel                DisplayString,
                    wrlsShowinfoRadioSupportChannels                 DisplayString,
                    wrlsShowinfoRadioWideChannels                    DisplayString
            }

            wrlsShowinfoRadioIndex OBJECT-TYPE
                SYNTAX       Integer32
                MAX-ACCESS   read-only
                STATUS       current
                DESCRIPTION 
                    "Index of wrlsShowinfoRadioEntry."
                ::= { wrlsShowinfoRadioEntry 1 }

            wrlsShowinfoRadioRadio OBJECT-TYPE
                SYNTAX       Integer32
                MAX-ACCESS   read-only
                STATUS       current
                DESCRIPTION 
                    "radio index - 0 [2.4g] / 1 [5g]"
                ::= { wrlsShowinfoRadioEntry 2 }

            wrlsShowinfoRadioCurrentChannel OBJECT-TYPE
                SYNTAX       DisplayString
                MAX-ACCESS   read-only
                STATUS       current
                DESCRIPTION 
                    "get the current channel of the radio band"
                ::= { wrlsShowinfoRadioEntry 3 }

            wrlsShowinfoRadioSecondaryChannel OBJECT-TYPE
                SYNTAX       DisplayString
                MAX-ACCESS   read-only
                STATUS       current
                DESCRIPTION 
                    "get the secondary channel of the radio band, if applicable"
                ::= { wrlsShowinfoRadioEntry 4 }

            wrlsShowinfoRadioSupportChannels OBJECT-TYPE
                SYNTAX       DisplayString
                MAX-ACCESS   read-only
                STATUS       current
                DESCRIPTION 
                    "get the supported channels of the radio band"
                ::= { wrlsShowinfoRadioEntry 5 }

            wrlsShowinfoRadioWideChannels OBJECT-TYPE
                SYNTAX       DisplayString
                MAX-ACCESS   read-only
                STATUS       current
                DESCRIPTION 
                    "get the wide channels of the radio band"
                ::= { wrlsShowinfoRadioEntry 6 }

            wrlsShowinfoSystem OBJECT IDENTIFIER ::= { wrlsShowinfo 4 }

                wrlsShowinfoSystemOperStatus OBJECT-TYPE
                    SYNTAX       DisplayString
                    MAX-ACCESS   read-only
                    STATUS       current
                    DESCRIPTION 
                        "get the operational status of wifi service"
                    ::= { wrlsShowinfoSystem 1 }

        wrlsWpsConnect OBJECT IDENTIFIER ::= { wrls 5 }

            wrlsWpsConnectAdminStatus OBJECT-TYPE
                SYNTAX       INTEGER {
                    disable(1),
                    enable(2)
                }
                MAX-ACCESS   read-write
                STATUS       current
                DESCRIPTION 
                    "configure the activation of wps service, specify the authentication
                     method, if applicable"
                ::= { wrlsWpsConnect 1 }

            wrlsWpsConnectAuthMethod OBJECT-TYPE
                SYNTAX       INTEGER {
                    pbc(1),
                    pin(2)
                }
                MAX-ACCESS   read-write
                STATUS       current
                DESCRIPTION 
                    "set authentication method to either pbc or pin"
                ::= { wrlsWpsConnect 2 }

            wrlsWpsConnectAuthMethodPinPin OBJECT-TYPE
                SYNTAX       DisplayString
                MAX-ACCESS   read-write
                STATUS       current
                DESCRIPTION 
                    "set 8-digit pin"
                ::= { wrlsWpsConnect 3 }

            wrlsWpsConnectWpsPasscode OBJECT-TYPE
                SYNTAX       DisplayString
                MAX-ACCESS   read-only
                STATUS       current
                DESCRIPTION 
                    "the generated wpa-psk key for legency wstation to use, will show
                     on wps webpage"
                ::= { wrlsWpsConnect 4 }

            wrlsWpsConnectWpsScrty OBJECT-TYPE
                SYNTAX       DisplayString
                MAX-ACCESS   read-only
                STATUS       current
                DESCRIPTION 
                    "the default security type for wps"
                ::= { wrlsWpsConnect 5 }

            wrlsWpsConnectWpsEncryption OBJECT-TYPE
                SYNTAX       DisplayString
                MAX-ACCESS   read-only
                STATUS       current
                DESCRIPTION 
                    "the default encryption type for wps"
                ::= { wrlsWpsConnect 6 }

        wrlsRatelimit OBJECT IDENTIFIER ::= { wrls 6 }

            wrlsRatelimitVapRatelimitTable OBJECT-TYPE
                SYNTAX       SEQUENCE OF WrlsRatelimitVapRatelimitEntry
                MAX-ACCESS   not-accessible 
                STATUS       current
                DESCRIPTION 
                    "configure rate limit setting by vap"
                ::= { wrlsRatelimit 1 }

            wrlsRatelimitVapRatelimitEntry OBJECT-TYPE
                SYNTAX       WrlsRatelimitVapRatelimitEntry
                MAX-ACCESS   not-accessible 
                STATUS       current
                DESCRIPTION 
                    "Entry of table wrlsRatelimitVapRatelimit"
                INDEX        { wrlsRatelimitVapRatelimitIndex }
                ::= { wrlsRatelimitVapRatelimitTable 1 }

            WrlsRatelimitVapRatelimitEntry ::=
            SEQUENCE {
                    wrlsRatelimitVapRatelimitIndex                   Integer32,
                    wrlsRatelimitVapRatelimitRowStatus               RowStatus,
                    wrlsRatelimitVapRatelimitVapId                   INTEGER,
                    wrlsRatelimitVapRatelimitVapGuaBandwidth         Integer32,
                    wrlsRatelimitVapRatelimitVapMaxBandwidth         Integer32
            }

            wrlsRatelimitVapRatelimitIndex OBJECT-TYPE
                SYNTAX       Integer32
                MAX-ACCESS   read-only
                STATUS       current
                DESCRIPTION 
                    "Index of wrlsRatelimitVapRatelimitEntry."
                ::= { wrlsRatelimitVapRatelimitEntry 1 }

            wrlsRatelimitVapRatelimitRowStatus OBJECT-TYPE
                SYNTAX       RowStatus
                MAX-ACCESS   read-create
                STATUS       current
                DESCRIPTION 
                    "The status of this conceptual row.
                     Set createAndGo(4) or createAndWait(5) to create a row in this table.
                     Set destroy(6) to delete all of the instances associated with an existing
                     conceptual row."
                ::= { wrlsRatelimitVapRatelimitEntry 2 }

            wrlsRatelimitVapRatelimitVapId OBJECT-TYPE
                SYNTAX       INTEGER {
                    hotspot(1),
                    public(2),
                    subscriber(3)
                }
                MAX-ACCESS   read-create
                STATUS       current
                DESCRIPTION 
                    "configure what vap we want"
                ::= { wrlsRatelimitVapRatelimitEntry 3 }

            wrlsRatelimitVapRatelimitVapGuaBandwidth OBJECT-TYPE
                SYNTAX       Integer32
                MAX-ACCESS   read-create
                STATUS       current
                DESCRIPTION 
                    "configure the guaranteed bandwith for specified vap, in kilobits"
                ::= { wrlsRatelimitVapRatelimitEntry 4 }

            wrlsRatelimitVapRatelimitVapMaxBandwidth OBJECT-TYPE
                SYNTAX       Integer32
                MAX-ACCESS   read-create
                STATUS       current
                DESCRIPTION 
                    "configure the maximum bandwith for specified vap, in kilobits"
                ::= { wrlsRatelimitVapRatelimitEntry 5 }

            wrlsRatelimitStationRatelimitTable OBJECT-TYPE
                SYNTAX       SEQUENCE OF WrlsRatelimitStationRatelimitEntry
                MAX-ACCESS   not-accessible 
                STATUS       current
                DESCRIPTION 
                    "configure rate limit setting by station"
                ::= { wrlsRatelimit 2 }

            wrlsRatelimitStationRatelimitEntry OBJECT-TYPE
                SYNTAX       WrlsRatelimitStationRatelimitEntry
                MAX-ACCESS   not-accessible 
                STATUS       current
                DESCRIPTION 
                    "Entry of table wrlsRatelimitStationRatelimit"
                INDEX        { wrlsRatelimitStationRatelimitIndex }
                ::= { wrlsRatelimitStationRatelimitTable 1 }

            WrlsRatelimitStationRatelimitEntry ::=
            SEQUENCE {
                    wrlsRatelimitStationRatelimitIndex               Integer32,
                    wrlsRatelimitStationRatelimitRowStatus           RowStatus,
                    wrlsRatelimitStationRatelimitVapId               INTEGER,
                    wrlsRatelimitStationRatelimitStationMacAddr      DisplayString,
                    wrlsRatelimitStationRatelimitStationGuaBandwidth Integer32,
                    wrlsRatelimitStationRatelimitStationMaxBandwidth Integer32
            }

            wrlsRatelimitStationRatelimitIndex OBJECT-TYPE
                SYNTAX       Integer32
                MAX-ACCESS   read-only
                STATUS       current
                DESCRIPTION 
                    "Index of wrlsRatelimitStationRatelimitEntry."
                ::= { wrlsRatelimitStationRatelimitEntry 1 }

            wrlsRatelimitStationRatelimitRowStatus OBJECT-TYPE
                SYNTAX       RowStatus
                MAX-ACCESS   read-create
                STATUS       current
                DESCRIPTION 
                    "The status of this conceptual row.
                     Set createAndGo(4) or createAndWait(5) to create a row in this table.
                     Set destroy(6) to delete all of the instances associated with an existing
                     conceptual row."
                ::= { wrlsRatelimitStationRatelimitEntry 2 }

            wrlsRatelimitStationRatelimitVapId OBJECT-TYPE
                SYNTAX       INTEGER {
                    hotspot(1),
                    public(2),
                    subscriber(3)
                }
                MAX-ACCESS   read-create
                STATUS       current
                DESCRIPTION 
                    "configure what vap we want"
                ::= { wrlsRatelimitStationRatelimitEntry 3 }

            wrlsRatelimitStationRatelimitStationMacAddr OBJECT-TYPE
                SYNTAX       DisplayString
                MAX-ACCESS   read-create
                STATUS       current
                DESCRIPTION 
                    "mac address for configuration update on rate limit on station
                     connectivity"
                ::= { wrlsRatelimitStationRatelimitEntry 4 }

            wrlsRatelimitStationRatelimitStationGuaBandwidth OBJECT-TYPE
                SYNTAX       Integer32
                MAX-ACCESS   read-create
                STATUS       current
                DESCRIPTION 
                    "configure the guaranteed bandwith for station connected to specified
                     vap"
                ::= { wrlsRatelimitStationRatelimitEntry 5 }

            wrlsRatelimitStationRatelimitStationMaxBandwidth OBJECT-TYPE
                SYNTAX       Integer32
                MAX-ACCESS   read-create
                STATUS       current
                DESCRIPTION 
                    "configure the maximum bandwith for station connected to specified
                     vap"
                ::= { wrlsRatelimitStationRatelimitEntry 6 }

            wrlsRatelimitRateLimitStatus OBJECT-TYPE
                SYNTAX       INTEGER {
                    enable(1),
                    disable(2)
                }
                MAX-ACCESS   read-write
                STATUS       current
                DESCRIPTION 
                    "configure the activation of a vap rate limited"
                ::= { wrlsRatelimit 3 }

        wrlsMacFilt OBJECT IDENTIFIER ::= { wrls 7 }

            wrlsMacFiltMacFiltPlcyTable OBJECT-TYPE
                SYNTAX       SEQUENCE OF WrlsMacFiltMacFiltPlcyEntry
                MAX-ACCESS   not-accessible 
                STATUS       current
                DESCRIPTION 
                    "configure the default mac authentication policy"
                ::= { wrlsMacFilt 1 }

            wrlsMacFiltMacFiltPlcyEntry OBJECT-TYPE
                SYNTAX       WrlsMacFiltMacFiltPlcyEntry
                MAX-ACCESS   not-accessible 
                STATUS       current
                DESCRIPTION 
                    "Entry of table wrlsMacFiltMacFiltPlcy"
                INDEX        { wrlsMacFiltMacFiltPlcyIndex }
                ::= { wrlsMacFiltMacFiltPlcyTable 1 }

            WrlsMacFiltMacFiltPlcyEntry ::=
            SEQUENCE {
                    wrlsMacFiltMacFiltPlcyIndex                      Integer32,
                    wrlsMacFiltMacFiltPlcyRowStatus                  RowStatus,
                    wrlsMacFiltMacFiltPlcyVapId                      INTEGER,
                    wrlsMacFiltMacFiltPlcyAdminStatus                INTEGER
            }

            wrlsMacFiltMacFiltPlcyIndex OBJECT-TYPE
                SYNTAX       Integer32
                MAX-ACCESS   read-only
                STATUS       current
                DESCRIPTION 
                    "Index of wrlsMacFiltMacFiltPlcyEntry."
                ::= { wrlsMacFiltMacFiltPlcyEntry 1 }

            wrlsMacFiltMacFiltPlcyRowStatus OBJECT-TYPE
                SYNTAX       RowStatus
                MAX-ACCESS   read-create
                STATUS       current
                DESCRIPTION 
                    "The status of this conceptual row.
                     Set createAndGo(4) or createAndWait(5) to create a row in this table.
                     Set destroy(6) to delete all of the instances associated with an existing
                     conceptual row."
                ::= { wrlsMacFiltMacFiltPlcyEntry 2 }

            wrlsMacFiltMacFiltPlcyVapId OBJECT-TYPE
                SYNTAX       INTEGER {
                    home(1),
                    hotspot(2),
                    public(3),
                    subscriber(4)
                }
                MAX-ACCESS   read-create
                STATUS       current
                DESCRIPTION 
                    "vap id for configuration update on mac filter authentication"
                ::= { wrlsMacFiltMacFiltPlcyEntry 3 }

            wrlsMacFiltMacFiltPlcyAdminStatus OBJECT-TYPE
                SYNTAX       INTEGER {
                    disabled(1),
                    default-allow(2),
                    default-deny(3)
                }
                MAX-ACCESS   read-create
                STATUS       current
                DESCRIPTION 
                    "configure the activation of mac authentication and default policy,
                     if applicable"
                ::= { wrlsMacFiltMacFiltPlcyEntry 4 }

            wrlsMacFiltMacFiltListTable OBJECT-TYPE
                SYNTAX       SEQUENCE OF WrlsMacFiltMacFiltListEntry
                MAX-ACCESS   not-accessible 
                STATUS       current
                DESCRIPTION 
                    "insert or remove mac address from allow or deny list in mac authentication"
                ::= { wrlsMacFilt 2 }

            wrlsMacFiltMacFiltListEntry OBJECT-TYPE
                SYNTAX       WrlsMacFiltMacFiltListEntry
                MAX-ACCESS   not-accessible 
                STATUS       current
                DESCRIPTION 
                    "Entry of table wrlsMacFiltMacFiltList"
                INDEX        { wrlsMacFiltMacFiltListIndex }
                ::= { wrlsMacFiltMacFiltListTable 1 }

            WrlsMacFiltMacFiltListEntry ::=
            SEQUENCE {
                    wrlsMacFiltMacFiltListIndex                      Integer32,
                    wrlsMacFiltMacFiltListRowStatus                  RowStatus,
                    wrlsMacFiltMacFiltListVapId                      INTEGER,
                    wrlsMacFiltMacFiltListMacAddr                    DisplayString,
                    wrlsMacFiltMacFiltListListType                   INTEGER
            }

            wrlsMacFiltMacFiltListIndex OBJECT-TYPE
                SYNTAX       Integer32
                MAX-ACCESS   read-only
                STATUS       current
                DESCRIPTION 
                    "Index of wrlsMacFiltMacFiltListEntry."
                ::= { wrlsMacFiltMacFiltListEntry 1 }

            wrlsMacFiltMacFiltListRowStatus OBJECT-TYPE
                SYNTAX       RowStatus
                MAX-ACCESS   read-create
                STATUS       current
                DESCRIPTION 
                    "The status of this conceptual row.
                     Set createAndGo(4) or createAndWait(5) to create a row in this table.
                     Set destroy(6) to delete all of the instances associated with an existing
                     conceptual row."
                ::= { wrlsMacFiltMacFiltListEntry 2 }

            wrlsMacFiltMacFiltListVapId OBJECT-TYPE
                SYNTAX       INTEGER {
                    home(1),
                    hotspot(2),
                    public(3),
                    subscriber(4)
                }
                MAX-ACCESS   read-create
                STATUS       current
                DESCRIPTION 
                    "vap id for configuration update on mac filter authentication"
                ::= { wrlsMacFiltMacFiltListEntry 3 }

            wrlsMacFiltMacFiltListMacAddr OBJECT-TYPE
                SYNTAX       DisplayString
                MAX-ACCESS   read-create
                STATUS       current
                DESCRIPTION 
                    "mac address for configuration update on mac authentication for
                     either insert or delete operation"
                ::= { wrlsMacFiltMacFiltListEntry 4 }

            wrlsMacFiltMacFiltListListType OBJECT-TYPE
                SYNTAX       INTEGER {
                    allow(1),
                    deny(2)
                }
                MAX-ACCESS   read-create
                STATUS       current
                DESCRIPTION 
                    "configure allow or deny list in mac authentication for this vap
                     id and mac address applied"
                ::= { wrlsMacFiltMacFiltListEntry 5 }

        wrlsHomevapTable OBJECT-TYPE
            SYNTAX       SEQUENCE OF WrlsHomevapEntry
            MAX-ACCESS   not-accessible 
            STATUS       current
            DESCRIPTION 
                "wireless vap table for home user"
            ::= { wrls 8 }

        wrlsHomevapEntry OBJECT-TYPE
            SYNTAX       WrlsHomevapEntry
            MAX-ACCESS   not-accessible 
            STATUS       current
            DESCRIPTION 
                "Entry of table wrlsHomevap"
            INDEX        { wrlsHomevapIndex }
            ::= { wrlsHomevapTable 1 }

        WrlsHomevapEntry ::=
        SEQUENCE {
                wrlsHomevapIndex                                 Integer32,
                wrlsHomevapRowStatus                             RowStatus,
                wrlsHomevapVapId                                 INTEGER,
                wrlsHomevapFrequencyBand                         INTEGER,
                wrlsHomevapAdminStatus                           INTEGER,
                wrlsHomevapSsidName                              DisplayString,
                wrlsHomevapBroadcastSsid                         INTEGER,
                wrlsHomevapWmm                                   INTEGER,
                wrlsHomevapScrty                                 INTEGER,
                wrlsHomevapScrtyWepLength                        INTEGER,
                wrlsHomevapScrtyWepLength64WepKey                DisplayString,
                wrlsHomevapScrtyWepLength128WepKey               DisplayString,
                wrlsHomevapScrtyWpapskTkipWpapsktkipKey          DisplayString,
                wrlsHomevapScrtyWpapskAesWpapskaesKey            DisplayString,
                wrlsHomevapScrtyWpa2pskTkipWpa2tkipKey           DisplayString,
                wrlsHomevapScrtyWpa2pskAesWpa2aesKey             DisplayString
        }

        wrlsHomevapIndex OBJECT-TYPE
            SYNTAX       Integer32
            MAX-ACCESS   read-only
            STATUS       current
            DESCRIPTION 
                "Index of wrlsHomevapEntry."
            ::= { wrlsHomevapEntry 1 }

        wrlsHomevapRowStatus OBJECT-TYPE
            SYNTAX       RowStatus
            MAX-ACCESS   read-create
            STATUS       current
            DESCRIPTION 
                "The status of this conceptual row.
                 Set createAndGo(4) or createAndWait(5) to create a row in this table.
                 Set destroy(6) to delete all of the instances associated with an existing
                 conceptual row."
            ::= { wrlsHomevapEntry 2 }

        wrlsHomevapVapId OBJECT-TYPE
            SYNTAX       INTEGER {
                home(1)
            }
            MAX-ACCESS   read-create
            STATUS       current
            DESCRIPTION 
                "vap id for configuration update on vap table"
            ::= { wrlsHomevapEntry 3 }

        wrlsHomevapFrequencyBand OBJECT-TYPE
            SYNTAX       INTEGER {
                s2dot4G(1),
                s5G(2),
                s2dot4G-5G(3),
                none(4)
            }
            MAX-ACCESS   read-create
            STATUS       current
            DESCRIPTION 
                "configure the activation of frequency band"
            ::= { wrlsHomevapEntry 4 }

        wrlsHomevapAdminStatus OBJECT-TYPE
            SYNTAX       INTEGER {
                enable(1),
                disable(2)
            }
            MAX-ACCESS   read-create
            STATUS       current
            DESCRIPTION 
                "configure the activation of a vap"
            ::= { wrlsHomevapEntry 5 }

        wrlsHomevapSsidName OBJECT-TYPE
            SYNTAX       DisplayString
            MAX-ACCESS   read-create
            STATUS       current
            DESCRIPTION 
                "wireless network name ssid"
            ::= { wrlsHomevapEntry 6 }

        wrlsHomevapBroadcastSsid OBJECT-TYPE
            SYNTAX       INTEGER {
                enable(1),
                disable(2)
            }
            MAX-ACCESS   read-create
            STATUS       current
            DESCRIPTION 
                "configure the hidden capacity of a vap"
            ::= { wrlsHomevapEntry 7 }

        wrlsHomevapWmm OBJECT-TYPE
            SYNTAX       INTEGER {
                enable(1),
                disable(2)
            }
            MAX-ACCESS   read-create
            STATUS       current
            DESCRIPTION 
                "configure the wmm mode of a vap"
            ::= { wrlsHomevapEntry 8 }

        wrlsHomevapScrty OBJECT-TYPE
            SYNTAX       INTEGER {
                none(1),
                wep(2),
                wpapsk-tkip(3),
                wpapsk-aes(4),
                wpa2psk-tkip(5),
                wpa2psk-aes(6)
            }
            MAX-ACCESS   read-create
            STATUS       current
            DESCRIPTION 
                "set security mode: none/wep/wpapsk_tkip/wpapsk_aes/wpa2psk-tkip/wpa2psk-aes"
            ::= { wrlsHomevapEntry 9 }

        wrlsHomevapScrtyWepLength OBJECT-TYPE
            SYNTAX       INTEGER {
                s64(1),
                s128(2)
            }
            MAX-ACCESS   read-create
            STATUS       current
            DESCRIPTION 
                "set wep key length"
            ::= { wrlsHomevapEntry 10 }

        wrlsHomevapScrtyWepLength64WepKey OBJECT-TYPE
            SYNTAX       DisplayString
            MAX-ACCESS   read-create
            STATUS       current
            DESCRIPTION 
                "wep key1 value, with default key type: ascii or hex, key length:
                 64bits (5 or 10 chars)"
            ::= { wrlsHomevapEntry 11 }

        wrlsHomevapScrtyWepLength128WepKey OBJECT-TYPE
            SYNTAX       DisplayString
            MAX-ACCESS   read-create
            STATUS       current
            DESCRIPTION 
                "wep key1 value, with default key type: ascii or hex, key length:
                 128bits (13 or 26 chars)"
            ::= { wrlsHomevapEntry 12 }

        wrlsHomevapScrtyWpapskTkipWpapsktkipKey OBJECT-TYPE
            SYNTAX       DisplayString
            MAX-ACCESS   read-create
            STATUS       current
            DESCRIPTION 
                "wpa pre-shared key value, with key type: ascii or hex, key length
                 {8, 63} or 64"
            ::= { wrlsHomevapEntry 13 }

        wrlsHomevapScrtyWpapskAesWpapskaesKey OBJECT-TYPE
            SYNTAX       DisplayString
            MAX-ACCESS   read-create
            STATUS       current
            DESCRIPTION 
                "wpa pre-shared key value, with key type: ascii or hex, key length
                 {8, 63} or 64"
            ::= { wrlsHomevapEntry 14 }

        wrlsHomevapScrtyWpa2pskTkipWpa2tkipKey OBJECT-TYPE
            SYNTAX       DisplayString
            MAX-ACCESS   read-create
            STATUS       current
            DESCRIPTION 
                "wpa pre-shared key value, with key type: ascii or hex, key length
                 {8, 63} or 64"
            ::= { wrlsHomevapEntry 15 }

        wrlsHomevapScrtyWpa2pskAesWpa2aesKey OBJECT-TYPE
            SYNTAX       DisplayString
            MAX-ACCESS   read-create
            STATUS       current
            DESCRIPTION 
                "wpa pre-shared key value, with key type: ascii or hex, key length
                 {8, 63} or 64"
            ::= { wrlsHomevapEntry 16 }

    iface OBJECT IDENTIFIER ::= { smcUsgGateway 2 }

        ifaceWan OBJECT IDENTIFIER ::= { iface 1 }

            ifaceWanWanIpMode OBJECT-TYPE
                SYNTAX       INTEGER {
                    same-as-rf-interface(1),
                    ipv4-only(2),
                    ipv6-only(3),
                    dual-stack(4)
                }
                MAX-ACCESS   read-write
                STATUS       current
                DESCRIPTION 
                    "specify WAN IP mode"
                ::= { ifaceWan 1 }

            ifaceWanStatus OBJECT-TYPE
                SYNTAX       DisplayString
                MAX-ACCESS   read-only
                STATUS       current
                DESCRIPTION 
                    "status of wan interface"
                ::= { ifaceWan 2 }

            ifaceWanRebootWan OBJECT-TYPE
                SYNTAX       TruthValue
                MAX-ACCESS   read-write
                STATUS       current
                DESCRIPTION 
                    "Write-only object. Reading this object will result in implementation-specific
                     value, generally empty or a string describing the node is write-only.

                     reboot wan interface"
                ::= { ifaceWan 3 }

            ifaceWanUsage OBJECT IDENTIFIER ::= { ifaceWan 4 }

                ifaceWanUsageToday OBJECT-TYPE
                    SYNTAX       DisplayString
                    MAX-ACCESS   read-only
                    STATUS       current
                    DESCRIPTION 
                        "get flow usage today"
                    ::= { ifaceWanUsage 1 }

                ifaceWanUsageLast7days OBJECT-TYPE
                    SYNTAX       DisplayString
                    MAX-ACCESS   read-only
                    STATUS       current
                    DESCRIPTION 
                        "get flow usage in last 7 days"
                    ::= { ifaceWanUsage 2 }

                ifaceWanUsageLast30days OBJECT-TYPE
                    SYNTAX       DisplayString
                    MAX-ACCESS   read-only
                    STATUS       current
                    DESCRIPTION 
                        "get flow usage in last 30 days"
                    ::= { ifaceWanUsage 3 }

                ifaceWanUsageLast3months OBJECT-TYPE
                    SYNTAX       DisplayString
                    MAX-ACCESS   read-only
                    STATUS       current
                    DESCRIPTION 
                        "get flow usage in last 3 months"
                    ::= { ifaceWanUsage 4 }

                ifaceWanUsageLast1year OBJECT-TYPE
                    SYNTAX       DisplayString
                    MAX-ACCESS   read-only
                    STATUS       current
                    DESCRIPTION 
                        "get flow usage in last 1 year"
                    ::= { ifaceWanUsage 5 }

        ifaceLan OBJECT IDENTIFIER ::= { iface 2 }

            ifaceLanIp OBJECT-TYPE
                SYNTAX       InetAddress
                MAX-ACCESS   read-write
                STATUS       current
                DESCRIPTION 
                    "ip address of lan interface,last 16 addresses each sub-net are
                     reserved"
                ::= { ifaceLan 1 }

            ifaceLanIpMask OBJECT-TYPE
                SYNTAX       InetAddress
                MAX-ACCESS   read-write
                STATUS       current
                DESCRIPTION 
                    "netmask, must not be /28,/29,/30,/31"
                ::= { ifaceLan 2 }

            ifaceLanRestoreLan OBJECT-TYPE
                SYNTAX       TruthValue
                MAX-ACCESS   read-write
                STATUS       current
                DESCRIPTION 
                    "Write-only object. Reading this object will result in implementation-specific
                     value, generally empty or a string describing the node is write-only.

                     restore lan interface"
                ::= { ifaceLan 3 }

            ifaceLanDhcpSrvr OBJECT-TYPE
                SYNTAX       INTEGER {
                    enable(1),
                    disable(2)
                }
                MAX-ACCESS   read-write
                STATUS       current
                DESCRIPTION 
                    "setting of dhcp server for lan interface"
                ::= { ifaceLan 4 }

            ifaceLanDhcpSrvrEnblBeginningIp OBJECT-TYPE
                SYNTAX       InetAddress
                MAX-ACCESS   read-write
                STATUS       current
                DESCRIPTION 
                    "beginning ip, last 16 addresses each sub-net are reserved"
                ::= { ifaceLan 5 }

            ifaceLanDhcpSrvrEnblEndingIp OBJECT-TYPE
                SYNTAX       InetAddress
                MAX-ACCESS   read-write
                STATUS       current
                DESCRIPTION 
                    "ending ip, last 16 addresses each sub-net are reserved"
                ::= { ifaceLan 6 }

            ifaceLanDhcpSrvrEnblLeaseTime OBJECT-TYPE
                SYNTAX       DisplayString
                MAX-ACCESS   read-write
                STATUS       current
                DESCRIPTION 
                    "lease time in seconds,The minimum lease time is two minutes"
                ::= { ifaceLan 7 }

            ifaceLanDhcpSrvrEnblDomainName OBJECT-TYPE
                SYNTAX       DisplayString
                MAX-ACCESS   read-write
                STATUS       current
                DESCRIPTION 
                    "dhcp domain name"
                ::= { ifaceLan 8 }

            ifaceLanLanQos OBJECT-TYPE
                SYNTAX       TruthValue
                MAX-ACCESS   read-write
                STATUS       current
                DESCRIPTION 
                    "enable/disable lan qos"
                ::= { ifaceLan 9 }

        ifaceNetworkOperationalMode OBJECT-TYPE
            SYNTAX       INTEGER {
                bridge(1),
                router(2)
            }
            MAX-ACCESS   read-write
            STATUS       current
            DESCRIPTION 
                "operational mode of network"
            ::= { iface 3 }

    nat OBJECT IDENTIFIER ::= { smcUsgGateway 3 }

        natPortForwardingTable OBJECT-TYPE
            SYNTAX       SEQUENCE OF NatPortForwardingEntry
            MAX-ACCESS   not-accessible 
            STATUS       current
            DESCRIPTION 
                "port forwarding table"
            ::= { nat 1 }

        natPortForwardingEntry OBJECT-TYPE
            SYNTAX       NatPortForwardingEntry
            MAX-ACCESS   not-accessible 
            STATUS       current
            DESCRIPTION 
                "Entry of table natPortForwarding"
            INDEX        { natPortForwardingIndex }
            ::= { natPortForwardingTable 1 }

        NatPortForwardingEntry ::=
        SEQUENCE {
                natPortForwardingIndex                           Integer32,
                natPortForwardingRowStatus                       RowStatus,
                natPortForwardingSrvcName                        DisplayString,
                natPortForwardingServerip                        IpAddress,
                natPortForwardingProto                           INTEGER,
                natPortForwardingStartPort                       Integer32,
                natPortForwardingEndPort                         Integer32
        }

        natPortForwardingIndex OBJECT-TYPE
            SYNTAX       Integer32
            MAX-ACCESS   read-only
            STATUS       current
            DESCRIPTION 
                "Index of natPortForwardingEntry."
            ::= { natPortForwardingEntry 1 }

        natPortForwardingRowStatus OBJECT-TYPE
            SYNTAX       RowStatus
            MAX-ACCESS   read-create
            STATUS       current
            DESCRIPTION 
                "The status of this conceptual row.
                 Set createAndGo(4) or createAndWait(5) to create a row in this table.
                 Set destroy(6) to delete all of the instances associated with an existing
                 conceptual row."
            ::= { natPortForwardingEntry 2 }

        natPortForwardingSrvcName OBJECT-TYPE
            SYNTAX       DisplayString
            MAX-ACCESS   read-create
            STATUS       current
            DESCRIPTION 
                "service name"
            ::= { natPortForwardingEntry 3 }

        natPortForwardingServerip OBJECT-TYPE
            SYNTAX       IpAddress
            MAX-ACCESS   read-create
            STATUS       current
            DESCRIPTION 
                "server ip address."
            ::= { natPortForwardingEntry 4 }

        natPortForwardingProto OBJECT-TYPE
            SYNTAX       INTEGER {
                tcp(1),
                udp(2),
                tcp-udp(3)
            }
            MAX-ACCESS   read-create
            STATUS       current
            DESCRIPTION 
                "protocol"
            ::= { natPortForwardingEntry 5 }

        natPortForwardingStartPort OBJECT-TYPE
            SYNTAX       Integer32
            MAX-ACCESS   read-create
            STATUS       current
            DESCRIPTION 
                "starting port"
            ::= { natPortForwardingEntry 6 }

        natPortForwardingEndPort OBJECT-TYPE
            SYNTAX       Integer32
            MAX-ACCESS   read-create
            STATUS       current
            DESCRIPTION 
                "ending port."
            ::= { natPortForwardingEntry 7 }

        natPorttriggerEnbl OBJECT-TYPE
            SYNTAX       TruthValue
            MAX-ACCESS   read-write
            STATUS       current
            DESCRIPTION 
                "enable all port_trigger rules in port_trigger table"
            ::= { nat 2 }

        natPortTrgrTable OBJECT-TYPE
            SYNTAX       SEQUENCE OF NatPortTrgrEntry
            MAX-ACCESS   not-accessible 
            STATUS       current
            DESCRIPTION 
                "port trigger table"
            ::= { nat 3 }

        natPortTrgrEntry OBJECT-TYPE
            SYNTAX       NatPortTrgrEntry
            MAX-ACCESS   not-accessible 
            STATUS       current
            DESCRIPTION 
                "Entry of table natPortTrgr"
            INDEX        { natPortTrgrIndex }
            ::= { natPortTrgrTable 1 }

        NatPortTrgrEntry ::=
        SEQUENCE {
                natPortTrgrIndex                                 Integer32,
                natPortTrgrRowStatus                             RowStatus,
                natPortTrgrSrvcName                              DisplayString,
                natPortTrgrTriggeringStartPort                   Integer32,
                natPortTrgrTriggeringEndPort                     Integer32,
                natPortTrgrTriggeredStartPort                    Integer32,
                natPortTrgrTriggeredEndPort                      Integer32,
                natPortTrgrProto                                 INTEGER,
                natPortTrgrSrvcUsr                               INTEGER,
                natPortTrgrSrvcUsrSnglUsrIp                      IpAddress
        }

        natPortTrgrIndex OBJECT-TYPE
            SYNTAX       Integer32
            MAX-ACCESS   read-only
            STATUS       current
            DESCRIPTION 
                "Index of natPortTrgrEntry."
            ::= { natPortTrgrEntry 1 }

        natPortTrgrRowStatus OBJECT-TYPE
            SYNTAX       RowStatus
            MAX-ACCESS   read-create
            STATUS       current
            DESCRIPTION 
                "The status of this conceptual row.
                 Set createAndGo(4) or createAndWait(5) to create a row in this table.
                 Set destroy(6) to delete all of the instances associated with an existing
                 conceptual row."
            ::= { natPortTrgrEntry 2 }

        natPortTrgrSrvcName OBJECT-TYPE
            SYNTAX       DisplayString
            MAX-ACCESS   read-create
            STATUS       current
            DESCRIPTION 
                "service name"
            ::= { natPortTrgrEntry 3 }

        natPortTrgrTriggeringStartPort OBJECT-TYPE
            SYNTAX       Integer32
            MAX-ACCESS   read-create
            STATUS       current
            DESCRIPTION 
                "triggering starting port"
            ::= { natPortTrgrEntry 4 }

        natPortTrgrTriggeringEndPort OBJECT-TYPE
            SYNTAX       Integer32
            MAX-ACCESS   read-create
            STATUS       current
            DESCRIPTION 
                "triggering ending port"
            ::= { natPortTrgrEntry 5 }

        natPortTrgrTriggeredStartPort OBJECT-TYPE
            SYNTAX       Integer32
            MAX-ACCESS   read-create
            STATUS       current
            DESCRIPTION 
                "triggered starting port"
            ::= { natPortTrgrEntry 6 }

        natPortTrgrTriggeredEndPort OBJECT-TYPE
            SYNTAX       Integer32
            MAX-ACCESS   read-create
            STATUS       current
            DESCRIPTION 
                "triggered ending port"
            ::= { natPortTrgrEntry 7 }

        natPortTrgrProto OBJECT-TYPE
            SYNTAX       INTEGER {
                tcp(1),
                udp(2),
                tcp-udp(3)
            }
            MAX-ACCESS   read-create
            STATUS       current
            DESCRIPTION 
                "protocol of triggering"
            ::= { natPortTrgrEntry 8 }

        natPortTrgrSrvcUsr OBJECT-TYPE
            SYNTAX       INTEGER {
                any(1),
                single(2)
            }
            MAX-ACCESS   read-create
            STATUS       current
            DESCRIPTION 
                "service user of trigger"
            ::= { natPortTrgrEntry 9 }

        natPortTrgrSrvcUsrSnglUsrIp OBJECT-TYPE
            SYNTAX       IpAddress
            MAX-ACCESS   read-create
            STATUS       current
            DESCRIPTION 
                "ip address of triggered user"
            ::= { natPortTrgrEntry 10 }

        natDmzEnbl OBJECT-TYPE
            SYNTAX       TruthValue
            MAX-ACCESS   read-write
            STATUS       current
            DESCRIPTION 
                "enable/disable all rules in 121nat_mapping rules"
            ::= { nat 4 }

        natDmzMappedIp OBJECT-TYPE
            SYNTAX       IpAddress
            MAX-ACCESS   read-write
            STATUS       current
            DESCRIPTION 
                "mapped ip address"
            ::= { nat 5 }

        natPortforwardingEnbl OBJECT-TYPE
            SYNTAX       TruthValue
            MAX-ACCESS   read-write
            STATUS       current
            DESCRIPTION 
                "enable all port forwarding rules in port forwarding table"
            ::= { nat 6 }

        natPortblockingEnbl OBJECT-TYPE
            SYNTAX       TruthValue
            MAX-ACCESS   read-write
            STATUS       current
            DESCRIPTION 
                "enable all port blocking rules in port blocking table"
            ::= { nat 7 }

        natPortBlockingTable OBJECT-TYPE
            SYNTAX       SEQUENCE OF NatPortBlockingEntry
            MAX-ACCESS   not-accessible 
            STATUS       current
            DESCRIPTION 
                "port blocking table"
            ::= { nat 8 }

        natPortBlockingEntry OBJECT-TYPE
            SYNTAX       NatPortBlockingEntry
            MAX-ACCESS   not-accessible 
            STATUS       current
            DESCRIPTION 
                "Entry of table natPortBlocking"
            INDEX        { natPortBlockingIndex }
            ::= { natPortBlockingTable 1 }

        NatPortBlockingEntry ::=
        SEQUENCE {
                natPortBlockingIndex                             Integer32,
                natPortBlockingRowStatus                         RowStatus,
                natPortBlockingSrvcName                          DisplayString,
                natPortBlockingProto                             INTEGER,
                natPortBlockingPort                              Integer32
        }

        natPortBlockingIndex OBJECT-TYPE
            SYNTAX       Integer32
            MAX-ACCESS   read-only
            STATUS       current
            DESCRIPTION 
                "Index of natPortBlockingEntry."
            ::= { natPortBlockingEntry 1 }

        natPortBlockingRowStatus OBJECT-TYPE
            SYNTAX       RowStatus
            MAX-ACCESS   read-create
            STATUS       current
            DESCRIPTION 
                "The status of this conceptual row.
                 Set createAndGo(4) or createAndWait(5) to create a row in this table.
                 Set destroy(6) to delete all of the instances associated with an existing
                 conceptual row."
            ::= { natPortBlockingEntry 2 }

        natPortBlockingSrvcName OBJECT-TYPE
            SYNTAX       DisplayString
            MAX-ACCESS   read-create
            STATUS       current
            DESCRIPTION 
                "service name"
            ::= { natPortBlockingEntry 3 }

        natPortBlockingProto OBJECT-TYPE
            SYNTAX       INTEGER {
                tcp(1),
                udp(2),
                tcp-udp(3)
            }
            MAX-ACCESS   read-create
            STATUS       current
            DESCRIPTION 
                "protocol"
            ::= { natPortBlockingEntry 4 }

        natPortBlockingPort OBJECT-TYPE
            SYNTAX       Integer32
            MAX-ACCESS   read-create
            STATUS       current
            DESCRIPTION 
                "blocking port number"
            ::= { natPortBlockingEntry 5 }

    fw OBJECT IDENTIFIER ::= { smcUsgGateway 4 }

        fwFwLevel OBJECT-TYPE
            SYNTAX       INTEGER {
                high(1),
                medium(2),
                low(3),
                custom(4)
            }
            MAX-ACCESS   read-write
            STATUS       current
            DESCRIPTION 
                "configure firewall level"
            ::= { fw 1 }

        fwFwLevelCustomBlockHttp OBJECT-TYPE
            SYNTAX       TruthValue
            MAX-ACCESS   read-write
            STATUS       current
            DESCRIPTION 
                "block http and https service"
            ::= { fw 2 }

        fwFwLevelCustomBlockIcmpMsg OBJECT-TYPE
            SYNTAX       TruthValue
            MAX-ACCESS   read-write
            STATUS       current
            DESCRIPTION 
                "block icmp messages"
            ::= { fw 3 }

        fwFwLevelCustomBlockMulticast OBJECT-TYPE
            SYNTAX       TruthValue
            MAX-ACCESS   read-write
            STATUS       current
            DESCRIPTION 
                "block multicast message"
            ::= { fw 4 }

        fwFwLevelCustomBlockP2pApp OBJECT-TYPE
            SYNTAX       TruthValue
            MAX-ACCESS   read-write
            STATUS       current
            DESCRIPTION 
                "block peer to peer applications"
            ::= { fw 5 }

        fwFwLevelCustomBlockIdent OBJECT-TYPE
            SYNTAX       TruthValue
            MAX-ACCESS   read-write
            STATUS       current
            DESCRIPTION 
                "block ident service"
            ::= { fw 6 }

        fwFwLevelCustomEntrieFw OBJECT-TYPE
            SYNTAX       TruthValue
            MAX-ACCESS   read-write
            STATUS       current
            DESCRIPTION 
                "disable/enable entire firewall"
            ::= { fw 7 }

        fwFwLevelCustomBlockPingFromWan OBJECT-TYPE
            SYNTAX       TruthValue
            MAX-ACCESS   read-write
            STATUS       current
            DESCRIPTION 
                "enable/disable block ping from WAN"
            ::= { fw 8 }

        fwFwReboot OBJECT-TYPE
            SYNTAX       TruthValue
            MAX-ACCESS   read-write
            STATUS       current
            DESCRIPTION 
                "Write-only object. Reading this object will result in implementation-specific
                 value, generally empty or a string describing the node is write-only.

                 reboot firewall"
            ::= { fw 9 }

        fwFwRestore OBJECT-TYPE
            SYNTAX       TruthValue
            MAX-ACCESS   read-write
            STATUS       current
            DESCRIPTION 
                "Write-only object. Reading this object will result in implementation-specific
                 value, generally empty or a string describing the node is write-only.

                 restore firewall"
            ::= { fw 10 }

    usrMgmt OBJECT IDENTIFIER ::= { smcUsgGateway 5 }

        usrMgmtMso OBJECT-TYPE
            SYNTAX       DisplayString
            MAX-ACCESS   read-write
            STATUS       current
            DESCRIPTION 
                "mso user name"
            ::= { usrMgmt 1 }

        usrMgmtMsoPwd OBJECT-TYPE
            SYNTAX       DisplayString
            MAX-ACCESS   read-write
            STATUS       current
            DESCRIPTION 
                "mso user password, must be at least 8 charactors long"
            ::= { usrMgmt 2 }

        usrMgmtCusadmin OBJECT-TYPE
            SYNTAX       DisplayString
            MAX-ACCESS   read-write
            STATUS       current
            DESCRIPTION 
                "cusadmin user name"
            ::= { usrMgmt 3 }

        usrMgmtCusadminPwd OBJECT-TYPE
            SYNTAX       DisplayString
            MAX-ACCESS   read-write
            STATUS       current
            DESCRIPTION 
                "cusadmin user password, must be at least 8 charactors long"
            ::= { usrMgmt 4 }

        usrMgmtUsrTable OBJECT-TYPE
            SYNTAX       SEQUENCE OF UsrMgmtUsrEntry
            MAX-ACCESS   not-accessible 
            STATUS       current
            DESCRIPTION 
                "control user table"
            ::= { usrMgmt 5 }

        usrMgmtUsrEntry OBJECT-TYPE
            SYNTAX       UsrMgmtUsrEntry
            MAX-ACCESS   not-accessible 
            STATUS       current
            DESCRIPTION 
                "Entry of table usrMgmtUsr"
            INDEX        { usrMgmtUsrIndex }
            ::= { usrMgmtUsrTable 1 }

        UsrMgmtUsrEntry ::=
        SEQUENCE {
                usrMgmtUsrIndex                                  Integer32,
                usrMgmtUsrRowStatus                              RowStatus,
                usrMgmtUsrName                                   DisplayString,
                usrMgmtUsrPwd                                    DisplayString,
                usrMgmtUsrGrp                                    DisplayString
        }

        usrMgmtUsrIndex OBJECT-TYPE
            SYNTAX       Integer32
            MAX-ACCESS   read-only
            STATUS       current
            DESCRIPTION 
                "Index of usrMgmtUsrEntry."
            ::= { usrMgmtUsrEntry 1 }

        usrMgmtUsrRowStatus OBJECT-TYPE
            SYNTAX       RowStatus
            MAX-ACCESS   read-create
            STATUS       current
            DESCRIPTION 
                "The status of this conceptual row.
                 Set createAndGo(4) or createAndWait(5) to create a row in this table.
                 Set destroy(6) to delete all of the instances associated with an existing
                 conceptual row."
            ::= { usrMgmtUsrEntry 2 }

        usrMgmtUsrName OBJECT-TYPE
            SYNTAX       DisplayString
            MAX-ACCESS   read-create
            STATUS       current
            DESCRIPTION 
                "user name"
            ::= { usrMgmtUsrEntry 3 }

        usrMgmtUsrPwd OBJECT-TYPE
            SYNTAX       DisplayString
            MAX-ACCESS   read-create
            STATUS       current
            DESCRIPTION 
                "user password"
            ::= { usrMgmtUsrEntry 4 }

        usrMgmtUsrGrp OBJECT-TYPE
            SYNTAX       DisplayString
            MAX-ACCESS   read-create
            STATUS       current
            DESCRIPTION 
                "user group name
                 v - vpn
                 f - file server
                 p - print server
                 example: vfp"
            ::= { usrMgmtUsrEntry 5 }

    remtMgmt OBJECT IDENTIFIER ::= { smcUsgGateway 6 }

        remtMgmtEnbl OBJECT-TYPE
            SYNTAX       TruthValue
            MAX-ACCESS   read-write
            STATUS       current
            DESCRIPTION 
                "enable/disable remote managment"
            ::= { remtMgmt 1 }

        remtMgmtPortNum OBJECT-TYPE
            SYNTAX       Integer32
            MAX-ACCESS   read-write
            STATUS       current
            DESCRIPTION 
                "port number of remotemanagment"
            ::= { remtMgmt 2 }

        remtMgmtTrustedIp OBJECT-TYPE
            SYNTAX       INTEGER {
                any(1),
                single(2),
                range(3)
            }
            MAX-ACCESS   read-write
            STATUS       current
            DESCRIPTION 
                "configure ips that can have remote access,it can be ip address,
                 range, or any"
            ::= { remtMgmt 3 }

        remtMgmtTrustedIpSnglIp OBJECT-TYPE
            SYNTAX       IpAddress
            MAX-ACCESS   read-write
            STATUS       current
            DESCRIPTION 
                "source ip address"
            ::= { remtMgmt 4 }

        remtMgmtTrustedIpSnglDomain OBJECT-TYPE
            SYNTAX       DisplayString
            MAX-ACCESS   read-write
            STATUS       current
            DESCRIPTION 
                "domain name"
            ::= { remtMgmt 5 }

        remtMgmtTrustedIpRngStartIp OBJECT-TYPE
            SYNTAX       IpAddress
            MAX-ACCESS   read-write
            STATUS       current
            DESCRIPTION 
                "start of source ip address range"
            ::= { remtMgmt 6 }

        remtMgmtTrustedIpRngEndIp OBJECT-TYPE
            SYNTAX       IpAddress
            MAX-ACCESS   read-write
            STATUS       current
            DESCRIPTION 
                "end of source ip address range"
            ::= { remtMgmt 7 }

    dev OBJECT IDENTIFIER ::= { smcUsgGateway 7 }

        devEnblZeroCfg OBJECT-TYPE
            SYNTAX       TruthValue
            MAX-ACCESS   read-write
            STATUS       current
            DESCRIPTION 
                "enable or disable Zero Config for Device Discovery"
            ::= { dev 1 }

        devRefreshComputer OBJECT-TYPE
            SYNTAX       TruthValue
            MAX-ACCESS   read-write
            STATUS       current
            DESCRIPTION 
                "Write-only object. Reading this object will result in implementation-specific
                 value, generally empty or a string describing the node is write-only.

                 refresh connected computer table"
            ::= { dev 2 }

        devRefreshComputerStatus OBJECT-TYPE
            SYNTAX       DisplayString
            MAX-ACCESS   read-only
            STATUS       current
            DESCRIPTION 
                "status of refreshing connected computer table."
            ::= { dev 3 }

        devComputerTable OBJECT-TYPE
            SYNTAX       SEQUENCE OF DevComputerEntry
            MAX-ACCESS   not-accessible 
            STATUS       current
            DESCRIPTION 
                "static and dynamic configuration and information of connected
                 computers"
            ::= { dev 4 }

        devComputerEntry OBJECT-TYPE
            SYNTAX       DevComputerEntry
            MAX-ACCESS   not-accessible 
            STATUS       current
            DESCRIPTION 
                "Entry of table devComputer"
            INDEX        { devComputerIndex }
            ::= { devComputerTable 1 }

        DevComputerEntry ::=
        SEQUENCE {
                devComputerIndex                                 Integer32,
                devComputerRowStatus                             RowStatus,
                devComputerMac                                   DisplayString,
                devComputerComment                               DisplayString,
                devComputerReservedIp                            InetAddress,
                devComputerDevName                               DisplayString,
                devComputerIp                                    InetAddress,
                devComputerIface                                 DisplayString,
                devComputerConnection                            INTEGER,
                devComputerStatus                                INTEGER,
                devComputerDhcp                                  TruthValue,
                devComputerReservedIpv6                          InetAddress,
                devComputerIpv6                                  InetAddress,
                devComputerInterfacev6                           DisplayString,
                devComputerDhcpv6                                TruthValue
        }

        devComputerIndex OBJECT-TYPE
            SYNTAX       Integer32
            MAX-ACCESS   read-only
            STATUS       current
            DESCRIPTION 
                "Index of devComputerEntry."
            ::= { devComputerEntry 1 }

        devComputerRowStatus OBJECT-TYPE
            SYNTAX       RowStatus
            MAX-ACCESS   read-create
            STATUS       current
            DESCRIPTION 
                "The status of this conceptual row.
                 Set createAndGo(4) or createAndWait(5) to create a row in this table.
                 Set destroy(6) to delete all of the instances associated with an existing
                 conceptual row."
            ::= { devComputerEntry 2 }

        devComputerMac OBJECT-TYPE
            SYNTAX       DisplayString
            MAX-ACCESS   read-create
            STATUS       current
            DESCRIPTION 
                "computer mac address"
            ::= { devComputerEntry 3 }

        devComputerComment OBJECT-TYPE
            SYNTAX       DisplayString
            MAX-ACCESS   read-create
            STATUS       current
            DESCRIPTION 
                "computer description(example cli command to set comment:
                 device computer [mac] 'home pc')."
            ::= { devComputerEntry 4 }

        devComputerReservedIp OBJECT-TYPE
            SYNTAX       InetAddress
            MAX-ACCESS   read-create
            STATUS       current
            DESCRIPTION 
                "computer reserved ip address which is fed to dhcp server too"
            ::= { devComputerEntry 5 }

        devComputerDevName OBJECT-TYPE
            SYNTAX       DisplayString
            MAX-ACCESS   read-create
            STATUS       current
            DESCRIPTION 
                "device name of the computer"
            ::= { devComputerEntry 6 }

        devComputerIp OBJECT-TYPE
            SYNTAX       InetAddress
            MAX-ACCESS   read-only
            STATUS       current
            DESCRIPTION 
                "current computer ip address"
            ::= { devComputerEntry 7 }

        devComputerIface OBJECT-TYPE
            SYNTAX       DisplayString
            MAX-ACCESS   read-only
            STATUS       current
            DESCRIPTION 
                "which USG interface is connected to the computer"
            ::= { devComputerEntry 8 }

        devComputerConnection OBJECT-TYPE
            SYNTAX       INTEGER {
                ethernet(1),
                wifi-2-4(2),
                wifi-5(3)
            }
            MAX-ACCESS   read-only
            STATUS       current
            DESCRIPTION 
                "computer connection interface type"
            ::= { devComputerEntry 9 }

        devComputerStatus OBJECT-TYPE
            SYNTAX       INTEGER {
                online(1),
                offline(2)
            }
            MAX-ACCESS   read-only
            STATUS       current
            DESCRIPTION 
                "computer connection status"
            ::= { devComputerEntry 10 }

        devComputerDhcp OBJECT-TYPE
            SYNTAX       TruthValue
            MAX-ACCESS   read-create
            STATUS       current
            DESCRIPTION 
                "true if computer ip is assigned by dhcp server"
            ::= { devComputerEntry 11 }

        devComputerReservedIpv6 OBJECT-TYPE
            SYNTAX       InetAddress
            MAX-ACCESS   read-create
            STATUS       current
            DESCRIPTION 
                "computer reserved ipv6 address which is fed to dhcp server too"
            ::= { devComputerEntry 12 }

        devComputerIpv6 OBJECT-TYPE
            SYNTAX       InetAddress
            MAX-ACCESS   read-only
            STATUS       current
            DESCRIPTION 
                "current computer ipv6 address"
            ::= { devComputerEntry 13 }

        devComputerInterfacev6 OBJECT-TYPE
            SYNTAX       DisplayString
            MAX-ACCESS   read-only
            STATUS       current
            DESCRIPTION 
                "which USG interface is connected to the computer has a ipv6 address"
            ::= { devComputerEntry 14 }

        devComputerDhcpv6 OBJECT-TYPE
            SYNTAX       TruthValue
            MAX-ACCESS   read-create
            STATUS       current
            DESCRIPTION 
                "true if computer ipv6 address is assigned by dhcpv6 server"
            ::= { devComputerEntry 15 }

    prntlCtrl OBJECT IDENTIFIER ::= { smcUsgGateway 8 }

        prntlCtrlManagedSites OBJECT IDENTIFIER ::= { prntlCtrl 1 }

            prntlCtrlManagedSitesBlockedSitesTable OBJECT-TYPE
                SYNTAX       SEQUENCE OF PrntlCtrlManagedSitesBlockedSitesEntry
                MAX-ACCESS   not-accessible 
                STATUS       current
                DESCRIPTION 
                    "blocked sites table"
                ::= { prntlCtrlManagedSites 1 }

            prntlCtrlManagedSitesBlockedSitesEntry OBJECT-TYPE
                SYNTAX       PrntlCtrlManagedSitesBlockedSitesEntry
                MAX-ACCESS   not-accessible 
                STATUS       current
                DESCRIPTION 
                    "Entry of table prntlCtrlManagedSitesBlockedSites"
                INDEX        { prntlCtrlManagedSitesBlockedSitesIndex }
                ::= { prntlCtrlManagedSitesBlockedSitesTable 1 }

            PrntlCtrlManagedSitesBlockedSitesEntry ::=
            SEQUENCE {
                    prntlCtrlManagedSitesBlockedSitesIndex           Integer32,
                    prntlCtrlManagedSitesBlockedSitesRowStatus       RowStatus,
                    prntlCtrlManagedSitesBlockedSitesUrl             DisplayString,
                    prntlCtrlManagedSitesBlockedSitesTime            INTEGER,
                    prntlCtrlManagedSitesBlockedSitesTimeTimePeriodFromTime DisplayString,
                    prntlCtrlManagedSitesBlockedSitesTimeTimePeriodToTime DisplayString,
                    prntlCtrlManagedSitesBlockedSitesTimeTimePeriodRepeat DisplayString
            }

            prntlCtrlManagedSitesBlockedSitesIndex OBJECT-TYPE
                SYNTAX       Integer32
                MAX-ACCESS   read-only
                STATUS       current
                DESCRIPTION 
                    "Index of prntlCtrlManagedSitesBlockedSitesEntry."
                ::= { prntlCtrlManagedSitesBlockedSitesEntry 1 }

            prntlCtrlManagedSitesBlockedSitesRowStatus OBJECT-TYPE
                SYNTAX       RowStatus
                MAX-ACCESS   read-create
                STATUS       current
                DESCRIPTION 
                    "The status of this conceptual row.
                     Set createAndGo(4) or createAndWait(5) to create a row in this table.
                     Set destroy(6) to delete all of the instances associated with an existing
                     conceptual row."
                ::= { prntlCtrlManagedSitesBlockedSitesEntry 2 }

            prntlCtrlManagedSitesBlockedSitesUrl OBJECT-TYPE
                SYNTAX       DisplayString
                MAX-ACCESS   read-create
                STATUS       current
                DESCRIPTION 
                    "blocked url string"
                ::= { prntlCtrlManagedSitesBlockedSitesEntry 3 }

            prntlCtrlManagedSitesBlockedSitesTime OBJECT-TYPE
                SYNTAX       INTEGER {
                    always(1),
                    time-period(2)
                }
                MAX-ACCESS   read-create
                STATUS       current
                DESCRIPTION 
                    "time value"
                ::= { prntlCtrlManagedSitesBlockedSitesEntry 4 }

            prntlCtrlManagedSitesBlockedSitesTimeTimePeriodFromTime OBJECT-TYPE
                SYNTAX       DisplayString
                MAX-ACCESS   read-create
                STATUS       current
                DESCRIPTION 
                    "start time(format: HH:MM ;between 00:00 and 23:59)"
                ::= { prntlCtrlManagedSitesBlockedSitesEntry 5 }

            prntlCtrlManagedSitesBlockedSitesTimeTimePeriodToTime OBJECT-TYPE
                SYNTAX       DisplayString
                MAX-ACCESS   read-create
                STATUS       current
                DESCRIPTION 
                    "end time(format: HH:MM ;between 00:00 and 23:59)"
                ::= { prntlCtrlManagedSitesBlockedSitesEntry 6 }

            prntlCtrlManagedSitesBlockedSitesTimeTimePeriodRepeat OBJECT-TYPE
                SYNTAX       DisplayString
                MAX-ACCESS   read-create
                STATUS       current
                DESCRIPTION 
                    "list of weely days to repeat, (format: Mon,Tue,Wed,Thu,Fri,Sat,Sun
                     ;)"
                ::= { prntlCtrlManagedSitesBlockedSitesEntry 7 }

            prntlCtrlManagedSitesBlockedKeywordsTable OBJECT-TYPE
                SYNTAX       SEQUENCE OF PrntlCtrlManagedSitesBlockedKeywordsEntry
                MAX-ACCESS   not-accessible 
                STATUS       current
                DESCRIPTION 
                    "blocked keyword table"
                ::= { prntlCtrlManagedSites 2 }

            prntlCtrlManagedSitesBlockedKeywordsEntry OBJECT-TYPE
                SYNTAX       PrntlCtrlManagedSitesBlockedKeywordsEntry
                MAX-ACCESS   not-accessible 
                STATUS       current
                DESCRIPTION 
                    "Entry of table prntlCtrlManagedSitesBlockedKeywords"
                INDEX        { prntlCtrlManagedSitesBlockedKeywordsIndex }
                ::= { prntlCtrlManagedSitesBlockedKeywordsTable 1 }

            PrntlCtrlManagedSitesBlockedKeywordsEntry ::=
            SEQUENCE {
                    prntlCtrlManagedSitesBlockedKeywordsIndex        Integer32,
                    prntlCtrlManagedSitesBlockedKeywordsRowStatus    RowStatus,
                    prntlCtrlManagedSitesBlockedKeywordsKeyword      DisplayString,
                    prntlCtrlManagedSitesBlockedKeywordsTime         INTEGER,
                    prntlCtrlManagedSitesBlockedKeywordsTimeTimePeriodFromTime DisplayString,
                    prntlCtrlManagedSitesBlockedKeywordsTimeTimePeriodToTime DisplayString,
                    prntlCtrlManagedSitesBlockedKeywordsTimeTimePeriodRepeat DisplayString
            }

            prntlCtrlManagedSitesBlockedKeywordsIndex OBJECT-TYPE
                SYNTAX       Integer32
                MAX-ACCESS   read-only
                STATUS       current
                DESCRIPTION 
                    "Index of prntlCtrlManagedSitesBlockedKeywordsEntry."
                ::= { prntlCtrlManagedSitesBlockedKeywordsEntry 1 }

            prntlCtrlManagedSitesBlockedKeywordsRowStatus OBJECT-TYPE
                SYNTAX       RowStatus
                MAX-ACCESS   read-create
                STATUS       current
                DESCRIPTION 
                    "The status of this conceptual row.
                     Set createAndGo(4) or createAndWait(5) to create a row in this table.
                     Set destroy(6) to delete all of the instances associated with an existing
                     conceptual row."
                ::= { prntlCtrlManagedSitesBlockedKeywordsEntry 2 }

            prntlCtrlManagedSitesBlockedKeywordsKeyword OBJECT-TYPE
                SYNTAX       DisplayString
                MAX-ACCESS   read-create
                STATUS       current
                DESCRIPTION 
                    "blocked keyword string"
                ::= { prntlCtrlManagedSitesBlockedKeywordsEntry 3 }

            prntlCtrlManagedSitesBlockedKeywordsTime OBJECT-TYPE
                SYNTAX       INTEGER {
                    always(1),
                    time-period(2)
                }
                MAX-ACCESS   read-create
                STATUS       current
                DESCRIPTION 
                    "time value"
                ::= { prntlCtrlManagedSitesBlockedKeywordsEntry 4 }

            prntlCtrlManagedSitesBlockedKeywordsTimeTimePeriodFromTime OBJECT-TYPE
                SYNTAX       DisplayString
                MAX-ACCESS   read-create
                STATUS       current
                DESCRIPTION 
                    "start time(format: HH:MM ;between 00:00 and 23:59)"
                ::= { prntlCtrlManagedSitesBlockedKeywordsEntry 5 }

            prntlCtrlManagedSitesBlockedKeywordsTimeTimePeriodToTime OBJECT-TYPE
                SYNTAX       DisplayString
                MAX-ACCESS   read-create
                STATUS       current
                DESCRIPTION 
                    "end time(format: HH:MM ;between 00:00 and 23:59)"
                ::= { prntlCtrlManagedSitesBlockedKeywordsEntry 6 }

            prntlCtrlManagedSitesBlockedKeywordsTimeTimePeriodRepeat OBJECT-TYPE
                SYNTAX       DisplayString
                MAX-ACCESS   read-create
                STATUS       current
                DESCRIPTION 
                    "list of weely days to repeat, (format: Mon,Tue,Wed,Thu,Fri,Sat,Sun
                     ;)"
                ::= { prntlCtrlManagedSitesBlockedKeywordsEntry 7 }

            prntlCtrlManagedSitesTrustComputerTable OBJECT-TYPE
                SYNTAX       SEQUENCE OF PrntlCtrlManagedSitesTrustComputerEntry
                MAX-ACCESS   not-accessible 
                STATUS       current
                DESCRIPTION 
                    "trust computer table"
                ::= { prntlCtrlManagedSites 3 }

            prntlCtrlManagedSitesTrustComputerEntry OBJECT-TYPE
                SYNTAX       PrntlCtrlManagedSitesTrustComputerEntry
                MAX-ACCESS   not-accessible 
                STATUS       current
                DESCRIPTION 
                    "Entry of table prntlCtrlManagedSitesTrustComputer"
                INDEX        { prntlCtrlManagedSitesTrustComputerIndex }
                ::= { prntlCtrlManagedSitesTrustComputerTable 1 }

            PrntlCtrlManagedSitesTrustComputerEntry ::=
            SEQUENCE {
                    prntlCtrlManagedSitesTrustComputerIndex          Integer32,
                    prntlCtrlManagedSitesTrustComputerRowStatus      RowStatus,
                    prntlCtrlManagedSitesTrustComputerMac            DisplayString,
                    prntlCtrlManagedSitesTrustComputerEnbl           TruthValue,
                    prntlCtrlManagedSitesTrustComputerDevName        DisplayString
            }

            prntlCtrlManagedSitesTrustComputerIndex OBJECT-TYPE
                SYNTAX       Integer32
                MAX-ACCESS   read-only
                STATUS       current
                DESCRIPTION 
                    "Index of prntlCtrlManagedSitesTrustComputerEntry."
                ::= { prntlCtrlManagedSitesTrustComputerEntry 1 }

            prntlCtrlManagedSitesTrustComputerRowStatus OBJECT-TYPE
                SYNTAX       RowStatus
                MAX-ACCESS   read-create
                STATUS       current
                DESCRIPTION 
                    "The status of this conceptual row.
                     Set createAndGo(4) or createAndWait(5) to create a row in this table.
                     Set destroy(6) to delete all of the instances associated with an existing
                     conceptual row."
                ::= { prntlCtrlManagedSitesTrustComputerEntry 2 }

            prntlCtrlManagedSitesTrustComputerMac OBJECT-TYPE
                SYNTAX       DisplayString
                MAX-ACCESS   read-create
                STATUS       current
                DESCRIPTION 
                    "trust computer mac address"
                ::= { prntlCtrlManagedSitesTrustComputerEntry 3 }

            prntlCtrlManagedSitesTrustComputerEnbl OBJECT-TYPE
                SYNTAX       TruthValue
                MAX-ACCESS   read-create
                STATUS       current
                DESCRIPTION 
                    "enable/disable this computer as trust computer"
                ::= { prntlCtrlManagedSitesTrustComputerEntry 4 }

            prntlCtrlManagedSitesTrustComputerDevName OBJECT-TYPE
                SYNTAX       DisplayString
                MAX-ACCESS   read-only
                STATUS       current
                DESCRIPTION 
                    "trust computer name"
                ::= { prntlCtrlManagedSitesTrustComputerEntry 5 }

        prntlCtrlManagedServices OBJECT IDENTIFIER ::= { prntlCtrl 2 }

            prntlCtrlManagedServicesBlockedServicesTable OBJECT-TYPE
                SYNTAX       SEQUENCE OF PrntlCtrlManagedServicesBlockedServicesEntry
                MAX-ACCESS   not-accessible 
                STATUS       current
                DESCRIPTION 
                    "blocked services table"
                ::= { prntlCtrlManagedServices 1 }

            prntlCtrlManagedServicesBlockedServicesEntry OBJECT-TYPE
                SYNTAX       PrntlCtrlManagedServicesBlockedServicesEntry
                MAX-ACCESS   not-accessible 
                STATUS       current
                DESCRIPTION 
                    "Entry of table prntlCtrlManagedServicesBlockedServices"
                INDEX        { prntlCtrlManagedServicesBlockedServicesIndex }
                ::= { prntlCtrlManagedServicesBlockedServicesTable 1 }

            PrntlCtrlManagedServicesBlockedServicesEntry ::=
            SEQUENCE {
                    prntlCtrlManagedServicesBlockedServicesIndex     Integer32,
                    prntlCtrlManagedServicesBlockedServicesRowStatus RowStatus,
                    prntlCtrlManagedServicesBlockedServicesSrvc      DisplayString,
                    prntlCtrlManagedServicesBlockedServicesProto     INTEGER,
                    prntlCtrlManagedServicesBlockedServicesStartPort Integer32,
                    prntlCtrlManagedServicesBlockedServicesEndPort   Integer32,
                    prntlCtrlManagedServicesBlockedServicesTime      INTEGER,
                    prntlCtrlManagedServicesBlockedServicesTimeTimePeriodFromTime DisplayString,
                    prntlCtrlManagedServicesBlockedServicesTimeTimePeriodToTime DisplayString,
                    prntlCtrlManagedServicesBlockedServicesTimeTimePeriodRepeat DisplayString
            }

            prntlCtrlManagedServicesBlockedServicesIndex OBJECT-TYPE
                SYNTAX       Integer32
                MAX-ACCESS   read-only
                STATUS       current
                DESCRIPTION 
                    "Index of prntlCtrlManagedServicesBlockedServicesEntry."
                ::= { prntlCtrlManagedServicesBlockedServicesEntry 1 }

            prntlCtrlManagedServicesBlockedServicesRowStatus OBJECT-TYPE
                SYNTAX       RowStatus
                MAX-ACCESS   read-create
                STATUS       current
                DESCRIPTION 
                    "The status of this conceptual row.
                     Set createAndGo(4) or createAndWait(5) to create a row in this table.
                     Set destroy(6) to delete all of the instances associated with an existing
                     conceptual row."
                ::= { prntlCtrlManagedServicesBlockedServicesEntry 2 }

            prntlCtrlManagedServicesBlockedServicesSrvc OBJECT-TYPE
                SYNTAX       DisplayString
                MAX-ACCESS   read-create
                STATUS       current
                DESCRIPTION 
                    "blocked services name"
                ::= { prntlCtrlManagedServicesBlockedServicesEntry 3 }

            prntlCtrlManagedServicesBlockedServicesProto OBJECT-TYPE
                SYNTAX       INTEGER {
                    tcp(1),
                    udp(2),
                    tcp-udp(3)
                }
                MAX-ACCESS   read-create
                STATUS       current
                DESCRIPTION 
                    "blocked services protocol"
                ::= { prntlCtrlManagedServicesBlockedServicesEntry 4 }

            prntlCtrlManagedServicesBlockedServicesStartPort OBJECT-TYPE
                SYNTAX       Integer32
                MAX-ACCESS   read-create
                STATUS       current
                DESCRIPTION 
                    "starting port of blocked services"
                ::= { prntlCtrlManagedServicesBlockedServicesEntry 5 }

            prntlCtrlManagedServicesBlockedServicesEndPort OBJECT-TYPE
                SYNTAX       Integer32
                MAX-ACCESS   read-create
                STATUS       current
                DESCRIPTION 
                    "ending port of blocked services"
                ::= { prntlCtrlManagedServicesBlockedServicesEntry 6 }

            prntlCtrlManagedServicesBlockedServicesTime OBJECT-TYPE
                SYNTAX       INTEGER {
                    always(1),
                    time-period(2)
                }
                MAX-ACCESS   read-create
                STATUS       current
                DESCRIPTION 
                    "time value"
                ::= { prntlCtrlManagedServicesBlockedServicesEntry 7 }

            prntlCtrlManagedServicesBlockedServicesTimeTimePeriodFromTime OBJECT-TYPE
                SYNTAX       DisplayString
                MAX-ACCESS   read-create
                STATUS       current
                DESCRIPTION 
                    "start time(format: HH:MM ;between 00:00 and 23:59)"
                ::= { prntlCtrlManagedServicesBlockedServicesEntry 8 }

            prntlCtrlManagedServicesBlockedServicesTimeTimePeriodToTime OBJECT-TYPE
                SYNTAX       DisplayString
                MAX-ACCESS   read-create
                STATUS       current
                DESCRIPTION 
                    "end time(format: HH:MM ;between 00:00 and 23:59)"
                ::= { prntlCtrlManagedServicesBlockedServicesEntry 9 }

            prntlCtrlManagedServicesBlockedServicesTimeTimePeriodRepeat OBJECT-TYPE
                SYNTAX       DisplayString
                MAX-ACCESS   read-create
                STATUS       current
                DESCRIPTION 
                    "list of weely days to repeat,(format: Mon,Tue,Wed,Thu,Fri,Sat,Sun
                     ;)"
                ::= { prntlCtrlManagedServicesBlockedServicesEntry 10 }

            prntlCtrlManagedServicesTrustComputerTable OBJECT-TYPE
                SYNTAX       SEQUENCE OF PrntlCtrlManagedServicesTrustComputerEntry
                MAX-ACCESS   not-accessible 
                STATUS       current
                DESCRIPTION 
                    "trust computer table"
                ::= { prntlCtrlManagedServices 2 }

            prntlCtrlManagedServicesTrustComputerEntry OBJECT-TYPE
                SYNTAX       PrntlCtrlManagedServicesTrustComputerEntry
                MAX-ACCESS   not-accessible 
                STATUS       current
                DESCRIPTION 
                    "Entry of table prntlCtrlManagedServicesTrustComputer"
                INDEX        { prntlCtrlManagedServicesTrustComputerIndex }
                ::= { prntlCtrlManagedServicesTrustComputerTable 1 }

            PrntlCtrlManagedServicesTrustComputerEntry ::=
            SEQUENCE {
                    prntlCtrlManagedServicesTrustComputerIndex       Integer32,
                    prntlCtrlManagedServicesTrustComputerRowStatus   RowStatus,
                    prntlCtrlManagedServicesTrustComputerMac         DisplayString,
                    prntlCtrlManagedServicesTrustComputerEnbl        TruthValue,
                    prntlCtrlManagedServicesTrustComputerDevName     DisplayString
            }

            prntlCtrlManagedServicesTrustComputerIndex OBJECT-TYPE
                SYNTAX       Integer32
                MAX-ACCESS   read-only
                STATUS       current
                DESCRIPTION 
                    "Index of prntlCtrlManagedServicesTrustComputerEntry."
                ::= { prntlCtrlManagedServicesTrustComputerEntry 1 }

            prntlCtrlManagedServicesTrustComputerRowStatus OBJECT-TYPE
                SYNTAX       RowStatus
                MAX-ACCESS   read-create
                STATUS       current
                DESCRIPTION 
                    "The status of this conceptual row.
                     Set createAndGo(4) or createAndWait(5) to create a row in this table.
                     Set destroy(6) to delete all of the instances associated with an existing
                     conceptual row."
                ::= { prntlCtrlManagedServicesTrustComputerEntry 2 }

            prntlCtrlManagedServicesTrustComputerMac OBJECT-TYPE
                SYNTAX       DisplayString
                MAX-ACCESS   read-create
                STATUS       current
                DESCRIPTION 
                    "trust computer mac address"
                ::= { prntlCtrlManagedServicesTrustComputerEntry 3 }

            prntlCtrlManagedServicesTrustComputerEnbl OBJECT-TYPE
                SYNTAX       TruthValue
                MAX-ACCESS   read-create
                STATUS       current
                DESCRIPTION 
                    "enable/disable this computer as trust computer"
                ::= { prntlCtrlManagedServicesTrustComputerEntry 4 }

            prntlCtrlManagedServicesTrustComputerDevName OBJECT-TYPE
                SYNTAX       DisplayString
                MAX-ACCESS   read-only
                STATUS       current
                DESCRIPTION 
                    "trust computer name"
                ::= { prntlCtrlManagedServicesTrustComputerEntry 5 }

        prntlCtrlManagedComputersTable OBJECT-TYPE
            SYNTAX       SEQUENCE OF PrntlCtrlManagedComputersEntry
            MAX-ACCESS   not-accessible 
            STATUS       current
            DESCRIPTION 
                "online computer access table"
            ::= { prntlCtrl 3 }

        prntlCtrlManagedComputersEntry OBJECT-TYPE
            SYNTAX       PrntlCtrlManagedComputersEntry
            MAX-ACCESS   not-accessible 
            STATUS       current
            DESCRIPTION 
                "Entry of table prntlCtrlManagedComputers"
            INDEX        { prntlCtrlManagedComputersIndex }
            ::= { prntlCtrlManagedComputersTable 1 }

        PrntlCtrlManagedComputersEntry ::=
        SEQUENCE {
                prntlCtrlManagedComputersIndex                   Integer32,
                prntlCtrlManagedComputersRowStatus               RowStatus,
                prntlCtrlManagedComputersDevMac                  DisplayString,
                prntlCtrlManagedComputersDevName                 DisplayString,
                prntlCtrlManagedComputersTime                    INTEGER,
                prntlCtrlManagedComputersTimeTimePeriodFromTime  DisplayString,
                prntlCtrlManagedComputersTimeTimePeriodToTime    DisplayString,
                prntlCtrlManagedComputersTimeTimePeriodRepeat    DisplayString
        }

        prntlCtrlManagedComputersIndex OBJECT-TYPE
            SYNTAX       Integer32
            MAX-ACCESS   read-only
            STATUS       current
            DESCRIPTION 
                "Index of prntlCtrlManagedComputersEntry."
            ::= { prntlCtrlManagedComputersEntry 1 }

        prntlCtrlManagedComputersRowStatus OBJECT-TYPE
            SYNTAX       RowStatus
            MAX-ACCESS   read-create
            STATUS       current
            DESCRIPTION 
                "The status of this conceptual row.
                 Set createAndGo(4) or createAndWait(5) to create a row in this table.
                 Set destroy(6) to delete all of the instances associated with an existing
                 conceptual row."
            ::= { prntlCtrlManagedComputersEntry 2 }

        prntlCtrlManagedComputersDevMac OBJECT-TYPE
            SYNTAX       DisplayString
            MAX-ACCESS   read-create
            STATUS       current
            DESCRIPTION 
                "computer mac address"
            ::= { prntlCtrlManagedComputersEntry 3 }

        prntlCtrlManagedComputersDevName OBJECT-TYPE
            SYNTAX       DisplayString
            MAX-ACCESS   read-create
            STATUS       current
            DESCRIPTION 
                "online device name"
            ::= { prntlCtrlManagedComputersEntry 4 }

        prntlCtrlManagedComputersTime OBJECT-TYPE
            SYNTAX       INTEGER {
                always(1),
                time-period(2)
            }
            MAX-ACCESS   read-create
            STATUS       current
            DESCRIPTION 
                "time value"
            ::= { prntlCtrlManagedComputersEntry 5 }

        prntlCtrlManagedComputersTimeTimePeriodFromTime OBJECT-TYPE
            SYNTAX       DisplayString
            MAX-ACCESS   read-create
            STATUS       current
            DESCRIPTION 
                "start time(format: HH:MM ;between 00:00 and 23:59)"
            ::= { prntlCtrlManagedComputersEntry 6 }

        prntlCtrlManagedComputersTimeTimePeriodToTime OBJECT-TYPE
            SYNTAX       DisplayString
            MAX-ACCESS   read-create
            STATUS       current
            DESCRIPTION 
                "end time(format: HH:MM ;between 00:00 and 23:59)"
            ::= { prntlCtrlManagedComputersEntry 7 }

        prntlCtrlManagedComputersTimeTimePeriodRepeat OBJECT-TYPE
            SYNTAX       DisplayString
            MAX-ACCESS   read-create
            STATUS       current
            DESCRIPTION 
                "list of weely days to repeat,(format: Mon,Tue,Wed,Thu,Fri,Sat,Sun
                 ;)"
            ::= { prntlCtrlManagedComputersEntry 8 }

        prntlCtrlManagedComputersAccesstype OBJECT-TYPE
            SYNTAX       INTEGER {
                allowall(1),
                blockall(2)
            }
            MAX-ACCESS   read-write
            STATUS       current
            DESCRIPTION 
                "list of managed computer access type"
            ::= { prntlCtrl 4 }

    show OBJECT IDENTIFIER ::= { smcUsgGateway 9 }

        showDhcpLeasesTable OBJECT-TYPE
            SYNTAX       SEQUENCE OF ShowDhcpLeasesEntry
            MAX-ACCESS   not-accessible 
            STATUS       current
            DESCRIPTION 
                "show dhcp lease table"
            ::= { show 1 }

        showDhcpLeasesEntry OBJECT-TYPE
            SYNTAX       ShowDhcpLeasesEntry
            MAX-ACCESS   not-accessible 
            STATUS       current
            DESCRIPTION 
                "Entry of table showDhcpLeases"
            INDEX        { showDhcpLeasesIndex }
            ::= { showDhcpLeasesTable 1 }

        ShowDhcpLeasesEntry ::=
        SEQUENCE {
                showDhcpLeasesIndex                              Integer32,
                showDhcpLeasesIpAddr                             DisplayString,
                showDhcpLeasesMacAddr                            DisplayString,
                showDhcpLeasesDevName                            DisplayString
        }

        showDhcpLeasesIndex OBJECT-TYPE
            SYNTAX       Integer32
            MAX-ACCESS   read-only
            STATUS       current
            DESCRIPTION 
                "Index of showDhcpLeasesEntry."
            ::= { showDhcpLeasesEntry 1 }

        showDhcpLeasesIpAddr OBJECT-TYPE
            SYNTAX       DisplayString
            MAX-ACCESS   read-only
            STATUS       current
            DESCRIPTION 
                "leased ip address"
            ::= { showDhcpLeasesEntry 2 }

        showDhcpLeasesMacAddr OBJECT-TYPE
            SYNTAX       DisplayString
            MAX-ACCESS   read-only
            STATUS       current
            DESCRIPTION 
                "computer mac address"
            ::= { showDhcpLeasesEntry 3 }

        showDhcpLeasesDevName OBJECT-TYPE
            SYNTAX       DisplayString
            MAX-ACCESS   read-only
            STATUS       current
            DESCRIPTION 
                "computer name"
            ::= { showDhcpLeasesEntry 4 }

        showWanIp OBJECT-TYPE
            SYNTAX       DisplayString
            MAX-ACCESS   read-only
            STATUS       current
            DESCRIPTION 
                "show the wan ip address"
            ::= { show 2 }

        showWanExpiretime OBJECT-TYPE
            SYNTAX       DisplayString
            MAX-ACCESS   read-only
            STATUS       current
            DESCRIPTION 
                "show the wan expire time"
            ::= { show 3 }

        showLanTable OBJECT-TYPE
            SYNTAX       SEQUENCE OF ShowLanEntry
            MAX-ACCESS   not-accessible 
            STATUS       current
            DESCRIPTION 
                "show all lan ip address and netmask"
            ::= { show 4 }

        showLanEntry OBJECT-TYPE
            SYNTAX       ShowLanEntry
            MAX-ACCESS   not-accessible 
            STATUS       current
            DESCRIPTION 
                "Entry of table showLan"
            INDEX        { showLanIndex }
            ::= { showLanTable 1 }

        ShowLanEntry ::=
        SEQUENCE {
                showLanIndex                                     Integer32,
                showLanIfName                                    DisplayString,
                showLanIpAddr                                    DisplayString,
                showLanMask                                      DisplayString
        }

        showLanIndex OBJECT-TYPE
            SYNTAX       Integer32
            MAX-ACCESS   read-only
            STATUS       current
            DESCRIPTION 
                "Index of showLanEntry."
            ::= { showLanEntry 1 }

        showLanIfName OBJECT-TYPE
            SYNTAX       DisplayString
            MAX-ACCESS   read-only
            STATUS       current
            DESCRIPTION 
                "interface name"
            ::= { showLanEntry 2 }

        showLanIpAddr OBJECT-TYPE
            SYNTAX       DisplayString
            MAX-ACCESS   read-only
            STATUS       current
            DESCRIPTION 
                "interface ip address"
            ::= { showLanEntry 3 }

        showLanMask OBJECT-TYPE
            SYNTAX       DisplayString
            MAX-ACCESS   read-only
            STATUS       current
            DESCRIPTION 
                "interface netmask"
            ::= { showLanEntry 4 }

        showPrimaryDnsSrvr OBJECT-TYPE
            SYNTAX       DisplayString
            MAX-ACCESS   read-only
            STATUS       current
            DESCRIPTION 
                "primary dns server ip"
            ::= { show 5 }

        showSecondaryDnsSrvr OBJECT-TYPE
            SYNTAX       DisplayString
            MAX-ACCESS   read-only
            STATUS       current
            DESCRIPTION 
                "secondary dns server ip"
            ::= { show 6 }

    ar OBJECT IDENTIFIER ::= { smcUsgGateway 10 }

        arSystem OBJECT-TYPE
            SYNTAX       INTEGER {
                soft-reset(1),
                poweroff(2)
            }
            MAX-ACCESS   read-write
            STATUS       current
            DESCRIPTION 
                "Write-only object. Reading this object will result in implementation-specific
                 value, generally empty or a string describing the node is write-only.

                 control (reboot, shutdown) ar system"
            ::= { ar 1 }

        arFirmwareUpgrade OBJECT-TYPE
            SYNTAX       DisplayString
            MAX-ACCESS   read-write
            STATUS       current
            DESCRIPTION 
                "upgrade ar system firmware filename"
            ::= { ar 2 }

        arFirmwareUpgradeVer OBJECT-TYPE
            SYNTAX       DisplayString
            MAX-ACCESS   read-only
            STATUS       current
            DESCRIPTION 
                "version of firmware"
            ::= { ar 3 }

        arFirmwareUpgradeIp OBJECT-TYPE
            SYNTAX       InetAddress
            MAX-ACCESS   read-write
            STATUS       current
            DESCRIPTION 
                "server ip"
            ::= { ar 4 }

        arFirmwareUpgradeMethod OBJECT-TYPE
            SYNTAX       INTEGER {
                tftp(1),
                http(2)
            }
            MAX-ACCESS   read-write
            STATUS       current
            DESCRIPTION 
                "choice upgrade method"
            ::= { ar 5 }

        arBoot OBJECT-TYPE
            SYNTAX       INTEGER {
                a-partition(1),
                b-partition(2),
                backup(3)
            }
            MAX-ACCESS   read-write
            STATUS       current
            DESCRIPTION 
                "Write-only object. Reading this object will result in implementation-specific
                 value, generally empty or a string describing the node is write-only.

                 set next boot image partition"
            ::= { ar 6 }

        arNotify OBJECT IDENTIFIER ::= { ar 7 }

            arNotifyFwUpgradeInit OBJECT-TYPE
                SYNTAX       INTEGER {
                    enable(1),
                    disable(2)
                }
                MAX-ACCESS   read-write
                STATUS       current
                DESCRIPTION 
                    "set snmp send fw_upgrade_init trap"
                ::= { arNotify 1 }

            arNotifyFwUpgradeFail OBJECT-TYPE
                SYNTAX       INTEGER {
                    enable(1),
                    disable(2)
                }
                MAX-ACCESS   read-write
                STATUS       current
                DESCRIPTION 
                    "set snmp send fw_upgrade_fail trap"
                ::= { arNotify 2 }

            arNotifyFwUpgradeSuccess OBJECT-TYPE
                SYNTAX       INTEGER {
                    enable(1),
                    disable(2)
                }
                MAX-ACCESS   read-write
                STATUS       current
                DESCRIPTION 
                    "set snmp send fw_upgrade_success trap"
                ::= { arNotify 3 }

        arShow OBJECT IDENTIFIER ::= { ar 8 }

            arShowArVer OBJECT-TYPE
                SYNTAX       DisplayString
                MAX-ACCESS   read-only
                STATUS       current
                DESCRIPTION 
                    "show ar system version"
                ::= { arShow 1 }

            arShowBootIndicator OBJECT-TYPE
                SYNTAX       DisplayString
                MAX-ACCESS   read-only
                STATUS       current
                DESCRIPTION 
                    "show active and next boot partition"
                ::= { arShow 2 }

            arShowSystemUptime OBJECT-TYPE
                SYNTAX       DisplayString
                MAX-ACCESS   read-only
                STATUS       current
                DESCRIPTION 
                    "show ar system uptime"
                ::= { arShow 3 }

        arFirmware OBJECT IDENTIFIER ::= { ar 9 }

            arFirmwareFilename OBJECT-TYPE
                SYNTAX       DisplayString
                MAX-ACCESS   read-write
                STATUS       current
                DESCRIPTION 
                    "set firmware filename"
                ::= { arFirmware 1 }

            arFirmwareIp OBJECT-TYPE
                SYNTAX       InetAddress
                MAX-ACCESS   read-write
                STATUS       current
                DESCRIPTION 
                    "set image server ip address"
                ::= { arFirmware 2 }

            arFirmwareMethod OBJECT-TYPE
                SYNTAX       INTEGER {
                    tftp(1),
                    http(2)
                }
                MAX-ACCESS   read-write
                STATUS       current
                DESCRIPTION 
                    "set fimware upgrade method"
                ::= { arFirmware 3 }

            arFirmwareOperStatus OBJECT-TYPE
                SYNTAX       Integer32
                MAX-ACCESS   read-only
                STATUS       current
                DESCRIPTION 
                    "(1)in_progress, (2)complete_from_provisioning, (3) complete_from_mgt,
                     (4)failed, (5)other"
                ::= { arFirmware 4 }

            arFirmwareAdminStatus OBJECT-TYPE
                SYNTAX       INTEGER {
                    upgrade-from-mgt(1),
                    allow-prov-upgrade(2),
                    ignore-prov-upgrade(3)
                }
                MAX-ACCESS   read-write
                STATUS       current
                DESCRIPTION 
                    "get ar system admin state"
                ::= { arFirmware 5 }

    printer OBJECT IDENTIFIER ::= { smcUsgGateway 11 }

        printerSrvr OBJECT-TYPE
            SYNTAX       INTEGER {
                start(1),
                stop(2)
            }
            MAX-ACCESS   read-write
            STATUS       current
            DESCRIPTION 
                "Write-only object. Reading this object will result in implementation-specific
                 value, generally empty or a string describing the node is write-only.

                 enable or disable printer server"
            ::= { printer 1 }

        printerPrinterManageTable OBJECT-TYPE
            SYNTAX       SEQUENCE OF PrinterPrinterManageEntry
            MAX-ACCESS   not-accessible 
            STATUS       current
            DESCRIPTION 
                "add printer or edit printer"
            ::= { printer 2 }

        printerPrinterManageEntry OBJECT-TYPE
            SYNTAX       PrinterPrinterManageEntry
            MAX-ACCESS   not-accessible 
            STATUS       current
            DESCRIPTION 
                "Entry of table printerPrinterManage"
            INDEX        { printerPrinterManageIndex }
            ::= { printerPrinterManageTable 1 }

        PrinterPrinterManageEntry ::=
        SEQUENCE {
                printerPrinterManageIndex                        Integer32,
                printerPrinterManageRowStatus                    RowStatus,
                printerPrinterManagePrinterName                  DisplayString,
                printerPrinterManageUri                          DisplayString,
                printerPrinterManageDescription                  DisplayString,
                printerPrinterManageLocation                     DisplayString
        }

        printerPrinterManageIndex OBJECT-TYPE
            SYNTAX       Integer32
            MAX-ACCESS   read-only
            STATUS       current
            DESCRIPTION 
                "Index of printerPrinterManageEntry."
            ::= { printerPrinterManageEntry 1 }

        printerPrinterManageRowStatus OBJECT-TYPE
            SYNTAX       RowStatus
            MAX-ACCESS   read-create
            STATUS       current
            DESCRIPTION 
                "The status of this conceptual row.
                 Set createAndGo(4) or createAndWait(5) to create a row in this table.
                 Set destroy(6) to delete all of the instances associated with an existing
                 conceptual row."
            ::= { printerPrinterManageEntry 2 }

        printerPrinterManagePrinterName OBJECT-TYPE
            SYNTAX       DisplayString
            MAX-ACCESS   read-create
            STATUS       current
            DESCRIPTION 
                "input name of printer"
            ::= { printerPrinterManageEntry 3 }

        printerPrinterManageUri OBJECT-TYPE
            SYNTAX       DisplayString
            MAX-ACCESS   read-create
            STATUS       current
            DESCRIPTION 
                "input device bus of printer, please use 'printer usb show' to
                 view."
            ::= { printerPrinterManageEntry 4 }

        printerPrinterManageDescription OBJECT-TYPE
            SYNTAX       DisplayString
            MAX-ACCESS   read-create
            STATUS       current
            DESCRIPTION 
                "input description of printer"
            ::= { printerPrinterManageEntry 5 }

        printerPrinterManageLocation OBJECT-TYPE
            SYNTAX       DisplayString
            MAX-ACCESS   read-create
            STATUS       current
            DESCRIPTION 
                "input location of printer"
            ::= { printerPrinterManageEntry 6 }

        printerGetQueueStatusTable OBJECT-TYPE
            SYNTAX       SEQUENCE OF PrinterGetQueueStatusEntry
            MAX-ACCESS   not-accessible 
            STATUS       current
            DESCRIPTION 
                "show current jobs in queue"
            ::= { printer 3 }

        printerGetQueueStatusEntry OBJECT-TYPE
            SYNTAX       PrinterGetQueueStatusEntry
            MAX-ACCESS   not-accessible 
            STATUS       current
            DESCRIPTION 
                "Entry of table printerGetQueueStatus"
            INDEX        { printerGetQueueStatusIndex }
            ::= { printerGetQueueStatusTable 1 }

        PrinterGetQueueStatusEntry ::=
        SEQUENCE {
                printerGetQueueStatusIndex                       Integer32,
                printerGetQueueStatusJobid                       DisplayString,
                printerGetQueueStatusComputerName                DisplayString,
                printerGetQueueStatusJobName                     DisplayString,
                printerGetQueueStatusStatus                      DisplayString,
                printerGetQueueStatusSize                        DisplayString,
                printerGetQueueStatusPages                       DisplayString
        }

        printerGetQueueStatusIndex OBJECT-TYPE
            SYNTAX       Integer32
            MAX-ACCESS   read-only
            STATUS       current
            DESCRIPTION 
                "Index of printerGetQueueStatusEntry."
            ::= { printerGetQueueStatusEntry 1 }

        printerGetQueueStatusJobid OBJECT-TYPE
            SYNTAX       DisplayString
            MAX-ACCESS   read-only
            STATUS       current
            DESCRIPTION 
                "id of job"
            ::= { printerGetQueueStatusEntry 2 }

        printerGetQueueStatusComputerName OBJECT-TYPE
            SYNTAX       DisplayString
            MAX-ACCESS   read-only
            STATUS       current
            DESCRIPTION 
                "name of user who printing the job"
            ::= { printerGetQueueStatusEntry 3 }

        printerGetQueueStatusJobName OBJECT-TYPE
            SYNTAX       DisplayString
            MAX-ACCESS   read-only
            STATUS       current
            DESCRIPTION 
                "name of printing file"
            ::= { printerGetQueueStatusEntry 4 }

        printerGetQueueStatusStatus OBJECT-TYPE
            SYNTAX       DisplayString
            MAX-ACCESS   read-only
            STATUS       current
            DESCRIPTION 
                "status of printing job"
            ::= { printerGetQueueStatusEntry 5 }

        printerGetQueueStatusSize OBJECT-TYPE
            SYNTAX       DisplayString
            MAX-ACCESS   read-only
            STATUS       current
            DESCRIPTION 
                "size of printing file"
            ::= { printerGetQueueStatusEntry 6 }

        printerGetQueueStatusPages OBJECT-TYPE
            SYNTAX       DisplayString
            MAX-ACCESS   read-only
            STATUS       current
            DESCRIPTION 
                "pages of printing file"
            ::= { printerGetQueueStatusEntry 7 }

        printerRemoveJob OBJECT-TYPE
            SYNTAX       DisplayString
            MAX-ACCESS   read-write
            STATUS       current
            DESCRIPTION 
                "Write-only object. Reading this object will result in implementation-specific
                 value, generally empty or a string describing the node is write-only.

                 remove job from queue, default is remove all jobs"
            ::= { printer 4 }

        printerStatus OBJECT-TYPE
            SYNTAX       DisplayString
            MAX-ACCESS   read-only
            STATUS       current
            DESCRIPTION 
                "view printer server working status"
            ::= { printer 5 }

        printerUsbTable OBJECT-TYPE
            SYNTAX       SEQUENCE OF PrinterUsbEntry
            MAX-ACCESS   not-accessible 
            STATUS       current
            DESCRIPTION 
                "show current plugin printers in usb interfaces"
            ::= { printer 6 }

        printerUsbEntry OBJECT-TYPE
            SYNTAX       PrinterUsbEntry
            MAX-ACCESS   not-accessible 
            STATUS       current
            DESCRIPTION 
                "Entry of table printerUsb"
            INDEX        { printerUsbIndex }
            ::= { printerUsbTable 1 }

        PrinterUsbEntry ::=
        SEQUENCE {
                printerUsbIndex                                  Integer32,
                printerUsbUrl                                    DisplayString,
                printerUsbPrinterModel                           DisplayString,
                printerUsbPrinterOrder                           DisplayString
        }

        printerUsbIndex OBJECT-TYPE
            SYNTAX       Integer32
            MAX-ACCESS   read-only
            STATUS       current
            DESCRIPTION 
                "Index of printerUsbEntry."
            ::= { printerUsbEntry 1 }

        printerUsbUrl OBJECT-TYPE
            SYNTAX       DisplayString
            MAX-ACCESS   read-only
            STATUS       current
            DESCRIPTION 
                "url of usb printer"
            ::= { printerUsbEntry 2 }

        printerUsbPrinterModel OBJECT-TYPE
            SYNTAX       DisplayString
            MAX-ACCESS   read-only
            STATUS       current
            DESCRIPTION 
                "printer model"
            ::= { printerUsbEntry 3 }

        printerUsbPrinterOrder OBJECT-TYPE
            SYNTAX       DisplayString
            MAX-ACCESS   read-only
            STATUS       current
            DESCRIPTION 
                "printer order in usb interface"
            ::= { printerUsbEntry 4 }

        printerReset OBJECT-TYPE
            SYNTAX       TruthValue
            MAX-ACCESS   read-write
            STATUS       current
            DESCRIPTION 
                "Write-only object. Reading this object will result in implementation-specific
                 value, generally empty or a string describing the node is write-only.

                 Reset the printer server"
            ::= { printer 7 }

        printerRestore OBJECT-TYPE
            SYNTAX       TruthValue
            MAX-ACCESS   read-write
            STATUS       current
            DESCRIPTION 
                "Write-only object. Reading this object will result in implementation-specific
                 value, generally empty or a string describing the node is write-only.

                 Restore the configuration of the printer server as default"
            ::= { printer 8 }

        printerPrinterInGwTable OBJECT-TYPE
            SYNTAX       SEQUENCE OF PrinterPrinterInGwEntry
            MAX-ACCESS   not-accessible 
            STATUS       current
            DESCRIPTION 
                "show all printers attached to gateway"
            ::= { printer 9 }

        printerPrinterInGwEntry OBJECT-TYPE
            SYNTAX       PrinterPrinterInGwEntry
            MAX-ACCESS   not-accessible 
            STATUS       current
            DESCRIPTION 
                "Entry of table printerPrinterInGw"
            INDEX        { printerPrinterInGwIndex }
            ::= { printerPrinterInGwTable 1 }

        PrinterPrinterInGwEntry ::=
        SEQUENCE {
                printerPrinterInGwIndex                          Integer32,
                printerPrinterInGwPrinterName                    DisplayString,
                printerPrinterInGwDescription                    DisplayString,
                printerPrinterInGwLocation                       DisplayString,
                printerPrinterInGwUrl                            DisplayString,
                printerPrinterInGwIp                             DisplayString,
                printerPrinterInGwManufacturer                   DisplayString,
                printerPrinterInGwModel                          DisplayString,
                printerPrinterInGwSerialNum                      DisplayString,
                printerPrinterInGwDriverVer                      DisplayString
        }

        printerPrinterInGwIndex OBJECT-TYPE
            SYNTAX       Integer32
            MAX-ACCESS   read-only
            STATUS       current
            DESCRIPTION 
                "Index of printerPrinterInGwEntry."
            ::= { printerPrinterInGwEntry 1 }

        printerPrinterInGwPrinterName OBJECT-TYPE
            SYNTAX       DisplayString
            MAX-ACCESS   read-only
            STATUS       current
            DESCRIPTION 
                "name of printer"
            ::= { printerPrinterInGwEntry 2 }

        printerPrinterInGwDescription OBJECT-TYPE
            SYNTAX       DisplayString
            MAX-ACCESS   read-only
            STATUS       current
            DESCRIPTION 
                "description of printer"
            ::= { printerPrinterInGwEntry 3 }

        printerPrinterInGwLocation OBJECT-TYPE
            SYNTAX       DisplayString
            MAX-ACCESS   read-only
            STATUS       current
            DESCRIPTION 
                "location of printer"
            ::= { printerPrinterInGwEntry 4 }

        printerPrinterInGwUrl OBJECT-TYPE
            SYNTAX       DisplayString
            MAX-ACCESS   read-only
            STATUS       current
            DESCRIPTION 
                "url of printer"
            ::= { printerPrinterInGwEntry 5 }

        printerPrinterInGwIp OBJECT-TYPE
            SYNTAX       DisplayString
            MAX-ACCESS   read-only
            STATUS       current
            DESCRIPTION 
                "ip of printer"
            ::= { printerPrinterInGwEntry 6 }

        printerPrinterInGwManufacturer OBJECT-TYPE
            SYNTAX       DisplayString
            MAX-ACCESS   read-only
            STATUS       current
            DESCRIPTION 
                "manufacturer of printer"
            ::= { printerPrinterInGwEntry 7 }

        printerPrinterInGwModel OBJECT-TYPE
            SYNTAX       DisplayString
            MAX-ACCESS   read-only
            STATUS       current
            DESCRIPTION 
                "model of printer"
            ::= { printerPrinterInGwEntry 8 }

        printerPrinterInGwSerialNum OBJECT-TYPE
            SYNTAX       DisplayString
            MAX-ACCESS   read-only
            STATUS       current
            DESCRIPTION 
                "serial number of printer"
            ::= { printerPrinterInGwEntry 9 }

        printerPrinterInGwDriverVer OBJECT-TYPE
            SYNTAX       DisplayString
            MAX-ACCESS   read-only
            STATUS       current
            DESCRIPTION 
                "driver version of printer"
            ::= { printerPrinterInGwEntry 10 }

        printerPrinterOnNetTable OBJECT-TYPE
            SYNTAX       SEQUENCE OF PrinterPrinterOnNetEntry
            MAX-ACCESS   not-accessible 
            STATUS       current
            DESCRIPTION 
                "show other printer shared on the network"
            ::= { printer 10 }

        printerPrinterOnNetEntry OBJECT-TYPE
            SYNTAX       PrinterPrinterOnNetEntry
            MAX-ACCESS   not-accessible 
            STATUS       current
            DESCRIPTION 
                "Entry of table printerPrinterOnNet"
            INDEX        { printerPrinterOnNetIndex }
            ::= { printerPrinterOnNetTable 1 }

        PrinterPrinterOnNetEntry ::=
        SEQUENCE {
                printerPrinterOnNetIndex                         Integer32,
                printerPrinterOnNetPrinterName                   DisplayString,
                printerPrinterOnNetDescription                   DisplayString,
                printerPrinterOnNetLocation                      DisplayString,
                printerPrinterOnNetUrl                           DisplayString,
                printerPrinterOnNetIp                            DisplayString
        }

        printerPrinterOnNetIndex OBJECT-TYPE
            SYNTAX       Integer32
            MAX-ACCESS   read-only
            STATUS       current
            DESCRIPTION 
                "Index of printerPrinterOnNetEntry."
            ::= { printerPrinterOnNetEntry 1 }

        printerPrinterOnNetPrinterName OBJECT-TYPE
            SYNTAX       DisplayString
            MAX-ACCESS   read-only
            STATUS       current
            DESCRIPTION 
                "name of printer"
            ::= { printerPrinterOnNetEntry 2 }

        printerPrinterOnNetDescription OBJECT-TYPE
            SYNTAX       DisplayString
            MAX-ACCESS   read-only
            STATUS       current
            DESCRIPTION 
                "description of printer"
            ::= { printerPrinterOnNetEntry 3 }

        printerPrinterOnNetLocation OBJECT-TYPE
            SYNTAX       DisplayString
            MAX-ACCESS   read-only
            STATUS       current
            DESCRIPTION 
                "location of printer"
            ::= { printerPrinterOnNetEntry 4 }

        printerPrinterOnNetUrl OBJECT-TYPE
            SYNTAX       DisplayString
            MAX-ACCESS   read-only
            STATUS       current
            DESCRIPTION 
                "url of printer"
            ::= { printerPrinterOnNetEntry 5 }

        printerPrinterOnNetIp OBJECT-TYPE
            SYNTAX       DisplayString
            MAX-ACCESS   read-only
            STATUS       current
            DESCRIPTION 
                "ip of printer"
            ::= { printerPrinterOnNetEntry 6 }

        printerPauseJob OBJECT-TYPE
            SYNTAX       DisplayString
            MAX-ACCESS   read-write
            STATUS       current
            DESCRIPTION 
                "Write-only object. Reading this object will result in implementation-specific
                 value, generally empty or a string describing the node is write-only.

                 pause job from queue"
            ::= { printer 11 }

        printerResumeJob OBJECT-TYPE
            SYNTAX       DisplayString
            MAX-ACCESS   read-write
            STATUS       current
            DESCRIPTION 
                "Write-only object. Reading this object will result in implementation-specific
                 value, generally empty or a string describing the node is write-only.

                 resume job from queue"
            ::= { printer 12 }

    networkstorage OBJECT IDENTIFIER ::= { smcUsgGateway 12 }

        networkstorageGetsharedfolders OBJECT-TYPE
            SYNTAX       DisplayString
            MAX-ACCESS   read-only
            STATUS       current
            DESCRIPTION 
                "Use this method to enumerate all of the shared folders exposed
                 by the network device."
            ::= { networkstorage 1 }

        networkstorageGetphysicaldrives OBJECT-TYPE
            SYNTAX       DisplayString
            MAX-ACCESS   read-only
            STATUS       current
            DESCRIPTION 
                "Use this method to obtain information about the physical disk
                 drive attached to this storage device"
            ::= { networkstorage 2 }

        networkstorageGetlogicaldrives OBJECT-TYPE
            SYNTAX       DisplayString
            MAX-ACCESS   read-only
            STATUS       current
            DESCRIPTION 
                "Use this method to obtain information about the logical drives
                 attached to this storage device."
            ::= { networkstorage 3 }

        networkstorageFormatstorage OBJECT-TYPE
            SYNTAX       DisplayString
            MAX-ACCESS   read-write
            STATUS       current
            DESCRIPTION 
                "Write-only object. Reading this object will result in implementation-specific
                 value, generally empty or a string describing the node is write-only.

                 PhysicalDriveID to be format, e.g., /dev/sda1"
            ::= { networkstorage 4 }

        networkstorageFormatstorageArraytype OBJECT-TYPE
            SYNTAX       INTEGER {
                none(1),
                jBOD(2),
                rAID0(3),
                rAID1(4),
                rAID5(5)
            }
            MAX-ACCESS   read-write
            STATUS       current
            DESCRIPTION 
                "Write-only object. Reading this object will result in implementation-specific
                 value, generally empty or a string describing the node is write-only.

                 Desired configuration for network storage device."
            ::= { networkstorage 5 }

        networkstorageGetformatstatus OBJECT-TYPE
            SYNTAX       DisplayString
            MAX-ACCESS   read-only
            STATUS       current
            DESCRIPTION 
                "Use this method to query the status of a pending format operation."
            ::= { networkstorage 6 }

        networkstorageAddsharedfolder OBJECT-TYPE
            SYNTAX       DisplayString
            MAX-ACCESS   read-write
            STATUS       current
            DESCRIPTION 
                "Write-only object. Reading this object will result in implementation-specific
                 value, generally empty or a string describing the node is write-only.

                 Specifies a name for this share to be added."
            ::= { networkstorage 7 }

        networkstorageAddsharedfolderLogicaldriveid OBJECT-TYPE
            SYNTAX       DisplayString
            MAX-ACCESS   read-write
            STATUS       current
            DESCRIPTION 
                "Write-only object. Reading this object will result in implementation-specific
                 value, generally empty or a string describing the node is write-only.

                 Id of the logical drive on the NAS device to be used to store
                 content for this file share."
            ::= { networkstorage 8 }

        networkstorageAddsharedfolderReadonly OBJECT-TYPE
            SYNTAX       TruthValue
            MAX-ACCESS   read-write
            STATUS       current
            DESCRIPTION 
                "Write-only object. Reading this object will result in implementation-specific
                 value, generally empty or a string describing the node is write-only.

                 Boolean value that specifies if the share should be created read-only
                 or read-write."
            ::= { networkstorage 9 }

        networkstorageModifysharefold OBJECT-TYPE
            SYNTAX       DisplayString
            MAX-ACCESS   read-write
            STATUS       current
            DESCRIPTION 
                "Write-only object. Reading this object will result in implementation-specific
                 value, generally empty or a string describing the node is write-only.

                 Specifies a original name for this share to modify."
            ::= { networkstorage 10 }

        networkstorageModifysharefoldNewname OBJECT-TYPE
            SYNTAX       DisplayString
            MAX-ACCESS   read-write
            STATUS       current
            DESCRIPTION 
                "Write-only object. Reading this object will result in implementation-specific
                 value, generally empty or a string describing the node is write-only.

                 Specifies the new name for this file share to modify to."
            ::= { networkstorage 11 }

        networkstorageModifysharefoldReadonly OBJECT-TYPE
            SYNTAX       TruthValue
            MAX-ACCESS   read-write
            STATUS       current
            DESCRIPTION 
                "Write-only object. Reading this object will result in implementation-specific
                 value, generally empty or a string describing the node is write-only.

                 Boolean value that specifies if the share should be created read-only
                 or read-write."
            ::= { networkstorage 12 }

        networkstorageDeletesharefold OBJECT-TYPE
            SYNTAX       DisplayString
            MAX-ACCESS   read-write
            STATUS       current
            DESCRIPTION 
                "Write-only object. Reading this object will result in implementation-specific
                 value, generally empty or a string describing the node is write-only.

                 Specifies a name for this share to delete."
            ::= { networkstorage 13 }

        networkstorageUsbInfo3 OBJECT-TYPE
            SYNTAX       DisplayString
            MAX-ACCESS   read-only
            STATUS       current
            DESCRIPTION 
                "Get USB Hardware Information"
            ::= { networkstorage 14 }

        networkstorageUsbInfo3Status OBJECT-TYPE
            SYNTAX       DisplayString
            MAX-ACCESS   read-only
            STATUS       current
            DESCRIPTION 
                "get the status"
            ::= { networkstorage 15 }

        networkstorageUsbInfo3Description OBJECT-TYPE
            SYNTAX       DisplayString
            MAX-ACCESS   read-only
            STATUS       current
            DESCRIPTION 
                "get the description"
            ::= { networkstorage 16 }

        networkstorageUsbInfo3PortId OBJECT-TYPE
            SYNTAX       DisplayString
            MAX-ACCESS   read-only
            STATUS       current
            DESCRIPTION 
                "get the port id"
            ::= { networkstorage 17 }

        networkstorageUsbInfo3ProductId OBJECT-TYPE
            SYNTAX       DisplayString
            MAX-ACCESS   read-only
            STATUS       current
            DESCRIPTION 
                "get the product id"
            ::= { networkstorage 18 }

        networkstorageUsbInfo3VendorId OBJECT-TYPE
            SYNTAX       DisplayString
            MAX-ACCESS   read-only
            STATUS       current
            DESCRIPTION 
                "get the vendor id"
            ::= { networkstorage 19 }

        networkstorageUsbInfo3Ver OBJECT-TYPE
            SYNTAX       DisplayString
            MAX-ACCESS   read-only
            STATUS       current
            DESCRIPTION 
                "get the version"
            ::= { networkstorage 20 }

        networkstorageUsbInfo3SerialNum OBJECT-TYPE
            SYNTAX       DisplayString
            MAX-ACCESS   read-only
            STATUS       current
            DESCRIPTION 
                "get the serial number"
            ::= { networkstorage 21 }

        networkstorageUsbInfo3Speed OBJECT-TYPE
            SYNTAX       DisplayString
            MAX-ACCESS   read-only
            STATUS       current
            DESCRIPTION 
                "get the speed"
            ::= { networkstorage 22 }

        networkstorageUsbInfo3Manufacturer OBJECT-TYPE
            SYNTAX       DisplayString
            MAX-ACCESS   read-only
            STATUS       current
            DESCRIPTION 
                "get the manufacturer"
            ::= { networkstorage 23 }

        networkstorageUsbInfo3LocationId OBJECT-TYPE
            SYNTAX       DisplayString
            MAX-ACCESS   read-only
            STATUS       current
            DESCRIPTION 
                "get the location id"
            ::= { networkstorage 24 }

        networkstorageUsbInfo3CurrentAvailable OBJECT-TYPE
            SYNTAX       DisplayString
            MAX-ACCESS   read-only
            STATUS       current
            DESCRIPTION 
                "get the current available"
            ::= { networkstorage 25 }

        networkstorageUsbInfo3CurrentRequired OBJECT-TYPE
            SYNTAX       DisplayString
            MAX-ACCESS   read-only
            STATUS       current
            DESCRIPTION 
                "get the current required"
            ::= { networkstorage 26 }

        networkstorageUsbInfo4 OBJECT-TYPE
            SYNTAX       DisplayString
            MAX-ACCESS   read-only
            STATUS       current
            DESCRIPTION 
                "Get USB Hardware Information"
            ::= { networkstorage 27 }

        networkstorageUsbInfo4Status OBJECT-TYPE
            SYNTAX       DisplayString
            MAX-ACCESS   read-only
            STATUS       current
            DESCRIPTION 
                "get the status"
            ::= { networkstorage 28 }

        networkstorageUsbInfo4Description OBJECT-TYPE
            SYNTAX       DisplayString
            MAX-ACCESS   read-only
            STATUS       current
            DESCRIPTION 
                "get the description"
            ::= { networkstorage 29 }

        networkstorageUsbInfo4PortId OBJECT-TYPE
            SYNTAX       DisplayString
            MAX-ACCESS   read-only
            STATUS       current
            DESCRIPTION 
                "get the port id"
            ::= { networkstorage 30 }

        networkstorageUsbInfo4ProductId OBJECT-TYPE
            SYNTAX       DisplayString
            MAX-ACCESS   read-only
            STATUS       current
            DESCRIPTION 
                "get the product id"
            ::= { networkstorage 31 }

        networkstorageUsbInfo4VendorId OBJECT-TYPE
            SYNTAX       DisplayString
            MAX-ACCESS   read-only
            STATUS       current
            DESCRIPTION 
                "get the vendor id"
            ::= { networkstorage 32 }

        networkstorageUsbInfo4Ver OBJECT-TYPE
            SYNTAX       DisplayString
            MAX-ACCESS   read-only
            STATUS       current
            DESCRIPTION 
                "get the version"
            ::= { networkstorage 33 }

        networkstorageUsbInfo4SerialNum OBJECT-TYPE
            SYNTAX       DisplayString
            MAX-ACCESS   read-only
            STATUS       current
            DESCRIPTION 
                "get the serial number"
            ::= { networkstorage 34 }

        networkstorageUsbInfo4Speed OBJECT-TYPE
            SYNTAX       DisplayString
            MAX-ACCESS   read-only
            STATUS       current
            DESCRIPTION 
                "get the speed"
            ::= { networkstorage 35 }

        networkstorageUsbInfo4Manufacturer OBJECT-TYPE
            SYNTAX       DisplayString
            MAX-ACCESS   read-only
            STATUS       current
            DESCRIPTION 
                "get the manufacturer"
            ::= { networkstorage 36 }

        networkstorageUsbInfo4LocationId OBJECT-TYPE
            SYNTAX       DisplayString
            MAX-ACCESS   read-only
            STATUS       current
            DESCRIPTION 
                "get the location id"
            ::= { networkstorage 37 }

        networkstorageUsbInfo4CurrentAvailable OBJECT-TYPE
            SYNTAX       DisplayString
            MAX-ACCESS   read-only
            STATUS       current
            DESCRIPTION 
                "get the current available"
            ::= { networkstorage 38 }

        networkstorageUsbInfo4CurrentRequired OBJECT-TYPE
            SYNTAX       DisplayString
            MAX-ACCESS   read-only
            STATUS       current
            DESCRIPTION 
                "get the current required"
            ::= { networkstorage 39 }

        networkstorageGetstorageattachedTable OBJECT-TYPE
            SYNTAX       SEQUENCE OF NetworkstorageGetstorageattachedEntry
            MAX-ACCESS   not-accessible 
            STATUS       current
            DESCRIPTION 
                "Use this method to get the information for the storages attached
                 to Gateway."
            ::= { networkstorage 40 }

        networkstorageGetstorageattachedEntry OBJECT-TYPE
            SYNTAX       NetworkstorageGetstorageattachedEntry
            MAX-ACCESS   not-accessible 
            STATUS       current
            DESCRIPTION 
                "Entry of table networkstorageGetstorageattached"
            INDEX        { networkstorageGetstorageattachedIndex }
            ::= { networkstorageGetstorageattachedTable 1 }

        NetworkstorageGetstorageattachedEntry ::=
        SEQUENCE {
                networkstorageGetstorageattachedIndex            Integer32,
                networkstorageGetstorageattachedStoragename      DisplayString,
                networkstorageGetstorageattachedFilesystem       DisplayString,
                networkstorageGetstorageattachedSpaceavailable   DisplayString,
                networkstorageGetstorageattachedTotalspace       DisplayString,
                networkstorageGetstorageattachedLocation         DisplayString
        }

        networkstorageGetstorageattachedIndex OBJECT-TYPE
            SYNTAX       Integer32
            MAX-ACCESS   read-only
            STATUS       current
            DESCRIPTION 
                "Index of networkstorageGetstorageattachedEntry."
            ::= { networkstorageGetstorageattachedEntry 1 }

        networkstorageGetstorageattachedStoragename OBJECT-TYPE
            SYNTAX       DisplayString
            MAX-ACCESS   read-write
            STATUS       current
            DESCRIPTION 
                "Write-only object. Reading this object will result in implementation-specific
                 value, generally empty or a string describing the node is write-only.

                 This is the storage name."
            ::= { networkstorageGetstorageattachedEntry 2 }

        networkstorageGetstorageattachedFilesystem OBJECT-TYPE
            SYNTAX       DisplayString
            MAX-ACCESS   read-write
            STATUS       current
            DESCRIPTION 
                "Write-only object. Reading this object will result in implementation-specific
                 value, generally empty or a string describing the node is write-only.

                 This is the File System type."
            ::= { networkstorageGetstorageattachedEntry 3 }

        networkstorageGetstorageattachedSpaceavailable OBJECT-TYPE
            SYNTAX       DisplayString
            MAX-ACCESS   read-write
            STATUS       current
            DESCRIPTION 
                "Write-only object. Reading this object will result in implementation-specific
                 value, generally empty or a string describing the node is write-only.

                 This is the space available."
            ::= { networkstorageGetstorageattachedEntry 4 }

        networkstorageGetstorageattachedTotalspace OBJECT-TYPE
            SYNTAX       DisplayString
            MAX-ACCESS   read-write
            STATUS       current
            DESCRIPTION 
                "Write-only object. Reading this object will result in implementation-specific
                 value, generally empty or a string describing the node is write-only.

                 This is the totalspace."
            ::= { networkstorageGetstorageattachedEntry 5 }

        networkstorageGetstorageattachedLocation OBJECT-TYPE
            SYNTAX       DisplayString
            MAX-ACCESS   read-write
            STATUS       current
            DESCRIPTION 
                "Write-only object. Reading this object will result in implementation-specific
                 value, generally empty or a string describing the node is write-only.

                 This is the location."
            ::= { networkstorageGetstorageattachedEntry 6 }

        networkstorageEditstoragename OBJECT-TYPE
            SYNTAX       DisplayString
            MAX-ACCESS   read-write
            STATUS       current
            DESCRIPTION 
                "Write-only object. Reading this object will result in implementation-specific
                 value, generally empty or a string describing the node is write-only.

                 Edit Storage Name, This the original name to be updated."
            ::= { networkstorage 41 }

        networkstorageEditstoragenameNewstoragename OBJECT-TYPE
            SYNTAX       DisplayString
            MAX-ACCESS   read-write
            STATUS       current
            DESCRIPTION 
                "Write-only object. Reading this object will result in implementation-specific
                 value, generally empty or a string describing the node is write-only.

                 This the new name to update."
            ::= { networkstorage 42 }

        networkstorageDeletestorage OBJECT-TYPE
            SYNTAX       DisplayString
            MAX-ACCESS   read-write
            STATUS       current
            DESCRIPTION 
                "Write-only object. Reading this object will result in implementation-specific
                 value, generally empty or a string describing the node is write-only.

                 Delete the Storeage, This the name to be deleted."
            ::= { networkstorage 43 }

    fileserver OBJECT IDENTIFIER ::= { smcUsgGateway 13 }

        fileserverAfp OBJECT IDENTIFIER ::= { fileserver 1 }

            fileserverAfpReset OBJECT-TYPE
                SYNTAX       TruthValue
                MAX-ACCESS   read-write
                STATUS       current
                DESCRIPTION 
                    "Write-only object. Reading this object will result in implementation-specific
                     value, generally empty or a string describing the node is write-only.

                     Reset the SAMBA File/Printer Sharing
                     feature for entire system"
                ::= { fileserverAfp 1 }

            fileserverAfpRestore OBJECT-TYPE
                SYNTAX       TruthValue
                MAX-ACCESS   read-write
                STATUS       current
                DESCRIPTION 
                    "Write-only object. Reading this object will result in implementation-specific
                     value, generally empty or a string describing the node is write-only.

                     Restore the configuration of the SAMBA
                     File/Printer Sharing feature as default."
                ::= { fileserverAfp 2 }

            fileserverAfpEnbl OBJECT-TYPE
                SYNTAX       TruthValue
                MAX-ACCESS   read-write
                STATUS       current
                DESCRIPTION 
                    "Enable or disable the SAMBA File/Printer
                     Sharing feature for entire system"
                ::= { fileserverAfp 3 }

            fileserverAfpSrvrName OBJECT-TYPE
                SYNTAX       DisplayString
                MAX-ACCESS   read-write
                STATUS       current
                DESCRIPTION 
                    "Name of the server. If this field is left
                     empty the default server is specified."
                ::= { fileserverAfp 4 }

            fileserverAfpAuth OBJECT-TYPE
                SYNTAX       INTEGER {
                    anonymous(1),
                    user(2)
                }
                MAX-ACCESS   read-write
                STATUS       current
                DESCRIPTION 
                    "Authentication method."
                ::= { fileserverAfp 5 }

            fileserverAfpSharedFileTable OBJECT-TYPE
                SYNTAX       SEQUENCE OF FileserverAfpSharedFileEntry
                MAX-ACCESS   not-accessible 
                STATUS       current
                DESCRIPTION 
                    "Shared file"
                ::= { fileserverAfp 6 }

            fileserverAfpSharedFileEntry OBJECT-TYPE
                SYNTAX       FileserverAfpSharedFileEntry
                MAX-ACCESS   not-accessible 
                STATUS       current
                DESCRIPTION 
                    "Entry of table fileserverAfpSharedFile"
                INDEX        { fileserverAfpSharedFileIndex }
                ::= { fileserverAfpSharedFileTable 1 }

            FileserverAfpSharedFileEntry ::=
            SEQUENCE {
                    fileserverAfpSharedFileIndex                     Integer32,
                    fileserverAfpSharedFileRowStatus                 RowStatus,
                    fileserverAfpSharedFileName                      DisplayString,
                    fileserverAfpSharedFilePath                      DisplayString,
                    fileserverAfpSharedFileReadOnlyAccess            TruthValue,
                    fileserverAfpSharedFileAllow                     DisplayString,
                    fileserverAfpSharedFileDeny                      DisplayString
            }

            fileserverAfpSharedFileIndex OBJECT-TYPE
                SYNTAX       Integer32
                MAX-ACCESS   read-only
                STATUS       current
                DESCRIPTION 
                    "Index of fileserverAfpSharedFileEntry."
                ::= { fileserverAfpSharedFileEntry 1 }

            fileserverAfpSharedFileRowStatus OBJECT-TYPE
                SYNTAX       RowStatus
                MAX-ACCESS   read-create
                STATUS       current
                DESCRIPTION 
                    "The status of this conceptual row.
                     Set createAndGo(4) or createAndWait(5) to create a row in this table.
                     Set destroy(6) to delete all of the instances associated with an existing
                     conceptual row."
                ::= { fileserverAfpSharedFileEntry 2 }

            fileserverAfpSharedFileName OBJECT-TYPE
                SYNTAX       DisplayString
                MAX-ACCESS   read-create
                STATUS       current
                DESCRIPTION 
                    "key of this shares"
                ::= { fileserverAfpSharedFileEntry 3 }

            fileserverAfpSharedFilePath OBJECT-TYPE
                SYNTAX       DisplayString
                MAX-ACCESS   read-create
                STATUS       current
                DESCRIPTION 
                    "Path to be shared."
                ::= { fileserverAfpSharedFileEntry 4 }

            fileserverAfpSharedFileReadOnlyAccess OBJECT-TYPE
                SYNTAX       TruthValue
                MAX-ACCESS   read-create
                STATUS       current
                DESCRIPTION 
                    "If this parameter is set to true, then users
                     may not create or modify files in the share.
                     create or modify files in the share."
                ::= { fileserverAfpSharedFileEntry 5 }

            fileserverAfpSharedFileAllow OBJECT-TYPE
                SYNTAX       DisplayString
                MAX-ACCESS   read-create
                STATUS       current
                DESCRIPTION 
                    "This option allows the users and groups that
                     access a share to be specified. Users and
                     groups are specified, delimited by commas.
                     Groups are designated by a @ prefix."
                ::= { fileserverAfpSharedFileEntry 6 }

            fileserverAfpSharedFileDeny OBJECT-TYPE
                SYNTAX       DisplayString
                MAX-ACCESS   read-create
                STATUS       current
                DESCRIPTION 
                    "The deny option specifies users and groups
                     who are not allowed access to the share.
                     It follows the same format as the allow option."
                ::= { fileserverAfpSharedFileEntry 7 }

        fileserverSamba OBJECT IDENTIFIER ::= { fileserver 2 }

            fileserverSambaReset OBJECT-TYPE
                SYNTAX       TruthValue
                MAX-ACCESS   read-write
                STATUS       current
                DESCRIPTION 
                    "Write-only object. Reading this object will result in implementation-specific
                     value, generally empty or a string describing the node is write-only.

                     Reset the SAMBA File/Printer Sharing
                     feature for entire system"
                ::= { fileserverSamba 1 }

            fileserverSambaRestore OBJECT-TYPE
                SYNTAX       TruthValue
                MAX-ACCESS   read-write
                STATUS       current
                DESCRIPTION 
                    "Write-only object. Reading this object will result in implementation-specific
                     value, generally empty or a string describing the node is write-only.

                     Restore the configuration of the SAMBA
                     File/Printer Sharing feature as default."
                ::= { fileserverSamba 2 }

            fileserverSambaIsReady OBJECT-TYPE
                SYNTAX       TruthValue
                MAX-ACCESS   read-only
                STATUS       current
                DESCRIPTION 
                    "Report status whether SAMBA is ready
                     for directory browsing."
                ::= { fileserverSamba 3 }

            fileserverSambaEnbl OBJECT-TYPE
                SYNTAX       TruthValue
                MAX-ACCESS   read-write
                STATUS       current
                DESCRIPTION 
                    "Enable or disable the SAMBA File/Printer
                     Sharing feature for entire system"
                ::= { fileserverSamba 4 }

            fileserverSambaWorkgroup OBJECT-TYPE
                SYNTAX       DisplayString
                MAX-ACCESS   read-write
                STATUS       current
                DESCRIPTION 
                    "the workgroup name of the SAMBA File/Printer
                     Sharing appearing in the Windows network
                     neighborhood. The maximum length of the
                     workgroup name is 15.
                     (maximum 15 characters)."
                ::= { fileserverSamba 5 }

            fileserverSambaNetbiosName OBJECT-TYPE
                SYNTAX       DisplayString
                MAX-ACCESS   read-write
                STATUS       current
                DESCRIPTION 
                    "the NetBIOS name of the SAMBA File/Printer
                     Sharing appearing in the Windows network
                     neighborhood."
                ::= { fileserverSamba 6 }

            fileserverSambaAuth OBJECT-TYPE
                SYNTAX       INTEGER {
                    anonymous(1),
                    user(2)
                }
                MAX-ACCESS   read-write
                STATUS       current
                DESCRIPTION 
                    "Authentication method."
                ::= { fileserverSamba 7 }

            fileserverSambaSharedFileTable OBJECT-TYPE
                SYNTAX       SEQUENCE OF FileserverSambaSharedFileEntry
                MAX-ACCESS   not-accessible 
                STATUS       current
                DESCRIPTION 
                    "Shared file"
                ::= { fileserverSamba 8 }

            fileserverSambaSharedFileEntry OBJECT-TYPE
                SYNTAX       FileserverSambaSharedFileEntry
                MAX-ACCESS   not-accessible 
                STATUS       current
                DESCRIPTION 
                    "Entry of table fileserverSambaSharedFile"
                INDEX        { fileserverSambaSharedFileIndex }
                ::= { fileserverSambaSharedFileTable 1 }

            FileserverSambaSharedFileEntry ::=
            SEQUENCE {
                    fileserverSambaSharedFileIndex                   Integer32,
                    fileserverSambaSharedFileRowStatus               RowStatus,
                    fileserverSambaSharedFileName                    DisplayString,
                    fileserverSambaSharedFilePath                    DisplayString,
                    fileserverSambaSharedFileReadOnlyAccess          TruthValue,
                    fileserverSambaSharedFileDescription             DisplayString,
                    fileserverSambaSharedFileValidUsers              DisplayString,
                    fileserverSambaSharedFileInvalidUsers            DisplayString,
                    fileserverSambaSharedFileUsername                DisplayString,
                    fileserverSambaSharedFilePasswd                  DisplayString,
                    fileserverSambaSharedFileDomain                  DisplayString
            }

            fileserverSambaSharedFileIndex OBJECT-TYPE
                SYNTAX       Integer32
                MAX-ACCESS   read-only
                STATUS       current
                DESCRIPTION 
                    "Index of fileserverSambaSharedFileEntry."
                ::= { fileserverSambaSharedFileEntry 1 }

            fileserverSambaSharedFileRowStatus OBJECT-TYPE
                SYNTAX       RowStatus
                MAX-ACCESS   read-create
                STATUS       current
                DESCRIPTION 
                    "The status of this conceptual row.
                     Set createAndGo(4) or createAndWait(5) to create a row in this table.
                     Set destroy(6) to delete all of the instances associated with an existing
                     conceptual row."
                ::= { fileserverSambaSharedFileEntry 2 }

            fileserverSambaSharedFileName OBJECT-TYPE
                SYNTAX       DisplayString
                MAX-ACCESS   read-create
                STATUS       current
                DESCRIPTION 
                    "key of this shares"
                ::= { fileserverSambaSharedFileEntry 3 }

            fileserverSambaSharedFilePath OBJECT-TYPE
                SYNTAX       DisplayString
                MAX-ACCESS   read-create
                STATUS       current
                DESCRIPTION 
                    "Path to be shared."
                ::= { fileserverSambaSharedFileEntry 4 }

            fileserverSambaSharedFileReadOnlyAccess OBJECT-TYPE
                SYNTAX       TruthValue
                MAX-ACCESS   read-create
                STATUS       current
                DESCRIPTION 
                    "If this parameter is set to true, then users
                     may not create or modify files in the share.
                     create or modify files in the share."
                ::= { fileserverSambaSharedFileEntry 5 }

            fileserverSambaSharedFileDescription OBJECT-TYPE
                SYNTAX       DisplayString
                MAX-ACCESS   read-create
                STATUS       current
                DESCRIPTION 
                    "description of this shares"
                ::= { fileserverSambaSharedFileEntry 6 }

            fileserverSambaSharedFileValidUsers OBJECT-TYPE
                SYNTAX       DisplayString
                MAX-ACCESS   read-create
                STATUS       current
                DESCRIPTION 
                    "This option is a space delimited set of the
                     user(s) which are permitted to access this
                     share."
                ::= { fileserverSambaSharedFileEntry 7 }

            fileserverSambaSharedFileInvalidUsers OBJECT-TYPE
                SYNTAX       DisplayString
                MAX-ACCESS   read-create
                STATUS       current
                DESCRIPTION 
                    "This option is a space delimited set of the
                     user(s) which are NOT permitted to access
                     this share."
                ::= { fileserverSambaSharedFileEntry 8 }

            fileserverSambaSharedFileUsername OBJECT-TYPE
                SYNTAX       DisplayString
                MAX-ACCESS   read-create
                STATUS       current
                DESCRIPTION 
                    "Authenticated user name of the configured
                     device while sharing the Windows resource."
                ::= { fileserverSambaSharedFileEntry 9 }

            fileserverSambaSharedFilePasswd OBJECT-TYPE
                SYNTAX       DisplayString
                MAX-ACCESS   read-create
                STATUS       current
                DESCRIPTION 
                    "Authenticated password of the configured
                     device while sharing the Windows resource."
                ::= { fileserverSambaSharedFileEntry 10 }

            fileserverSambaSharedFileDomain OBJECT-TYPE
                SYNTAX       DisplayString
                MAX-ACCESS   read-create
                STATUS       current
                DESCRIPTION 
                    "Authenticated domain or workgroup of the
                     configured device while sharing the
                     Windows resource."
                ::= { fileserverSambaSharedFileEntry 11 }

            fileserverSambaShowinfo OBJECT IDENTIFIER ::= { fileserverSamba 9 }

                fileserverSambaShowinfoOtherSpaceTable OBJECT-TYPE
                    SYNTAX       SEQUENCE OF FileserverSambaShowinfoOtherSpaceEntry
                    MAX-ACCESS   not-accessible 
                    STATUS       current
                    DESCRIPTION 
                        "Show other storage on the network"
                    ::= { fileserverSambaShowinfo 1 }

                fileserverSambaShowinfoOtherSpaceEntry OBJECT-TYPE
                    SYNTAX       FileserverSambaShowinfoOtherSpaceEntry
                    MAX-ACCESS   not-accessible 
                    STATUS       current
                    DESCRIPTION 
                        "Entry of table fileserverSambaShowinfoOtherSpace"
                    INDEX        { fileserverSambaShowinfoOtherSpaceIndex }
                    ::= { fileserverSambaShowinfoOtherSpaceTable 1 }

                FileserverSambaShowinfoOtherSpaceEntry ::=
                SEQUENCE {
                        fileserverSambaShowinfoOtherSpaceIndex           Integer32,
                        fileserverSambaShowinfoOtherSpaceName            DisplayString,
                        fileserverSambaShowinfoOtherSpaceFilesys         DisplayString,
                        fileserverSambaShowinfoOtherSpaceLeftSpace       DisplayString,
                        fileserverSambaShowinfoOtherSpaceTotalSpace      DisplayString,
                        fileserverSambaShowinfoOtherSpaceLocation        DisplayString,
                        fileserverSambaShowinfoOtherSpaceProto           DisplayString
                }

                fileserverSambaShowinfoOtherSpaceIndex OBJECT-TYPE
                    SYNTAX       Integer32
                    MAX-ACCESS   read-only
                    STATUS       current
                    DESCRIPTION 
                        "Index of fileserverSambaShowinfoOtherSpaceEntry."
                    ::= { fileserverSambaShowinfoOtherSpaceEntry 1 }

                fileserverSambaShowinfoOtherSpaceName OBJECT-TYPE
                    SYNTAX       DisplayString
                    MAX-ACCESS   read-only
                    STATUS       current
                    DESCRIPTION 
                        "Key of the shared storage on the network"
                    ::= { fileserverSambaShowinfoOtherSpaceEntry 2 }

                fileserverSambaShowinfoOtherSpaceFilesys OBJECT-TYPE
                    SYNTAX       DisplayString
                    MAX-ACCESS   read-only
                    STATUS       current
                    DESCRIPTION 
                        "Filesystem type of the storage"
                    ::= { fileserverSambaShowinfoOtherSpaceEntry 3 }

                fileserverSambaShowinfoOtherSpaceLeftSpace OBJECT-TYPE
                    SYNTAX       DisplayString
                    MAX-ACCESS   read-only
                    STATUS       current
                    DESCRIPTION 
                        "Available space in KB of the storage"
                    ::= { fileserverSambaShowinfoOtherSpaceEntry 4 }

                fileserverSambaShowinfoOtherSpaceTotalSpace OBJECT-TYPE
                    SYNTAX       DisplayString
                    MAX-ACCESS   read-only
                    STATUS       current
                    DESCRIPTION 
                        "Available space in KB of the storage"
                    ::= { fileserverSambaShowinfoOtherSpaceEntry 5 }

                fileserverSambaShowinfoOtherSpaceLocation OBJECT-TYPE
                    SYNTAX       DisplayString
                    MAX-ACCESS   read-only
                    STATUS       current
                    DESCRIPTION 
                        "Location of the storage"
                    ::= { fileserverSambaShowinfoOtherSpaceEntry 6 }

                fileserverSambaShowinfoOtherSpaceProto OBJECT-TYPE
                    SYNTAX       DisplayString
                    MAX-ACCESS   read-only
                    STATUS       current
                    DESCRIPTION 
                        "Protocol of the storage"
                    ::= { fileserverSambaShowinfoOtherSpaceEntry 7 }

        fileserverFtp OBJECT IDENTIFIER ::= { fileserver 3 }

            fileserverFtpEnbl OBJECT-TYPE
                SYNTAX       TruthValue
                MAX-ACCESS   read-write
                STATUS       current
                DESCRIPTION 
                    "enable/disable FTP server"
                ::= { fileserverFtp 1 }

            fileserverFtpTcpPort OBJECT-TYPE
                SYNTAX       Integer32
                MAX-ACCESS   read-write
                STATUS       current
                DESCRIPTION 
                    "the TCP port number that the FTP server listen to, default is
                     21."
                ::= { fileserverFtp 2 }

            fileserverFtpMaxClients OBJECT-TYPE
                SYNTAX       Integer32
                MAX-ACCESS   read-write
                STATUS       current
                DESCRIPTION 
                    "maximum number of simultaneous clients for FTP server."
                ::= { fileserverFtp 3 }

            fileserverFtpMaxConns OBJECT-TYPE
                SYNTAX       Integer32
                MAX-ACCESS   read-write
                STATUS       current
                DESCRIPTION 
                    "maximum number of connections per IP address (0 = unlimited)."
                ::= { fileserverFtp 4 }

            fileserverFtpIdleTmout OBJECT-TYPE
                SYNTAX       Integer32
                MAX-ACCESS   read-write
                STATUS       current
                DESCRIPTION 
                    "maximum idle timeout in seconds."
                ::= { fileserverFtp 5 }

            fileserverFtpDataTmout OBJECT-TYPE
                SYNTAX       Integer32
                MAX-ACCESS   read-write
                STATUS       current
                DESCRIPTION 
                    "maximum data timeout in seconds."
                ::= { fileserverFtp 6 }

            fileserverFtpAnonOnly OBJECT-TYPE
                SYNTAX       TruthValue
                MAX-ACCESS   read-write
                STATUS       current
                DESCRIPTION 
                    "only allow anonymous users. Use this on a public FTP site with
                     no remote FTP access to real accounts."
                ::= { fileserverFtp 7 }

            fileserverFtpLocalOnly OBJECT-TYPE
                SYNTAX       TruthValue
                MAX-ACCESS   read-write
                STATUS       current
                DESCRIPTION 
                    "only allow authenticated users. Anonymous logins are prohibited."
                ::= { fileserverFtp 8 }

            fileserverFtpBanner OBJECT-TYPE
                SYNTAX       DisplayString
                MAX-ACCESS   read-write
                STATUS       current
                DESCRIPTION 
                    "greeting banner displayed by FTP when a connection first comes
                     in."
                ::= { fileserverFtp 9 }

            fileserverFtpWrite OBJECT-TYPE
                SYNTAX       TruthValue
                MAX-ACCESS   read-write
                STATUS       current
                DESCRIPTION 
                    "enable/disable any form of FTP write command."
                ::= { fileserverFtp 10 }

            fileserverFtpAnonMask OBJECT-TYPE
                SYNTAX       DisplayString
                MAX-ACCESS   read-write
                STATUS       current
                DESCRIPTION 
                    "use this option to override anonymous creation mask (077 by default)."
                ::= { fileserverFtp 11 }

            fileserverFtpLocalMask OBJECT-TYPE
                SYNTAX       DisplayString
                MAX-ACCESS   read-write
                STATUS       current
                DESCRIPTION 
                    "use this option to override local creation mask (022 by default)."
                ::= { fileserverFtp 12 }

            fileserverFtpAnonUpload OBJECT-TYPE
                SYNTAX       TruthValue
                MAX-ACCESS   read-write
                STATUS       current
                DESCRIPTION 
                    "use this option to allow the anonymous FTP user to upload files."
                ::= { fileserverFtp 13 }

            fileserverFtpAnonMkdir OBJECT-TYPE
                SYNTAX       TruthValue
                MAX-ACCESS   read-write
                STATUS       current
                DESCRIPTION 
                    "use this option to allow the anonymous FTP user to be able to
                     create new directories."
                ::= { fileserverFtp 14 }

        fileserverSmart OBJECT IDENTIFIER ::= { fileserver 4 }

            fileserverSmartEnbl OBJECT-TYPE
                SYNTAX       TruthValue
                MAX-ACCESS   read-write
                STATUS       current
                DESCRIPTION 
                    "enable/disable S.M.A.R.T."
                ::= { fileserverSmart 1 }

            fileserverSmartCheckInterval OBJECT-TYPE
                SYNTAX       Integer32
                MAX-ACCESS   read-write
                STATUS       current
                DESCRIPTION 
                    "sets the interval between disk checks to N seconds. The minimum
                     allowed value is 10."
                ::= { fileserverSmart 2 }

            fileserverSmartPowerMode OBJECT-TYPE
                SYNTAX       INTEGER {
                    never(1),
                    sleep(2),
                    standby(3),
                    idle(4)
                }
                MAX-ACCESS   read-write
                STATUS       current
                DESCRIPTION 
                    "
                     never - Poll (check) the device regardless of its power mode.
                     This may cause a disk which is spun-down to be spun-up when
                     it is checked.
                     sleep - Check the device unless it is in SLEEP mode.
                     standby - Check the device unless it is in SLEEP or STANDBY mode.
                     In these modes most disks are not spinning, so if you want
                     to prevent a laptop disk from spinning up each poll, this
                     is probably what you want.
                     idle - Check the device unless it is in SLEEP, STANDBY or IDLE
                     mode. In the IDLE state, most disks are still spinning, so
                     this is probably not what you want."
                ::= { fileserverSmart 3 }

            fileserverSmartDifference OBJECT-TYPE
                SYNTAX       Integer32
                MAX-ACCESS   read-write
                STATUS       current
                DESCRIPTION 
                    "report if the temperature had changed by at least N degrees Celsius
                     since last report. Set to 0 to disable this report."
                ::= { fileserverSmart 4 }

            fileserverSmartInformal OBJECT-TYPE
                SYNTAX       Integer32
                MAX-ACCESS   read-write
                STATUS       current
                DESCRIPTION 
                    "report if the temperature is greater or equal than N degrees
                     Celsius. Set to 0 to disable this report."
                ::= { fileserverSmart 5 }

            fileserverSmartCritical OBJECT-TYPE
                SYNTAX       Integer32
                MAX-ACCESS   read-write
                STATUS       current
                DESCRIPTION 
                    "report if the temperature is greater or equal than N degrees
                     Celsius. Set to 0 to disable this report."
                ::= { fileserverSmart 6 }

            fileserverSmartScheduleMonitorTable OBJECT-TYPE
                SYNTAX       SEQUENCE OF FileserverSmartScheduleMonitorEntry
                MAX-ACCESS   not-accessible 
                STATUS       current
                DESCRIPTION 
                    "schedule for S.M.A.R.T to monitor."
                ::= { fileserverSmart 7 }

            fileserverSmartScheduleMonitorEntry OBJECT-TYPE
                SYNTAX       FileserverSmartScheduleMonitorEntry
                MAX-ACCESS   not-accessible 
                STATUS       current
                DESCRIPTION 
                    "Entry of table fileserverSmartScheduleMonitor"
                INDEX        { fileserverSmartScheduleMonitorIndex }
                ::= { fileserverSmartScheduleMonitorTable 1 }

            FileserverSmartScheduleMonitorEntry ::=
            SEQUENCE {
                    fileserverSmartScheduleMonitorIndex              Integer32,
                    fileserverSmartScheduleMonitorRowStatus          RowStatus,
                    fileserverSmartScheduleMonitorDisk               DisplayString,
                    fileserverSmartScheduleMonitorType               INTEGER,
                    fileserverSmartScheduleMonitorHours              DisplayString,
                    fileserverSmartScheduleMonitorDays               DisplayString,
                    fileserverSmartScheduleMonitorMonths             DisplayString,
                    fileserverSmartScheduleMonitorWeekDays           DisplayString
            }

            fileserverSmartScheduleMonitorIndex OBJECT-TYPE
                SYNTAX       Integer32
                MAX-ACCESS   read-only
                STATUS       current
                DESCRIPTION 
                    "Index of fileserverSmartScheduleMonitorEntry."
                ::= { fileserverSmartScheduleMonitorEntry 1 }

            fileserverSmartScheduleMonitorRowStatus OBJECT-TYPE
                SYNTAX       RowStatus
                MAX-ACCESS   read-create
                STATUS       current
                DESCRIPTION 
                    "The status of this conceptual row.
                     Set createAndGo(4) or createAndWait(5) to create a row in this table.
                     Set destroy(6) to delete all of the instances associated with an existing
                     conceptual row."
                ::= { fileserverSmartScheduleMonitorEntry 2 }

            fileserverSmartScheduleMonitorDisk OBJECT-TYPE
                SYNTAX       DisplayString
                MAX-ACCESS   read-create
                STATUS       current
                DESCRIPTION 
                    "select a disk that is enabled for S.M.A.R.T. monitoring"
                ::= { fileserverSmartScheduleMonitorEntry 3 }

            fileserverSmartScheduleMonitorType OBJECT-TYPE
                SYNTAX       INTEGER {
                    short-selftest(1),
                    long-selftest(2),
                    convey-selftest(3),
                    offline-immediate(4)
                }
                MAX-ACCESS   read-create
                STATUS       current
                DESCRIPTION 
                    "type of S.M.A.R.T monitoring."
                ::= { fileserverSmartScheduleMonitorEntry 4 }

            fileserverSmartScheduleMonitorHours OBJECT-TYPE
                SYNTAX       DisplayString
                MAX-ACCESS   read-create
                STATUS       current
                DESCRIPTION 
                    "setting hours to monitor per day. Multiple values and delimited
                     by comma(,). 0 : 0 o'clock, 1 : 1 o'clock, 2 : 2 o'clock,
                     ..., 23 : 23 o'clock. all means 0 to 23."
                ::= { fileserverSmartScheduleMonitorEntry 5 }

            fileserverSmartScheduleMonitorDays OBJECT-TYPE
                SYNTAX       DisplayString
                MAX-ACCESS   read-create
                STATUS       current
                DESCRIPTION 
                    "setting days to monitor per month. Multiple values and delimited
                     by comma(,). 1 : 1st day in month, 2 : 2nd day in month,
                     3 : 3rd day in month, ..., 31 : 31th day in month. all mean
                     whole month."
                ::= { fileserverSmartScheduleMonitorEntry 6 }

            fileserverSmartScheduleMonitorMonths OBJECT-TYPE
                SYNTAX       DisplayString
                MAX-ACCESS   read-create
                STATUS       current
                DESCRIPTION 
                    "setting months to monitor per year. Multiple values and delimited
                     by comma(,). jan : january, feb : february, mar : march,
                     ..., dec : december. all means the whole year."
                ::= { fileserverSmartScheduleMonitorEntry 7 }

            fileserverSmartScheduleMonitorWeekDays OBJECT-TYPE
                SYNTAX       DisplayString
                MAX-ACCESS   read-create
                STATUS       current
                DESCRIPTION 
                    "setting week days to monitor. Multiple values and delimited by
                     comma(,). sun : Sunday, mon : Monday, ..., sat : Saturday.
                     all means the whole week."
                ::= { fileserverSmartScheduleMonitorEntry 8 }

    mediaserver OBJECT IDENTIFIER ::= { smcUsgGateway 14 }

        mediaserverStatus OBJECT-TYPE
            SYNTAX       TruthValue
            MAX-ACCESS   read-write
            STATUS       current
            DESCRIPTION 
                "enable/disable mediaservers feature module"
            ::= { mediaserver 1 }

        mediaserverDlnaserverstatus OBJECT-TYPE
            SYNTAX       TruthValue
            MAX-ACCESS   read-write
            STATUS       current
            DESCRIPTION 
                "enable/disable DLNA mediaserver"
            ::= { mediaserver 2 }

        mediaserverDlnaservername OBJECT-TYPE
            SYNTAX       DisplayString
            MAX-ACCESS   read-write
            STATUS       current
            DESCRIPTION 
                "configure DLNA mediaserver name"
            ::= { mediaserver 3 }

        mediaserverDlnaserverfilelocation OBJECT-TYPE
            SYNTAX       DisplayString
            MAX-ACCESS   read-write
            STATUS       current
            DESCRIPTION 
                "configure DLNA mediaserver file location"
            ::= { mediaserver 4 }

        mediaserverDlnafilterenable OBJECT-TYPE
            SYNTAX       TruthValue
            MAX-ACCESS   read-write
            STATUS       current
            DESCRIPTION 
                "enable/disable DLNA media compliance filtering"
            ::= { mediaserver 5 }

        mediaserverListupnpdmsTable OBJECT-TYPE
            SYNTAX       SEQUENCE OF MediaserverListupnpdmsEntry
            MAX-ACCESS   not-accessible 
            STATUS       current
            DESCRIPTION 
                "list all located UPnP servers"
            ::= { mediaserver 6 }

        mediaserverListupnpdmsEntry OBJECT-TYPE
            SYNTAX       MediaserverListupnpdmsEntry
            MAX-ACCESS   not-accessible 
            STATUS       current
            DESCRIPTION 
                "Entry of table mediaserverListupnpdms"
            INDEX        { mediaserverListupnpdmsIndex }
            ::= { mediaserverListupnpdmsTable 1 }

        MediaserverListupnpdmsEntry ::=
        SEQUENCE {
                mediaserverListupnpdmsIndex                      Integer32,
                mediaserverListupnpdmsRowStatus                  RowStatus,
                mediaserverListupnpdmsDmsnumber                  Integer32,
                mediaserverListupnpdmsDmsname                    DisplayString
        }

        mediaserverListupnpdmsIndex OBJECT-TYPE
            SYNTAX       Integer32
            MAX-ACCESS   read-only
            STATUS       current
            DESCRIPTION 
                "Index of mediaserverListupnpdmsEntry."
            ::= { mediaserverListupnpdmsEntry 1 }

        mediaserverListupnpdmsRowStatus OBJECT-TYPE
            SYNTAX       RowStatus
            MAX-ACCESS   read-create
            STATUS       current
            DESCRIPTION 
                "The status of this conceptual row.
                 Set createAndGo(4) or createAndWait(5) to create a row in this table.
                 Set destroy(6) to delete all of the instances associated with an existing
                 conceptual row."
            ::= { mediaserverListupnpdmsEntry 2 }

        mediaserverListupnpdmsDmsnumber OBJECT-TYPE
            SYNTAX       Integer32
            MAX-ACCESS   read-create
            STATUS       current
            DESCRIPTION 
                "UPnP server number"
            ::= { mediaserverListupnpdmsEntry 3 }

        mediaserverListupnpdmsDmsname OBJECT-TYPE
            SYNTAX       DisplayString
            MAX-ACCESS   read-create
            STATUS       current
            DESCRIPTION 
                "UPnP server name"
            ::= { mediaserverListupnpdmsEntry 4 }

        mediaserverListupnpdmpTable OBJECT-TYPE
            SYNTAX       SEQUENCE OF MediaserverListupnpdmpEntry
            MAX-ACCESS   not-accessible 
            STATUS       current
            DESCRIPTION 
                "list all located UPnP players"
            ::= { mediaserver 7 }

        mediaserverListupnpdmpEntry OBJECT-TYPE
            SYNTAX       MediaserverListupnpdmpEntry
            MAX-ACCESS   not-accessible 
            STATUS       current
            DESCRIPTION 
                "Entry of table mediaserverListupnpdmp"
            INDEX        { mediaserverListupnpdmpIndex }
            ::= { mediaserverListupnpdmpTable 1 }

        MediaserverListupnpdmpEntry ::=
        SEQUENCE {
                mediaserverListupnpdmpIndex                      Integer32,
                mediaserverListupnpdmpRowStatus                  RowStatus,
                mediaserverListupnpdmpDmpnumber                  Integer32,
                mediaserverListupnpdmpDmpname                    DisplayString
        }

        mediaserverListupnpdmpIndex OBJECT-TYPE
            SYNTAX       Integer32
            MAX-ACCESS   read-only
            STATUS       current
            DESCRIPTION 
                "Index of mediaserverListupnpdmpEntry."
            ::= { mediaserverListupnpdmpEntry 1 }

        mediaserverListupnpdmpRowStatus OBJECT-TYPE
            SYNTAX       RowStatus
            MAX-ACCESS   read-create
            STATUS       current
            DESCRIPTION 
                "The status of this conceptual row.
                 Set createAndGo(4) or createAndWait(5) to create a row in this table.
                 Set destroy(6) to delete all of the instances associated with an existing
                 conceptual row."
            ::= { mediaserverListupnpdmpEntry 2 }

        mediaserverListupnpdmpDmpnumber OBJECT-TYPE
            SYNTAX       Integer32
            MAX-ACCESS   read-create
            STATUS       current
            DESCRIPTION 
                "UPnP player number"
            ::= { mediaserverListupnpdmpEntry 3 }

        mediaserverListupnpdmpDmpname OBJECT-TYPE
            SYNTAX       DisplayString
            MAX-ACCESS   read-create
            STATUS       current
            DESCRIPTION 
                "UPnP player name"
            ::= { mediaserverListupnpdmpEntry 4 }

        mediaserverFireflystatus OBJECT-TYPE
            SYNTAX       TruthValue
            MAX-ACCESS   read-write
            STATUS       current
            DESCRIPTION 
                "enable/disable Firefly/iTunes server"
            ::= { mediaserver 8 }

        mediaserverFireflyservername OBJECT-TYPE
            SYNTAX       DisplayString
            MAX-ACCESS   read-write
            STATUS       current
            DESCRIPTION 
                "configure Firefly/iTunes name"
            ::= { mediaserver 9 }

        mediaserverFireflymediapassword OBJECT-TYPE
            SYNTAX       DisplayString
            MAX-ACCESS   read-write
            STATUS       current
            DESCRIPTION 
                "access password to Firefly/iTunes mediaserver"
            ::= { mediaserver 10 }

        mediaserverFireflyserverfilelocation OBJECT-TYPE
            SYNTAX       DisplayString
            MAX-ACCESS   read-write
            STATUS       current
            DESCRIPTION 
                "configure Firefly/iTunes mediaserver file location"
            ::= { mediaserver 11 }

        mediaserverFireflyplaylistenable OBJECT-TYPE
            SYNTAX       TruthValue
            MAX-ACCESS   read-write
            STATUS       current
            DESCRIPTION 
                "Firefly/iTunes playlists enable/disable"
            ::= { mediaserver 12 }

        mediaserverFireflyplaylistTable OBJECT-TYPE
            SYNTAX       SEQUENCE OF MediaserverFireflyplaylistEntry
            MAX-ACCESS   not-accessible 
            STATUS       current
            DESCRIPTION 
                "list Firefly/iTunes playlists"
            ::= { mediaserver 13 }

        mediaserverFireflyplaylistEntry OBJECT-TYPE
            SYNTAX       MediaserverFireflyplaylistEntry
            MAX-ACCESS   not-accessible 
            STATUS       current
            DESCRIPTION 
                "Entry of table mediaserverFireflyplaylist"
            INDEX        { mediaserverFireflyplaylistIndex }
            ::= { mediaserverFireflyplaylistTable 1 }

        MediaserverFireflyplaylistEntry ::=
        SEQUENCE {
                mediaserverFireflyplaylistIndex                  Integer32,
                mediaserverFireflyplaylistRowStatus              RowStatus,
                mediaserverFireflyplaylistFfplaylistnumber       Integer32,
                mediaserverFireflyplaylistFfplaylistcategory     DisplayString,
                mediaserverFireflyplaylistFfplaylistname         DisplayString
        }

        mediaserverFireflyplaylistIndex OBJECT-TYPE
            SYNTAX       Integer32
            MAX-ACCESS   read-only
            STATUS       current
            DESCRIPTION 
                "Index of mediaserverFireflyplaylistEntry."
            ::= { mediaserverFireflyplaylistEntry 1 }

        mediaserverFireflyplaylistRowStatus OBJECT-TYPE
            SYNTAX       RowStatus
            MAX-ACCESS   read-create
            STATUS       current
            DESCRIPTION 
                "The status of this conceptual row.
                 Set createAndGo(4) or createAndWait(5) to create a row in this table.
                 Set destroy(6) to delete all of the instances associated with an existing
                 conceptual row."
            ::= { mediaserverFireflyplaylistEntry 2 }

        mediaserverFireflyplaylistFfplaylistnumber OBJECT-TYPE
            SYNTAX       Integer32
            MAX-ACCESS   read-create
            STATUS       current
            DESCRIPTION 
                "playlist number"
            ::= { mediaserverFireflyplaylistEntry 3 }

        mediaserverFireflyplaylistFfplaylistcategory OBJECT-TYPE
            SYNTAX       DisplayString
            MAX-ACCESS   read-create
            STATUS       current
            DESCRIPTION 
                "iTunes library category"
            ::= { mediaserverFireflyplaylistEntry 4 }

        mediaserverFireflyplaylistFfplaylistname OBJECT-TYPE
            SYNTAX       DisplayString
            MAX-ACCESS   read-create
            STATUS       current
            DESCRIPTION 
                "iTunes playlist name"
            ::= { mediaserverFireflyplaylistEntry 5 }

        mediaserverTemplateVer OBJECT-TYPE
            SYNTAX       Integer32
            MAX-ACCESS   read-write
            STATUS       current
            DESCRIPTION 
                "template version 6"
            ::= { mediaserver 14 }

    battery OBJECT IDENTIFIER ::= { smcUsgGateway 15 }

        batteryOneWire OBJECT-TYPE
            SYNTAX       DisplayString
            MAX-ACCESS   read-only
            STATUS       current
            DESCRIPTION 
                "Show the battery info"
            ::= { battery 1 }

        batteryBatteryStatus OBJECT-TYPE
            SYNTAX       DisplayString
            MAX-ACCESS   read-only
            STATUS       current
            DESCRIPTION 
                "Show the battery status"
            ::= { battery 2 }

        batteryBatteryInsert OBJECT-TYPE
            SYNTAX       DisplayString
            MAX-ACCESS   read-only
            STATUS       current
            DESCRIPTION 
                "See if battery insert or not"
            ::= { battery 3 }

        batteryBatteryCondition OBJECT-TYPE
            SYNTAX       DisplayString
            MAX-ACCESS   read-only
            STATUS       current
            DESCRIPTION 
                "Show the condition of battery"
            ::= { battery 4 }

        batteryBatteryRemaincharge OBJECT-TYPE
            SYNTAX       DisplayString
            MAX-ACCESS   read-only
            STATUS       current
            DESCRIPTION 
                "Show the percentage of battery"
            ::= { battery 5 }

        batteryBatteryRemaintime OBJECT-TYPE
            SYNTAX       DisplayString
            MAX-ACCESS   read-only
            STATUS       current
            DESCRIPTION 
                "Show the remaintime of battery"
            ::= { battery 6 }

        batteryBatteryModelID OBJECT-TYPE
            SYNTAX       DisplayString
            MAX-ACCESS   read-only
            STATUS       current
            DESCRIPTION 
                "Show the battery Model Name"
            ::= { battery 7 }

    docsis OBJECT IDENTIFIER ::= { smcUsgGateway 16 }

        docsisNetwork OBJECT IDENTIFIER ::= { docsis 1 }

            docsisNetworkInternetStatus OBJECT-TYPE
                SYNTAX       DisplayString
                MAX-ACCESS   read-only
                STATUS       current
                DESCRIPTION 
                    "get the operational status of network"
                ::= { docsisNetwork 1 }

            docsisNetworkSpeedTier OBJECT-TYPE
                SYNTAX       DisplayString
                MAX-ACCESS   read-only
                STATUS       current
                DESCRIPTION 
                    "get the speed tier"
                ::= { docsisNetwork 2 }

            docsisNetworkSysUptime OBJECT-TYPE
                SYNTAX       DisplayString
                MAX-ACCESS   read-only
                STATUS       current
                DESCRIPTION 
                    "get the system up time"
                ::= { docsisNetwork 3 }

            docsisNetworkWanipAddr OBJECT-TYPE
                SYNTAX       DisplayString
                MAX-ACCESS   read-only
                STATUS       current
                DESCRIPTION 
                    "get the wan ip address"
                ::= { docsisNetwork 4 }

            docsisNetworkDhcpClientStatus OBJECT-TYPE
                SYNTAX       DisplayString
                MAX-ACCESS   read-only
                STATUS       current
                DESCRIPTION 
                    "get the status of dhcp client"
                ::= { docsisNetwork 5 }

            docsisNetworkDhcpExpireTime OBJECT-TYPE
                SYNTAX       DisplayString
                MAX-ACCESS   read-only
                STATUS       current
                DESCRIPTION 
                    "get the dhcp expire time"
                ::= { docsisNetwork 6 }

            docsisNetworkCmMac OBJECT-TYPE
                SYNTAX       DisplayString
                MAX-ACCESS   read-only
                STATUS       current
                DESCRIPTION 
                    "get the cm mac address"
                ::= { docsisNetwork 7 }

            docsisNetworkEmtaMac OBJECT-TYPE
                SYNTAX       DisplayString
                MAX-ACCESS   read-only
                STATUS       current
                DESCRIPTION 
                    "get the emta mac address"
                ::= { docsisNetwork 8 }

            docsisNetworkRfMac OBJECT-TYPE
                SYNTAX       DisplayString
                MAX-ACCESS   read-only
                STATUS       current
                DESCRIPTION 
                    "get the rf mac address"
                ::= { docsisNetwork 9 }

        docsisCableModem OBJECT IDENTIFIER ::= { docsis 2 }

            docsisCableModemHwVer OBJECT-TYPE
                SYNTAX       DisplayString
                MAX-ACCESS   read-only
                STATUS       current
                DESCRIPTION 
                    "get the hw version"
                ::= { docsisCableModem 1 }

            docsisCableModemVendor OBJECT-TYPE
                SYNTAX       DisplayString
                MAX-ACCESS   read-only
                STATUS       current
                DESCRIPTION 
                    "get the vendor name"
                ::= { docsisCableModem 2 }

            docsisCableModemBootVer OBJECT-TYPE
                SYNTAX       DisplayString
                MAX-ACCESS   read-only
                STATUS       current
                DESCRIPTION 
                    "get the boot version"
                ::= { docsisCableModem 3 }

            docsisCableModemCoreVer OBJECT-TYPE
                SYNTAX       DisplayString
                MAX-ACCESS   read-only
                STATUS       current
                DESCRIPTION 
                    "get the core version"
                ::= { docsisCableModem 4 }

            docsisCableModemModel OBJECT-TYPE
                SYNTAX       DisplayString
                MAX-ACCESS   read-only
                STATUS       current
                DESCRIPTION 
                    "get the model name"
                ::= { docsisCableModem 5 }

            docsisCableModemProductType OBJECT-TYPE
                SYNTAX       DisplayString
                MAX-ACCESS   read-only
                STATUS       current
                DESCRIPTION 
                    "get the product type"
                ::= { docsisCableModem 6 }

            docsisCableModemFlashPart OBJECT-TYPE
                SYNTAX       DisplayString
                MAX-ACCESS   read-only
                STATUS       current
                DESCRIPTION 
                    "get the flash part"
                ::= { docsisCableModem 7 }

            docsisCableModemDloadVer OBJECT-TYPE
                SYNTAX       DisplayString
                MAX-ACCESS   read-only
                STATUS       current
                DESCRIPTION 
                    "get the download version"
                ::= { docsisCableModem 8 }

            docsisCableModemSerialNum OBJECT-TYPE
                SYNTAX       DisplayString
                MAX-ACCESS   read-only
                STATUS       current
                DESCRIPTION 
                    "get the serial num"
                ::= { docsisCableModem 9 }

            docsisCableModemSysdescr OBJECT-TYPE
                SYNTAX       DisplayString
                MAX-ACCESS   read-only
                STATUS       current
                DESCRIPTION 
                    "get the system description"
                ::= { docsisCableModem 10 }

        docsisDownStream OBJECT IDENTIFIER ::= { docsis 3 }

            docsisDownStreamChannelId OBJECT-TYPE
                SYNTAX       DisplayString
                MAX-ACCESS   read-only
                STATUS       current
                DESCRIPTION 
                    "get the channel id"
                ::= { docsisDownStream 1 }

            docsisDownStreamFrequency OBJECT-TYPE
                SYNTAX       DisplayString
                MAX-ACCESS   read-only
                STATUS       current
                DESCRIPTION 
                    "get the frequency"
                ::= { docsisDownStream 2 }

            docsisDownStreamSnr OBJECT-TYPE
                SYNTAX       DisplayString
                MAX-ACCESS   read-only
                STATUS       current
                DESCRIPTION 
                    "get the SNR"
                ::= { docsisDownStream 3 }

            docsisDownStreamPower OBJECT-TYPE
                SYNTAX       DisplayString
                MAX-ACCESS   read-only
                STATUS       current
                DESCRIPTION 
                    "get the power"
                ::= { docsisDownStream 4 }

            docsisDownStreamModulation OBJECT-TYPE
                SYNTAX       DisplayString
                MAX-ACCESS   read-only
                STATUS       current
                DESCRIPTION 
                    "get the modulation"
                ::= { docsisDownStream 5 }

        docsisUpStream OBJECT IDENTIFIER ::= { docsis 4 }

            docsisUpStreamChannelId OBJECT-TYPE
                SYNTAX       DisplayString
                MAX-ACCESS   read-only
                STATUS       current
                DESCRIPTION 
                    "get the channel id"
                ::= { docsisUpStream 1 }

            docsisUpStreamFrequency OBJECT-TYPE
                SYNTAX       DisplayString
                MAX-ACCESS   read-only
                STATUS       current
                DESCRIPTION 
                    "get the frequency"
                ::= { docsisUpStream 2 }

            docsisUpStreamRangingSrvcId OBJECT-TYPE
                SYNTAX       DisplayString
                MAX-ACCESS   read-only
                STATUS       current
                DESCRIPTION 
                    "get the ranging service id"
                ::= { docsisUpStream 3 }

            docsisUpStreamSymbolRate OBJECT-TYPE
                SYNTAX       DisplayString
                MAX-ACCESS   read-only
                STATUS       current
                DESCRIPTION 
                    "get the symbol rate"
                ::= { docsisUpStream 4 }

            docsisUpStreamPowerLevel OBJECT-TYPE
                SYNTAX       DisplayString
                MAX-ACCESS   read-only
                STATUS       current
                DESCRIPTION 
                    "get the power level"
                ::= { docsisUpStream 5 }

            docsisUpStreamModulation OBJECT-TYPE
                SYNTAX       DisplayString
                MAX-ACCESS   read-only
                STATUS       current
                DESCRIPTION 
                    "get the modulation"
                ::= { docsisUpStream 6 }

            docsisUpStreamRangingStatus OBJECT-TYPE
                SYNTAX       DisplayString
                MAX-ACCESS   read-only
                STATUS       current
                DESCRIPTION 
                    "get the ranging status"
                ::= { docsisUpStream 7 }

            docsisUpStreamTheMap OBJECT-TYPE
                SYNTAX       DisplayString
                MAX-ACCESS   read-only
                STATUS       current
                DESCRIPTION 
                    "get the map"
                ::= { docsisUpStream 8 }

            docsisUpStreamModuleType OBJECT-TYPE
                SYNTAX       DisplayString
                MAX-ACCESS   read-only
                STATUS       current
                DESCRIPTION 
                    "get the module type"
                ::= { docsisUpStream 9 }

    moca OBJECT IDENTIFIER ::= { smcUsgGateway 17 }

        mocaEnbl OBJECT-TYPE
            SYNTAX       TruthValue
            MAX-ACCESS   read-write
            STATUS       current
            DESCRIPTION 
                "enable/disable MoCA"
            ::= { moca 1 }

        mocaBand OBJECT-TYPE
            SYNTAX       Integer32
            MAX-ACCESS   read-write
            STATUS       current
            DESCRIPTION 
                "setup D BAND from 1150MHz to 1500MHz,15:1150MHz,17:1200MHz ...29:1500MHz,0:SCAN
                 ALL"
            ::= { moca 2 }

        mocaMacaddr OBJECT-TYPE
            SYNTAX       DisplayString
            MAX-ACCESS   read-only
            STATUS       current
            DESCRIPTION 
                "get the mac address of the MoCA"
            ::= { moca 3 }

        mocaPrivacyEnbl OBJECT-TYPE
            SYNTAX       TruthValue
            MAX-ACCESS   read-write
            STATUS       current
            DESCRIPTION 
                "enable/disable privacy"
            ::= { moca 4 }

        mocaPrivacyPwd OBJECT-TYPE
            SYNTAX       DisplayString
            MAX-ACCESS   read-write
            STATUS       current
            DESCRIPTION 
                "set/get privacy password size applies 12-17 byte lenght ascii"
            ::= { moca 5 }

        mocaConstantPWEnbl OBJECT-TYPE
            SYNTAX       TruthValue
            MAX-ACCESS   read-write
            STATUS       current
            DESCRIPTION 
                "enable/disable constant power"
            ::= { moca 6 }

        mocaPreferredNCEnbl OBJECT-TYPE
            SYNTAX       TruthValue
            MAX-ACCESS   read-write
            STATUS       current
            DESCRIPTION 
                "enable/disable preferred NC"
            ::= { moca 7 }

        mocaLinkStatus OBJECT-TYPE
            SYNTAX       DisplayString
            MAX-ACCESS   read-only
            STATUS       current
            DESCRIPTION 
                "show link status(UP/DOWN) of MoCA"
            ::= { moca 8 }

        mocaLof OBJECT-TYPE
            SYNTAX       DisplayString
            MAX-ACCESS   read-only
            STATUS       current
            DESCRIPTION 
                "show last of frequecny"
            ::= { moca 9 }

        mocaHWVersion OBJECT-TYPE
            SYNTAX       DisplayString
            MAX-ACCESS   read-only
            STATUS       current
            DESCRIPTION 
                "show hardware verion of MoCA USG's"
            ::= { moca 10 }

        mocaTxPower OBJECT-TYPE
            SYNTAX       Integer32
            MAX-ACCESS   read-write
            STATUS       current
            DESCRIPTION 
                "set/get a level of power range was 0 - 10"
            ::= { moca 11 }

        mocaBeaconpwrlevel OBJECT-TYPE
            SYNTAX       Integer32
            MAX-ACCESS   read-write
            STATUS       current
            DESCRIPTION 
                "set/get setup a level of beacon power range was 0 - 10"
            ::= { moca 12 }

        -- This OID is obsolete
        -- mocaQoSEnbl OBJECT-TYPE ::= { moca 13 }

    puma5 OBJECT IDENTIFIER ::= { smcUsgGateway 18 }

        puma5SwVersion OBJECT IDENTIFIER ::= { puma5 1 }

            puma5SwVersionEmtaDocsis OBJECT-TYPE
                SYNTAX       DisplayString
                MAX-ACCESS   read-only
                STATUS       current
                DESCRIPTION 
                    "get the emta docsis software version"
                ::= { puma5SwVersion 1 }

            puma5SwVersionPacketCable OBJECT-TYPE
                SYNTAX       DisplayString
                MAX-ACCESS   read-only
                STATUS       current
                DESCRIPTION 
                    "get the packet cable version"
                ::= { puma5SwVersion 2 }

        puma5HwInfo OBJECT IDENTIFIER ::= { puma5 2 }

            puma5HwInfoHwIdentifier OBJECT-TYPE
                SYNTAX       DisplayString
                MAX-ACCESS   read-only
                STATUS       current
                DESCRIPTION 
                    "get the hw identifier"
                ::= { puma5HwInfo 1 }

            puma5HwInfoProcessorSpeed OBJECT-TYPE
                SYNTAX       DisplayString
                MAX-ACCESS   read-only
                STATUS       current
                DESCRIPTION 
                    "get the processor speed"
                ::= { puma5HwInfo 2 }

            puma5HwInfoDram OBJECT-TYPE
                SYNTAX       DisplayString
                MAX-ACCESS   read-only
                STATUS       current
                DESCRIPTION 
                    "get the dram size"
                ::= { puma5HwInfo 3 }

            puma5HwInfoFlash OBJECT-TYPE
                SYNTAX       DisplayString
                MAX-ACCESS   read-only
                STATUS       current
                DESCRIPTION 
                    "get the flash size"
                ::= { puma5HwInfo 4 }

            puma5HwInfoCpuUsage OBJECT-TYPE
                SYNTAX       DisplayString
                MAX-ACCESS   read-only
                STATUS       current
                DESCRIPTION 
                    "get the CPU usage"
                ::= { puma5HwInfo 5 }

            puma5HwInfoMemFrag OBJECT-TYPE
                SYNTAX       DisplayString
                MAX-ACCESS   read-only
                STATUS       current
                DESCRIPTION 
                    "get the Memory Fragmentation"
                ::= { puma5HwInfo 6 }

            puma5HwInfoMemInfo OBJECT-TYPE
                SYNTAX       DisplayString
                MAX-ACCESS   read-only
                STATUS       current
                DESCRIPTION 
                    "get the Memory Utilization"
                ::= { puma5HwInfo 7 }

            puma5HwInfoPackageQueue OBJECT-TYPE
                SYNTAX       DisplayString
                MAX-ACCESS   read-only
                STATUS       current
                DESCRIPTION 
                    "get the current and max package queue lengths"
                ::= { puma5HwInfo 8 }

            puma5HwInfoUsbEtherTime OBJECT-TYPE
                SYNTAX       DisplayString
                MAX-ACCESS   read-only
                STATUS       current
                DESCRIPTION 
                    "get the USB ether time"
                ::= { puma5HwInfo 9 }

        puma5UsbInfo OBJECT IDENTIFIER ::= { puma5 3 }

            puma5UsbInfoStatus OBJECT-TYPE
                SYNTAX       DisplayString
                MAX-ACCESS   read-only
                STATUS       current
                DESCRIPTION 
                    "get the status"
                ::= { puma5UsbInfo 1 }

            puma5UsbInfoDescription OBJECT-TYPE
                SYNTAX       DisplayString
                MAX-ACCESS   read-only
                STATUS       current
                DESCRIPTION 
                    "get the description"
                ::= { puma5UsbInfo 2 }

            puma5UsbInfoPortId OBJECT-TYPE
                SYNTAX       DisplayString
                MAX-ACCESS   read-only
                STATUS       current
                DESCRIPTION 
                    "get the port id"
                ::= { puma5UsbInfo 3 }

            puma5UsbInfoProductId OBJECT-TYPE
                SYNTAX       DisplayString
                MAX-ACCESS   read-only
                STATUS       current
                DESCRIPTION 
                    "get the product id"
                ::= { puma5UsbInfo 4 }

            puma5UsbInfoVendorId OBJECT-TYPE
                SYNTAX       DisplayString
                MAX-ACCESS   read-only
                STATUS       current
                DESCRIPTION 
                    "get the vendor id"
                ::= { puma5UsbInfo 5 }

            puma5UsbInfoVer OBJECT-TYPE
                SYNTAX       DisplayString
                MAX-ACCESS   read-only
                STATUS       current
                DESCRIPTION 
                    "get the version"
                ::= { puma5UsbInfo 6 }

            puma5UsbInfoSerialNum OBJECT-TYPE
                SYNTAX       DisplayString
                MAX-ACCESS   read-only
                STATUS       current
                DESCRIPTION 
                    "get the serial number"
                ::= { puma5UsbInfo 7 }

            puma5UsbInfoSpeed OBJECT-TYPE
                SYNTAX       DisplayString
                MAX-ACCESS   read-only
                STATUS       current
                DESCRIPTION 
                    "get the speed"
                ::= { puma5UsbInfo 8 }

            puma5UsbInfoManufacturer OBJECT-TYPE
                SYNTAX       DisplayString
                MAX-ACCESS   read-only
                STATUS       current
                DESCRIPTION 
                    "get the manufacturer"
                ::= { puma5UsbInfo 9 }

            puma5UsbInfoLocationId OBJECT-TYPE
                SYNTAX       DisplayString
                MAX-ACCESS   read-only
                STATUS       current
                DESCRIPTION 
                    "get the location id"
                ::= { puma5UsbInfo 10 }

            puma5UsbInfoCurrentAvailable OBJECT-TYPE
                SYNTAX       DisplayString
                MAX-ACCESS   read-only
                STATUS       current
                DESCRIPTION 
                    "get the current available"
                ::= { puma5UsbInfo 11 }

            puma5UsbInfoCurrentRequired OBJECT-TYPE
                SYNTAX       DisplayString
                MAX-ACCESS   read-only
                STATUS       current
                DESCRIPTION 
                    "get the current required"
                ::= { puma5UsbInfo 12 }

        puma5Reset OBJECT-TYPE
            SYNTAX       INTEGER {
                puma5-reboot(1),
                reset-factory-settings(2)
            }
            MAX-ACCESS   read-write
            STATUS       current
            DESCRIPTION 
                "Write-only object. Reading this object will result in implementation-specific
                 value, generally empty or a string describing the node is write-only.

                 Reset Gateway Settings/Reboot Gateway"
            ::= { puma5 4 }

    dect OBJECT IDENTIFIER ::= { smcUsgGateway 19 }

        dectEnbl OBJECT-TYPE
            SYNTAX       TruthValue
            MAX-ACCESS   read-write
            STATUS       current
            DESCRIPTION 
                "true(enable)/false(disable) DECT Module"
            ::= { dect 1 }

        dectHwInfo OBJECT IDENTIFIER ::= { dect 2 }

            dectHwInfoOperStatus OBJECT-TYPE
                SYNTAX       Integer32
                MAX-ACCESS   read-only
                STATUS       current
                DESCRIPTION 
                    "status of DECT module
                     inactive(0)
                     active(1)"
                ::= { dectHwInfo 1 }

            dectHwInfoSerialNum OBJECT-TYPE
                SYNTAX       DisplayString
                MAX-ACCESS   read-only
                STATUS       current
                DESCRIPTION 
                    "serial number of DECT BASE"
                ::= { dectHwInfo 2 }

            dectHwInfoVendor OBJECT-TYPE
                SYNTAX       DisplayString
                MAX-ACCESS   read-only
                STATUS       current
                DESCRIPTION 
                    "Vendor of USG"
                ::= { dectHwInfo 3 }

            dectHwInfoBootVer OBJECT-TYPE
                SYNTAX       DisplayString
                MAX-ACCESS   read-only
                STATUS       current
                DESCRIPTION 
                    "Version of bootloader of DECT BASE"
                ::= { dectHwInfo 4 }

            dectHwInfoModel OBJECT-TYPE
                SYNTAX       DisplayString
                MAX-ACCESS   read-only
                STATUS       current
                DESCRIPTION 
                    "Model of DECT BASE"
                ::= { dectHwInfo 5 }

            dectHwInfoProductType OBJECT-TYPE
                SYNTAX       DisplayString
                MAX-ACCESS   read-only
                STATUS       current
                DESCRIPTION 
                    "Product type of DECT BASE"
                ::= { dectHwInfo 6 }

            dectHwInfoFlashPart OBJECT-TYPE
                SYNTAX       DisplayString
                MAX-ACCESS   read-only
                STATUS       current
                DESCRIPTION 
                    "Flash part of DECT BASE"
                ::= { dectHwInfo 7 }

            dectHwInfoCodeVer OBJECT-TYPE
                SYNTAX       DisplayString
                MAX-ACCESS   read-only
                STATUS       current
                DESCRIPTION 
                    "Code version of DECT BASE"
                ::= { dectHwInfo 8 }

            dectHwInfoVer OBJECT-TYPE
                SYNTAX       DisplayString
                MAX-ACCESS   read-only
                STATUS       current
                DESCRIPTION 
                    "hardware version of DECT BASE"
                ::= { dectHwInfo 9 }

            dectHwInfoRfpi OBJECT-TYPE
                SYNTAX       DisplayString
                MAX-ACCESS   read-only
                STATUS       current
                DESCRIPTION 
                    "RFPI of DECT BASE"
                ::= { dectHwInfo 10 }

            dectHwInfoResetNow OBJECT-TYPE
                SYNTAX       TruthValue
                MAX-ACCESS   read-write
                STATUS       current
                DESCRIPTION 
                    "Immediately to reset DECT BASE"
                ::= { dectHwInfo 11 }

        dectBaseInfo OBJECT IDENTIFIER ::= { dect 3 }

            dectBaseInfoRegisterMode OBJECT-TYPE
                SYNTAX       TruthValue
                MAX-ACCESS   read-write
                STATUS       current
                DESCRIPTION 
                    "Write-only object. Reading this object will result in implementation-specific
                     value, generally empty or a string describing the node is write-only.

                     enter(true)/exit(false) registration mode"
                ::= { dectBaseInfo 1 }

            dectBaseInfoCurrentVer OBJECT-TYPE
                SYNTAX       DisplayString
                MAX-ACCESS   read-only
                STATUS       current
                DESCRIPTION 
                    "current software version of DECT BASE"
                ::= { dectBaseInfo 2 }

            dectBaseInfoDataSrvcVer OBJECT-TYPE
                SYNTAX       DisplayString
                MAX-ACCESS   read-only
                STATUS       current
                DESCRIPTION 
                    "software version of DECT and data service"
                ::= { dectBaseInfo 3 }

            dectBaseInfoOperStatus OBJECT-TYPE
                SYNTAX       Integer32
                MAX-ACCESS   read-only
                STATUS       current
                DESCRIPTION 
                    "updating status of DECT base
                     inProgress(1), completeFromProvisioning(2), completeFromMgt(3),
                     failed(4), other(5)"
                ::= { dectBaseInfo 4 }

            dectBaseInfoAdminStatus OBJECT-TYPE
                SYNTAX       Integer32
                MAX-ACCESS   read-write
                STATUS       current
                DESCRIPTION 
                    "updating mode of DECT base
                     upgradeFromMgt(1), allowProvisioningUpgrade(2)
                     ignoreProvisioningUpgrade(3)"
                ::= { dectBaseInfo 5 }

            dectBaseInfoSrvrIp OBJECT-TYPE
                SYNTAX       IpAddress
                MAX-ACCESS   read-write
                STATUS       current
                DESCRIPTION 
                    "server ip address"
                ::= { dectBaseInfo 6 }

            dectBaseInfoFilename OBJECT-TYPE
                SYNTAX       DisplayString
                MAX-ACCESS   read-write
                STATUS       current
                DESCRIPTION 
                    "The filename of the DECT base software image"
                ::= { dectBaseInfo 7 }

        dectHsSwInfo OBJECT IDENTIFIER ::= { dect 4 }

            dectHsSwInfoOperStatus OBJECT-TYPE
                SYNTAX       Integer32
                MAX-ACCESS   read-only
                STATUS       current
                DESCRIPTION 
                    "updating status of DECT HADSET
                     inProgress(1), completeFromProvisioning(2), completeFromMgt(3),
                     failed(4), other(5)"
                ::= { dectHsSwInfo 1 }

            dectHsSwInfoAdminStatus OBJECT-TYPE
                SYNTAX       Integer32
                MAX-ACCESS   read-write
                STATUS       current
                DESCRIPTION 
                    "updating mode of DECT HADSET
                     upgradeFromMgt(1), allowProvisioningUpgrade(2)
                     ignoreProvisioningUpgrade(3)"
                ::= { dectHsSwInfo 2 }

            dectHsSwInfoSrvrIp OBJECT-TYPE
                SYNTAX       IpAddress
                MAX-ACCESS   read-write
                STATUS       current
                DESCRIPTION 
                    "server ip address"
                ::= { dectHsSwInfo 3 }

            dectHsSwInfoFilename OBJECT-TYPE
                SYNTAX       DisplayString
                MAX-ACCESS   read-write
                STATUS       current
                DESCRIPTION 
                    "The filename of the DECT HANDSET software image"
                ::= { dectHsSwInfo 4 }

        dectHandsetTable OBJECT-TYPE
            SYNTAX       SEQUENCE OF DectHandsetEntry
            MAX-ACCESS   not-accessible 
            STATUS       current
            DESCRIPTION 
                "show the handsets software version and operation status."
            ::= { dect 5 }

        dectHandsetEntry OBJECT-TYPE
            SYNTAX       DectHandsetEntry
            MAX-ACCESS   not-accessible 
            STATUS       current
            DESCRIPTION 
                "Entry of table dectHandset"
            INDEX        { dectHandsetIndex }
            ::= { dectHandsetTable 1 }

        DectHandsetEntry ::=
        SEQUENCE {
                dectHandsetIndex                                 Integer32,
                dectHandsetRowStatus                             RowStatus,
                dectHandsetHsIndex                               Integer32,
                dectHandsetHsSwVer                               DisplayString,
                dectHandsetOperStatus                            Integer32
        }

        dectHandsetIndex OBJECT-TYPE
            SYNTAX       Integer32
            MAX-ACCESS   read-only
            STATUS       current
            DESCRIPTION 
                "Index of dectHandsetEntry."
            ::= { dectHandsetEntry 1 }

        dectHandsetRowStatus OBJECT-TYPE
            SYNTAX       RowStatus
            MAX-ACCESS   read-create
            STATUS       current
            DESCRIPTION 
                "The status of this conceptual row.
                 Set createAndGo(4) or createAndWait(5) to create a row in this table.
                 Set destroy(6) to delete all of the instances associated with an existing
                 conceptual row."
            ::= { dectHandsetEntry 2 }

        dectHandsetHsIndex OBJECT-TYPE
            SYNTAX       Integer32
            MAX-ACCESS   read-create
            STATUS       current
            DESCRIPTION 
                "index of DECT Handset"
            ::= { dectHandsetEntry 3 }

        dectHandsetHsSwVer OBJECT-TYPE
            SYNTAX       DisplayString
            MAX-ACCESS   read-only
            STATUS       current
            DESCRIPTION 
                "software version of DECT Handset"
            ::= { dectHandsetEntry 4 }

        dectHandsetOperStatus OBJECT-TYPE
            SYNTAX       Integer32
            MAX-ACCESS   read-only
            STATUS       current
            DESCRIPTION 
                "updating status of DECT HADSET
                 inProgress(1), completeFromProvisioning(2), completeFromMgt(3),
                 failed(4), other(5)"
            ::= { dectHandsetEntry 5 }

        dectAccountInfoTable OBJECT-TYPE
            SYNTAX       SEQUENCE OF DectAccountInfoEntry
            MAX-ACCESS   not-accessible 
            STATUS       current
            DESCRIPTION 
                "configure account information, can not add new entry"
            ::= { dect 6 }

        dectAccountInfoEntry OBJECT-TYPE
            SYNTAX       DectAccountInfoEntry
            MAX-ACCESS   not-accessible 
            STATUS       current
            DESCRIPTION 
                "Entry of table dectAccountInfo"
            INDEX        { dectAccountInfoIndex }
            ::= { dectAccountInfoTable 1 }

        DectAccountInfoEntry ::=
        SEQUENCE {
                dectAccountInfoIndex                             Integer32,
                dectAccountInfoRowStatus                         RowStatus,
                dectAccountInfoNcsId                             Integer32,
                dectAccountInfoUsr                               DisplayString,
                dectAccountInfoEMail                             DisplayString,
                dectAccountInfoTelephoneNum                      DisplayString,
                dectAccountInfoDef                               TruthValue,
                dectAccountInfoAlertColor                        Integer32,
                dectAccountInfoRingTone                          Integer32
        }

        dectAccountInfoIndex OBJECT-TYPE
            SYNTAX       Integer32
            MAX-ACCESS   read-only
            STATUS       current
            DESCRIPTION 
                "Index of dectAccountInfoEntry."
            ::= { dectAccountInfoEntry 1 }

        dectAccountInfoRowStatus OBJECT-TYPE
            SYNTAX       RowStatus
            MAX-ACCESS   read-create
            STATUS       current
            DESCRIPTION 
                "The status of this conceptual row.
                 Set createAndGo(4) or createAndWait(5) to create a row in this table.
                 Set destroy(6) to delete all of the instances associated with an existing
                 conceptual row."
            ::= { dectAccountInfoEntry 2 }

        dectAccountInfoNcsId OBJECT-TYPE
            SYNTAX       Integer32
            MAX-ACCESS   read-create
            STATUS       current
            DESCRIPTION 
                "index of NCS (key)"
            ::= { dectAccountInfoEntry 3 }

        dectAccountInfoUsr OBJECT-TYPE
            SYNTAX       DisplayString
            MAX-ACCESS   read-create
            STATUS       current
            DESCRIPTION 
                "user of profile (key)"
            ::= { dectAccountInfoEntry 4 }

        dectAccountInfoEMail OBJECT-TYPE
            SYNTAX       DisplayString
            MAX-ACCESS   read-create
            STATUS       current
            DESCRIPTION 
                "e-mail address of user (key)"
            ::= { dectAccountInfoEntry 5 }

        dectAccountInfoTelephoneNum OBJECT-TYPE
            SYNTAX       DisplayString
            MAX-ACCESS   read-create
            STATUS       current
            DESCRIPTION 
                "telephone of user (key)"
            ::= { dectAccountInfoEntry 6 }

        dectAccountInfoDef OBJECT-TYPE
            SYNTAX       TruthValue
            MAX-ACCESS   read-create
            STATUS       current
            DESCRIPTION 
                "default telephone (key)"
            ::= { dectAccountInfoEntry 7 }

        dectAccountInfoAlertColor OBJECT-TYPE
            SYNTAX       Integer32
            MAX-ACCESS   read-create
            STATUS       current
            DESCRIPTION 
                "index of alert color
                 Red(1), Blue(2), Green(3), Orange(4), Cyan(5), Purple(6)"
            ::= { dectAccountInfoEntry 8 }

        dectAccountInfoRingTone OBJECT-TYPE
            SYNTAX       Integer32
            MAX-ACCESS   read-create
            STATUS       current
            DESCRIPTION 
                "index of ringtone name
                 Baroque-harpsichord(1), Beethevon5th(2), Bumblebee(3),
                 Classical(4), Entertainer(5), Fantasy(6), Kiynago(7),
                 Lotus(8), Orleans(9), Ringer-crystal(10),
                 Ringer-doorbell(11), Ringer-telephone(12), Rumba(13),
                 St.Louis(14), Toccata(15)"
            ::= { dectAccountInfoEntry 9 }

        dectHsConnectTable OBJECT-TYPE
            SYNTAX       SEQUENCE OF DectHsConnectEntry
            MAX-ACCESS   not-accessible 
            STATUS       current
            DESCRIPTION 
                "configure DECT Handsets. The add command just let DECT BASE
                 enter registration mode, not use to add real entry."
            ::= { dect 7 }

        dectHsConnectEntry OBJECT-TYPE
            SYNTAX       DectHsConnectEntry
            MAX-ACCESS   not-accessible 
            STATUS       current
            DESCRIPTION 
                "Entry of table dectHsConnect"
            INDEX        { dectHsConnectIndex }
            ::= { dectHsConnectTable 1 }

        DectHsConnectEntry ::=
        SEQUENCE {
                dectHsConnectIndex                               Integer32,
                dectHsConnectRowStatus                           RowStatus,
                dectHsConnectHsIndex                             Integer32,
                dectHsConnectHsConnStatus                        INTEGER,
                dectHsConnectHsLineStatus                        DisplayString
        }

        dectHsConnectIndex OBJECT-TYPE
            SYNTAX       Integer32
            MAX-ACCESS   read-only
            STATUS       current
            DESCRIPTION 
                "Index of dectHsConnectEntry."
            ::= { dectHsConnectEntry 1 }

        dectHsConnectRowStatus OBJECT-TYPE
            SYNTAX       RowStatus
            MAX-ACCESS   read-create
            STATUS       current
            DESCRIPTION 
                "The status of this conceptual row.
                 Set createAndGo(4) or createAndWait(5) to create a row in this table.
                 Set destroy(6) to delete all of the instances associated with an existing
                 conceptual row."
            ::= { dectHsConnectEntry 2 }

        dectHsConnectHsIndex OBJECT-TYPE
            SYNTAX       Integer32
            MAX-ACCESS   read-create
            STATUS       current
            DESCRIPTION 
                "index of DECT Handset"
            ::= { dectHsConnectEntry 3 }

        dectHsConnectHsConnStatus OBJECT-TYPE
            SYNTAX       INTEGER {
                active(1),
                out-of-range(2)
            }
            MAX-ACCESS   read-only
            STATUS       current
            DESCRIPTION 
                "connection status of Handset"
            ::= { dectHsConnectEntry 4 }

        dectHsConnectHsLineStatus OBJECT-TYPE
            SYNTAX       DisplayString
            MAX-ACCESS   read-only
            STATUS       current
            DESCRIPTION 
                "Line status of Handset"
            ::= { dectHsConnectEntry 5 }

    email OBJECT IDENTIFIER ::= { smcUsgGateway 20 }

        emailFwBreach OBJECT-TYPE
            SYNTAX       TruthValue
            MAX-ACCESS   read-write
            STATUS       current
            DESCRIPTION 
                "enable email notification for firewall breach"
            ::= { email 1 }

        emailPrntlCtrlBreach OBJECT-TYPE
            SYNTAX       TruthValue
            MAX-ACCESS   read-write
            STATUS       current
            DESCRIPTION 
                "enable email notification for parental control breach"
            ::= { email 2 }

        emailAlertsWarnings OBJECT-TYPE
            SYNTAX       TruthValue
            MAX-ACCESS   read-write
            STATUS       current
            DESCRIPTION 
                "enable email notification for alert or warnings"
            ::= { email 3 }

        emailSendLogs OBJECT-TYPE
            SYNTAX       TruthValue
            MAX-ACCESS   read-write
            STATUS       current
            DESCRIPTION 
                "send logs"
            ::= { email 4 }

        emailEmailaddr OBJECT-TYPE
            SYNTAX       DisplayString
            MAX-ACCESS   read-write
            STATUS       current
            DESCRIPTION 
                "email receiver address"
            ::= { email 5 }

        emailSmtpserver OBJECT-TYPE
            SYNTAX       InetAddress
            MAX-ACCESS   read-write
            STATUS       current
            DESCRIPTION 
                "email server address"
            ::= { email 6 }

        emailSmtpserverSmtpUsername OBJECT-TYPE
            SYNTAX       DisplayString
            MAX-ACCESS   read-write
            STATUS       current
            DESCRIPTION 
                "smtp server username"
            ::= { email 7 }

        emailSmtpserverSmtpPswd OBJECT-TYPE
            SYNTAX       DisplayString
            MAX-ACCESS   read-write
            STATUS       current
            DESCRIPTION 
                "smtp server password"
            ::= { email 8 }

    psm OBJECT IDENTIFIER ::= { smcUsgGateway 21 }

        psmPSMPowerSrc OBJECT-TYPE
            SYNTAX       DisplayString
            MAX-ACCESS   read-only
            STATUS       current
            DESCRIPTION 
                "Show the Power_Source of PSM(AC/DC)"
            ::= { psm 1 }

        psmMAXServiceTime OBJECT-TYPE
            SYNTAX       DisplayString
            MAX-ACCESS   read-only
            STATUS       current
            DESCRIPTION 
                "Show Max Service Time(YES/NO)"
            ::= { psm 2 }

        psmUSB1Get OBJECT-TYPE
            SYNTAX       DisplayString
            MAX-ACCESS   read-only
            STATUS       current
            DESCRIPTION 
                "ON/OFF USB1 of PSM"
            ::= { psm 3 }

        psmUSB2Get OBJECT-TYPE
            SYNTAX       DisplayString
            MAX-ACCESS   read-only
            STATUS       current
            DESCRIPTION 
                "ON/OFF USB2 of PSM"
            ::= { psm 4 }

        psmSwitchGet OBJECT-TYPE
            SYNTAX       Integer32
            MAX-ACCESS   read-only
            STATUS       current
            DESCRIPTION 
                "Get Switch Mode(0,1,2,3) of PSM"
            ::= { psm 5 }

        psmWIFI24Get OBJECT-TYPE
            SYNTAX       DisplayString
            MAX-ACCESS   read-only
            STATUS       current
            DESCRIPTION 
                "ON/OFF Wifi2.4G of PSM"
            ::= { psm 6 }

        psmWIFI5Get OBJECT-TYPE
            SYNTAX       DisplayString
            MAX-ACCESS   read-only
            STATUS       current
            DESCRIPTION 
                "ON/OFF Wifi5G of PSM"
            ::= { psm 7 }

        psmPFSGet OBJECT-TYPE
            SYNTAX       DisplayString
            MAX-ACCESS   read-only
            STATUS       current
            DESCRIPTION 
                "ON/OFF Printer/File Sharing of PSM"
            ::= { psm 8 }

        psmMOCAGet OBJECT-TYPE
            SYNTAX       DisplayString
            MAX-ACCESS   read-only
            STATUS       current
            DESCRIPTION 
                "ON/OFF MOCA of PSM"
            ::= { psm 9 }

        psmUSB1Set OBJECT-TYPE
            SYNTAX       TruthValue
            MAX-ACCESS   read-write
            STATUS       current
            DESCRIPTION 
                "true(enable)/false(disable) USB1 of PSM"
            ::= { psm 10 }

        psmUSB2Set OBJECT-TYPE
            SYNTAX       TruthValue
            MAX-ACCESS   read-write
            STATUS       current
            DESCRIPTION 
                "true(enable)/false(disable) USB2 of PSM"
            ::= { psm 11 }

        psmSwitchSet OBJECT-TYPE
            SYNTAX       INTEGER {
                disable-All(1),
                disable-4-Ports(2),
                enable-Lan1(3),
                enable-All(4)
            }
            MAX-ACCESS   read-write
            STATUS       current
            DESCRIPTION 
                "set Switch of PSM"
            ::= { psm 12 }

        psmWIFI24Set OBJECT-TYPE
            SYNTAX       TruthValue
            MAX-ACCESS   read-write
            STATUS       current
            DESCRIPTION 
                "true(enable)/false(disable) Wifi2.4G of PSM"
            ::= { psm 13 }

        psmWIFI5Set OBJECT-TYPE
            SYNTAX       TruthValue
            MAX-ACCESS   read-write
            STATUS       current
            DESCRIPTION 
                "true(enable)/false(disable) Wifi5G of PSM"
            ::= { psm 14 }

        psmPFSSet OBJECT-TYPE
            SYNTAX       TruthValue
            MAX-ACCESS   read-write
            STATUS       current
            DESCRIPTION 
                "true(enable)/false(disable) Printer/File Sharing of PSM"
            ::= { psm 15 }

        psmMOCASet OBJECT-TYPE
            SYNTAX       TruthValue
            MAX-ACCESS   read-write
            STATUS       current
            DESCRIPTION 
                "true(enable)/false(disable) MOCA of PSM"
            ::= { psm 16 }

        psmSmcUsgPowerFailureEnableAll OBJECT-TYPE
            SYNTAX       TruthValue
            MAX-ACCESS   read-write
            STATUS       current
            DESCRIPTION 
                "true(enable)/false(disable) Enable all components, including
                 the Cable modem, Router and Wi-Fi components during power failure."
            ::= { psm 17 }

        psmSmcUsgPowerFailureEnableAll2ndBattery OBJECT-TYPE
            SYNTAX       TruthValue
            MAX-ACCESS   read-write
            STATUS       current
            DESCRIPTION 
                "true(enable)/false(disable) When a secondary battery is installed,
                 enable all components, including the Cable modem, Router
                 and Wi-Fi components during power failure."
            ::= { psm 18 }

    sysinfo OBJECT IDENTIFIER ::= { smcUsgGateway 22 }

        sysinfoDev OBJECT-TYPE
            SYNTAX       DisplayString
            MAX-ACCESS   read-only
            STATUS       current
            DESCRIPTION 
                "show device name"
            ::= { sysinfo 1 }

        sysinfoVendor OBJECT-TYPE
            SYNTAX       DisplayString
            MAX-ACCESS   read-only
            STATUS       current
            DESCRIPTION 
                "show vendor name"
            ::= { sysinfo 2 }

        sysinfoModel OBJECT-TYPE
            SYNTAX       DisplayString
            MAX-ACCESS   read-only
            STATUS       current
            DESCRIPTION 
                "show model name"
            ::= { sysinfo 3 }

        sysinfoModelDescription OBJECT-TYPE
            SYNTAX       DisplayString
            MAX-ACCESS   read-only
            STATUS       current
            DESCRIPTION 
                "show model description"
            ::= { sysinfo 4 }

        sysinfoSerial OBJECT-TYPE
            SYNTAX       DisplayString
            MAX-ACCESS   read-only
            STATUS       current
            DESCRIPTION 
                "show serial number"
            ::= { sysinfo 5 }

        sysinfoSwVer OBJECT-TYPE
            SYNTAX       DisplayString
            MAX-ACCESS   read-only
            STATUS       current
            DESCRIPTION 
                "show product firmware version"
            ::= { sysinfo 6 }

        sysinfoSwDate OBJECT-TYPE
            SYNTAX       DisplayString
            MAX-ACCESS   read-only
            STATUS       current
            DESCRIPTION 
                "show the date of product firmware generation"
            ::= { sysinfo 7 }

        sysinfoPresentationUrl OBJECT-TYPE
            SYNTAX       DisplayString
            MAX-ACCESS   read-only
            STATUS       current
            DESCRIPTION 
                "url for the web-based user interface used for configuration"
            ::= { sysinfo 8 }

        sysinfoRestore OBJECT-TYPE
            SYNTAX       INTEGER {
                usg(1),
                wifi-router(2)
            }
            MAX-ACCESS   read-write
            STATUS       current
            DESCRIPTION 
                "Write-only object. Reading this object will result in implementation-specific
                 value, generally empty or a string describing the node is write-only.

                 restore factory default configuration of the whole system or
                 a specific module"
            ::= { sysinfo 9 }

        sysinfoReboot OBJECT-TYPE
            SYNTAX       INTEGER {
                usg(1),
                wifi-router(2),
                hsi(3),
                telephoneline(4)
            }
            MAX-ACCESS   read-write
            STATUS       current
            DESCRIPTION 
                "Write-only object. Reading this object will result in implementation-specific
                 value, generally empty or a string describing the node is write-only.

                 reboot the whole system or a specific module"
            ::= { sysinfo 10 }

END
