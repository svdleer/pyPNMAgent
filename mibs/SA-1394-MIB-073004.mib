--
-- SA-1394-MIB.mib
-- MIB generated by MG-SOFT Visual MIB Builder Version 4.0 Build 349
-- Friday, July 30, 2004 at 10:41:53
--

-- Revision 1 : Initial Public Release
-- Date: Thursday, April 15, 2004 at 12:53:14
-- Comment:
-- The initial public release of this module.
-- 
-- Revision 2 : 2nd Public Release
-- Date: Friday, July 30, 2004 at 10:41:09
-- Comment:
-- Added sa1394VideoPlugAnalogSwitchingTable
-- 
	SA-1394-MIB DEFINITIONS ::= BEGIN
 
		IMPORTS
			sa1394Mib			
				FROM SA-DBDSGEN-MIB			
			saModules			
				FROM SCIATL-COMMON-MIB			
			OBJECT-GROUP, MODULE-COMPLIANCE			
				FROM SNMPv2-CONF			
			Integer32, Unsigned32, OBJECT-TYPE, MODULE-IDENTITY, OBJECT-IDENTITY			
				FROM SNMPv2-SMI			
			DisplayString, TimeStamp, TruthValue, AutonomousType, DateAndTime			
				FROM SNMPv2-TC;
	
	
-- 
-- 
		-- 1.3.6.1.4.1.1429.7.1.15
		sa1394MibModule MODULE-IDENTITY 
			LAST-UPDATED "200407301041Z"		-- July 30, 2004 at 10:41 GMT
			ORGANIZATION 
				"Scientific-Atlanta"
			CONTACT-INFO 
				"DBDS Software Engineering & Architecture
				Scientific-Atlanta
				5030 Sugarloaf Parkway
				Lawrenceville, GA 30044
				"
			DESCRIPTION 
				"The Scientific-Atlanta MIB module for 1394.
				
				This module Copyright 2003, 2004 Scientific Atlanta.
				
				"
			REVISION "200407301041Z"		-- July 30, 2004 at 10:41 GMT
			DESCRIPTION 
				"Added sa1394VideoPlugAnalogSwitchingTable"
			REVISION "200404151253Z"		-- April 15, 2004 at 12:53 GMT
			DESCRIPTION 
				"The initial public release of this module."
			::= { saModules 15 }

		
	
	
--
-- Node definitions
--
	
		-- 1.3.6.1.4.1.1429.9.1.13.1
		sa1394Conf OBJECT-IDENTITY
			STATUS current
			DESCRIPTION 
				"Conformance"
			::= { sa1394Mib 1 }

		
		-- 1.3.6.1.4.1.1429.9.1.13.1.1
		sa1394Groups OBJECT-IDENTITY
			STATUS current
			DESCRIPTION 
				"Object groups for the SA-1394-MIB"
			::= { sa1394Conf 1 }

		
		-- 1.3.6.1.4.1.1429.9.1.13.1.1.1
		sa1394DeviceTableGroup OBJECT-GROUP
			OBJECTS { sa1394DeviceIndex, sa1394DeviceEID64, sa1394DeviceIsLocal, sa1394DeviceIsAvc, sa1394DeviceEia775DeviceType, 
				sa1394DeviceEia775Version, sa1394DeviceVendorName, sa1394DeviceVendorModelID, sa1394DeviceVendorModelText, sa1394DeviceHasMonitor, 
				sa1394DeviceIsRevoked }
			STATUS current
			DESCRIPTION 
				"The table of devices."
			::= { sa1394Groups 1 }

		
		-- 1.3.6.1.4.1.1429.9.1.13.1.1.2
		sa1394SrmTableGroup OBJECT-GROUP
			OBJECTS { sa1394DtcpSrmGeneration, sa1394DtcpSrmVersion, sa1394DtcpSrmActivateTime, sa1394DtcpSrmStorage }
			STATUS current
			DESCRIPTION 
				"The SRM Table Group."
			::= { sa1394Groups 2 }

		
		-- 1.3.6.1.4.1.1429.9.1.13.1.1.3
		sa1394PlugTableGroup OBJECT-GROUP
			OBJECTS { sa1394PlugIndex, sa1394PlugType, sa1394PlugState, sa1394PlugSpecificType }
			STATUS current
			DESCRIPTION 
				"The Plug Table Group"
			::= { sa1394Groups 3 }

		
		-- 1.3.6.1.4.1.1429.9.1.13.1.1.4
		sa1394VideoPlugGroup OBJECT-GROUP
			OBJECTS { sa1394VideoPlugContainsSpts, sa1394VideoPlugPgmNum, sa1394VideoPlugVideoPID, sa1394VideoPlugAudioPID, sa1394VideoPlugPcrPid, 
				sa1394VideoPlugEmi, sa1394VideoPlugCci }
			STATUS current
			DESCRIPTION 
				"The Video Plug Group"
			::= { sa1394Groups 4 }

		
		-- 1.3.6.1.4.1.1429.9.1.13.1.1.5
		sa1394DevConnMapTableGroup OBJECT-GROUP
			OBJECTS { sa1394DevConnMapIndex, sa1394DevConnMapForeignDev, sa1394DevConnMapConnTime, sa1394DevConnMapAuth, sa1394DevConnMapLocalPlugValid, 
				sa1394DevConnMapLocalPlug, sa1394DevConnMapForeignPlugValid, sa1394DevConnMapForeignPlug }
			STATUS current
			DESCRIPTION 
				"The Device Connection Group"
			::= { sa1394Groups 5 }

		
		-- 1.3.6.1.4.1.1429.9.1.13.1.1.6
		sa1394AVSourceTableGroup OBJECT-GROUP
			OBJECTS { sa1394AVSourceId }
			STATUS current
			DESCRIPTION 
				"The AVSource Table Group."
			::= { sa1394Groups 6 }

		
		-- 1.3.6.1.4.1.1429.9.1.13.1.1.7
		sa1394VideoPlugAnalogSwitchingTableGroup OBJECT-GROUP
			OBJECTS { sa1394VideoPlugAnalogSwitchingSupported }
			STATUS current
			DESCRIPTION 
				"The Video Plug Analog Switching Table Group."
			::= { sa1394Groups 7 }

		
		-- 1.3.6.1.4.1.1429.9.1.13.1.2
		saLlcCompls OBJECT-IDENTITY
			STATUS current
			DESCRIPTION 
				"Compliance descriptions for the SA-1394-MIB"
			::= { sa1394Conf 2 }

		
		-- 1.3.6.1.4.1.1429.9.1.13.1.2.1
		sa1394BasicCompliance MODULE-COMPLIANCE
			STATUS current
			DESCRIPTION 
				"Identifies the most basic items that any implementation must provide."
			MODULE -- this module
				MANDATORY-GROUPS { sa1394DeviceTableGroup }
			::= { saLlcCompls 1 }

		
		-- 1.3.6.1.4.1.1429.9.1.13.2
		sa1394Objs OBJECT-IDENTITY
			STATUS current
			DESCRIPTION 
				"The objects of the SA-1394-MIB module."
			::= { sa1394Mib 2 }

		
		-- 1.3.6.1.4.1.1429.9.1.13.2.1
		sa1394Devices OBJECT-IDENTITY
			STATUS current
			DESCRIPTION 
				"1394 device characteristics"
			::= { sa1394Objs 1 }

		
		-- 1.3.6.1.4.1.1429.9.1.13.2.1.1
		sa1394DeviceTable OBJECT-TYPE
			SYNTAX SEQUENCE OF Sa1394DeviceEntry
			MAX-ACCESS not-accessible
			STATUS current
			DESCRIPTION
				"A table of 1394 devices known to the host, internal and external
				to the host."
			::= { sa1394Devices 1 }

		
		-- 1.3.6.1.4.1.1429.9.1.13.2.1.1.1
		sa1394DeviceEntry OBJECT-TYPE
			SYNTAX Sa1394DeviceEntry
			MAX-ACCESS not-accessible
			STATUS current
			DESCRIPTION
				"An entry in the table.
				
				If this device is also represented in the HOST-RESOURCES-MIB
				hrDeviceTable, then the value of sa1394DeviceIndex must
				match hrDeviceIndex."
			INDEX { sa1394DeviceIndex }
			::= { sa1394DeviceTable 1 }

		
		Sa1394DeviceEntry ::=
			SEQUENCE { 
				sa1394DeviceIndex
					Integer32,
				sa1394DeviceEID64
					OCTET STRING,
				sa1394DeviceIsLocal
					TruthValue,
				sa1394DeviceIsAvc
					TruthValue,
				sa1394DeviceEia775DeviceType
					INTEGER,
				sa1394DeviceEia775Version
					OCTET STRING,
				sa1394DeviceVendorName
					DisplayString,
				sa1394DeviceVendorModelID
					OCTET STRING,
				sa1394DeviceVendorModelText
					DisplayString,
				sa1394DeviceHasMonitor
					TruthValue,
				sa1394DeviceIsRevoked
					INTEGER
			 }

		-- 1.3.6.1.4.1.1429.9.1.13.2.1.1.1.1
		sa1394DeviceIndex OBJECT-TYPE
			SYNTAX Integer32 (1..2147483647)
			MAX-ACCESS read-only
			STATUS current
			DESCRIPTION
				"A unique number for each 1394 device in the table.
				
				If this device is also represented in the HOST-RESOURCES-MIB
				hrDeviceTable, then the value of sa1394DeviceIndex must
				match hrDeviceIndex."
			::= { sa1394DeviceEntry 1 }

		
		-- 1.3.6.1.4.1.1429.9.1.13.2.1.1.1.2
		sa1394DeviceEID64 OBJECT-TYPE
			SYNTAX OCTET STRING
			MAX-ACCESS read-only
			STATUS current
			DESCRIPTION
				"Globally Unique 'Extended ID' Unique for each 1394 device"
			::= { sa1394DeviceEntry 2 }

		
		-- 1.3.6.1.4.1.1429.9.1.13.2.1.1.1.3
		sa1394DeviceIsLocal OBJECT-TYPE
			SYNTAX TruthValue
			MAX-ACCESS read-only
			STATUS current
			DESCRIPTION
				"Indicates if the device is part of the host (true) or
				atteched to the host via the 1394 bus (false)."
			::= { sa1394DeviceEntry 3 }

		
		-- 1.3.6.1.4.1.1429.9.1.13.2.1.1.1.4
		sa1394DeviceIsAvc OBJECT-TYPE
			SYNTAX TruthValue
			MAX-ACCESS read-only
			STATUS current
			DESCRIPTION
				"Boolean stating whether AV/C is supported by the device"
			::= { sa1394DeviceEntry 4 }

		
		-- 1.3.6.1.4.1.1429.9.1.13.2.1.1.1.5
		sa1394DeviceEia775DeviceType OBJECT-TYPE
			SYNTAX INTEGER
				{
				notApplicable(1),
				producer(2),
				consumer(3),
				producerConsumer(4)
				}
			MAX-ACCESS read-only
			STATUS current
			DESCRIPTION
				"If the device is an EIA775 device, then this identifies
				the kind of device."
			::= { sa1394DeviceEntry 5 }

		
		-- 1.3.6.1.4.1.1429.9.1.13.2.1.1.1.6
		sa1394DeviceEia775Version OBJECT-TYPE
			SYNTAX OCTET STRING (SIZE (3))
			MAX-ACCESS read-only
			STATUS current
			DESCRIPTION
				"If EIA775 is supported by the device, this item provides the
				version of EIA775 supported by the device. The value is zero (0)
				otherwise.
				"
			::= { sa1394DeviceEntry 6 }

		
		-- 1.3.6.1.4.1.1429.9.1.13.2.1.1.1.7
		sa1394DeviceVendorName OBJECT-TYPE
			SYNTAX DisplayString
			MAX-ACCESS read-only
			STATUS current
			DESCRIPTION
				"The device's vendor name
				"
			::= { sa1394DeviceEntry 7 }

		
		-- 1.3.6.1.4.1.1429.9.1.13.2.1.1.1.8
		sa1394DeviceVendorModelID OBJECT-TYPE
			SYNTAX OCTET STRING (SIZE (3))
			MAX-ACCESS read-only
			STATUS current
			DESCRIPTION
				"The module ID assigned to the device by the vendor"
			::= { sa1394DeviceEntry 8 }

		
		-- 1.3.6.1.4.1.1429.9.1.13.2.1.1.1.9
		sa1394DeviceVendorModelText OBJECT-TYPE
			SYNTAX DisplayString
			MAX-ACCESS read-only
			STATUS current
			DESCRIPTION
				"The text description of the model
				"
			::= { sa1394DeviceEntry 9 }

		
		-- 1.3.6.1.4.1.1429.9.1.13.2.1.1.1.10
		sa1394DeviceHasMonitor OBJECT-TYPE
			SYNTAX TruthValue
			MAX-ACCESS read-only
			STATUS current
			DESCRIPTION
				"Boolean stating whether the 1394 device has a Monitor as a subunit.
				"
			::= { sa1394DeviceEntry 10 }

		
		-- 1.3.6.1.4.1.1429.9.1.13.2.1.1.1.11
		sa1394DeviceIsRevoked OBJECT-TYPE
			SYNTAX INTEGER
				{
				unknown(1),
				notRevoked(2),
				revoked(3)
				}
			MAX-ACCESS read-only
			STATUS current
			DESCRIPTION
				"Indicates if the device's certificates have been
				revoked (Contained in SRM's CRL).
				
				unknown    = The host does not know the revocation status
				notRevoked = The device's certificate have not been revoked
				revoked    = The device's certificates have been revoked"
			::= { sa1394DeviceEntry 11 }

		
		-- 1.3.6.1.4.1.1429.9.1.13.2.1.2
		sa1394DtcpSrmTable OBJECT-TYPE
			SYNTAX SEQUENCE OF Sa1394DtcpSrmEntry
			MAX-ACCESS not-accessible
			STATUS current
			DESCRIPTION
				"A table of SRM information associated with a device.
				"
			::= { sa1394Devices 2 }

		
		-- 1.3.6.1.4.1.1429.9.1.13.2.1.2.1
		sa1394DtcpSrmEntry OBJECT-TYPE
			SYNTAX Sa1394DtcpSrmEntry
			MAX-ACCESS not-accessible
			STATUS current
			DESCRIPTION
				"A row in the table."
			INDEX { sa1394DeviceIndex }
			::= { sa1394DtcpSrmTable 1 }

		
		Sa1394DtcpSrmEntry ::=
			SEQUENCE { 
				sa1394DtcpSrmGeneration
					Unsigned32,
				sa1394DtcpSrmVersion
					Unsigned32,
				sa1394DtcpSrmActivateTime
					DateAndTime,
				sa1394DtcpSrmStorage
					INTEGER
			 }

		-- 1.3.6.1.4.1.1429.9.1.13.2.1.2.1.1
		sa1394DtcpSrmGeneration OBJECT-TYPE
			SYNTAX Unsigned32
			MAX-ACCESS read-only
			STATUS current
			DESCRIPTION
				"The generation/format of the SRM data"
			::= { sa1394DtcpSrmEntry 1 }

		
		-- 1.3.6.1.4.1.1429.9.1.13.2.1.2.1.2
		sa1394DtcpSrmVersion OBJECT-TYPE
			SYNTAX Unsigned32
			MAX-ACCESS read-only
			STATUS current
			DESCRIPTION
				"The version of this particular SRM
				"
			::= { sa1394DtcpSrmEntry 2 }

		
		-- 1.3.6.1.4.1.1429.9.1.13.2.1.2.1.3
		sa1394DtcpSrmActivateTime OBJECT-TYPE
			SYNTAX DateAndTime
			MAX-ACCESS read-only
			STATUS current
			DESCRIPTION
				"The time when the device starting using this SRM data
				"
			::= { sa1394DtcpSrmEntry 3 }

		
		-- 1.3.6.1.4.1.1429.9.1.13.2.1.2.1.4
		sa1394DtcpSrmStorage OBJECT-TYPE
			SYNTAX INTEGER
				{
				network(1),
				local(2)
				}
			MAX-ACCESS read-only
			STATUS current
			DESCRIPTION
				"Indicates how the SRM is stored.
				
				network = The SRM is stored on the network
				local   = The SRM is stored on the device"
			::= { sa1394DtcpSrmEntry 4 }

		
		-- 1.3.6.1.4.1.1429.9.1.13.2.1.3
		sa1394DevConnMapTable OBJECT-TYPE
			SYNTAX SEQUENCE OF Sa1394DevConnMapEntry
			MAX-ACCESS not-accessible
			STATUS current
			DESCRIPTION
				"A table of 1394 devices connected to the currently indexed device.
				"
			::= { sa1394Devices 3 }

		
		-- 1.3.6.1.4.1.1429.9.1.13.2.1.3.1
		sa1394DevConnMapEntry OBJECT-TYPE
			SYNTAX Sa1394DevConnMapEntry
			MAX-ACCESS not-accessible
			STATUS current
			DESCRIPTION
				"A row in the table."
			INDEX { sa1394DeviceIndex, sa1394DevConnMapIndex }
			::= { sa1394DevConnMapTable 1 }

		
		Sa1394DevConnMapEntry ::=
			SEQUENCE { 
				sa1394DevConnMapIndex
					Integer32,
				sa1394DevConnMapForeignDev
					Integer32,
				sa1394DevConnMapConnTime
					TimeStamp,
				sa1394DevConnMapAuth
					INTEGER,
				sa1394DevConnMapLocalPlugValid
					TruthValue,
				sa1394DevConnMapLocalPlug
					Integer32,
				sa1394DevConnMapForeignPlugValid
					TruthValue,
				sa1394DevConnMapForeignPlug
					Integer32
			 }

		-- 1.3.6.1.4.1.1429.9.1.13.2.1.3.1.1
		sa1394DevConnMapIndex OBJECT-TYPE
			SYNTAX Integer32 (1..2147483647)
			MAX-ACCESS read-only
			STATUS current
			DESCRIPTION
				"A unique value for this entry within the domain of the
				sa394Device."
			::= { sa1394DevConnMapEntry 1 }

		
		-- 1.3.6.1.4.1.1429.9.1.13.2.1.3.1.2
		sa1394DevConnMapForeignDev OBJECT-TYPE
			SYNTAX Integer32
			MAX-ACCESS read-only
			STATUS current
			DESCRIPTION
				"The value of sa1394DeviceIndex corresponding to the foreign device.
				This indicates the entry of the sa1394DeviceTable that represents
				the device on the other 'side' of the connection.
				"
			::= { sa1394DevConnMapEntry 2 }

		
		-- 1.3.6.1.4.1.1429.9.1.13.2.1.3.1.3
		sa1394DevConnMapConnTime OBJECT-TYPE
			SYNTAX TimeStamp
			MAX-ACCESS read-only
			STATUS current
			DESCRIPTION
				"The time the connection was established."
			::= { sa1394DevConnMapEntry 3 }

		
		-- 1.3.6.1.4.1.1429.9.1.13.2.1.3.1.4
		sa1394DevConnMapAuth OBJECT-TYPE
			SYNTAX INTEGER
				{
				none(1),
				restricted(2),
				full(3)
				}
			MAX-ACCESS read-only
			STATUS current
			DESCRIPTION
				"Authentication type performed"
			::= { sa1394DevConnMapEntry 4 }

		
		-- 1.3.6.1.4.1.1429.9.1.13.2.1.3.1.5
		sa1394DevConnMapLocalPlugValid OBJECT-TYPE
			SYNTAX TruthValue
			MAX-ACCESS read-only
			STATUS current
			DESCRIPTION
				"A TruthValue stating whether the local plug ID is known.
				If this true, then the sa1394DevConnMapLocalPlug has a
				valid value; otherwise it does not."
			::= { sa1394DevConnMapEntry 5 }

		
		-- 1.3.6.1.4.1.1429.9.1.13.2.1.3.1.6
		sa1394DevConnMapLocalPlug OBJECT-TYPE
			SYNTAX Integer32
			MAX-ACCESS read-only
			STATUS current
			DESCRIPTION
				"A reference to the plug ID used by the local device for the connection.
				This value is only valid if sa1394DevConnMapLocalPlugValid is true.
				
				This value can be used to find the corresponding row in
				sa1394PlugTable by using it as the value for sa1394PlugIndex
				when querying that table. (The device index is the same value
				as that used to index this table)."
			::= { sa1394DevConnMapEntry 6 }

		
		-- 1.3.6.1.4.1.1429.9.1.13.2.1.3.1.7
		sa1394DevConnMapForeignPlugValid OBJECT-TYPE
			SYNTAX TruthValue
			MAX-ACCESS read-only
			STATUS current
			DESCRIPTION
				"A TruthValue stating whether the foreign plug ID is known.
				If this true, then the sa1394DevConnMapForeignPlug has a
				valid value; otherwise it does not."
			::= { sa1394DevConnMapEntry 7 }

		
		-- 1.3.6.1.4.1.1429.9.1.13.2.1.3.1.8
		sa1394DevConnMapForeignPlug OBJECT-TYPE
			SYNTAX Integer32
			MAX-ACCESS read-only
			STATUS current
			DESCRIPTION
				"A reference to the plug ID used by the foreign device for the connection.
				This value is only valid if sa1394DevConnMapForeignPlugValid is true.
				
				This value can be used to find the corresponding row in
				sa1394PlugTable by using it as the value for sa1394PlugIndex
				when querying that table. (The device index for the foreign device
				is the value of sa1394DevConnMapForeignDev for this row)"
			::= { sa1394DevConnMapEntry 8 }

		
		-- 1.3.6.1.4.1.1429.9.1.13.2.2
		sa1394Plugs OBJECT-IDENTITY
			STATUS current
			DESCRIPTION 
				"Plug characteristics"
			::= { sa1394Objs 2 }

		
		-- 1.3.6.1.4.1.1429.9.1.13.2.2.1
		sa1394PlugTable OBJECT-TYPE
			SYNTAX SEQUENCE OF Sa1394PlugEntry
			MAX-ACCESS not-accessible
			STATUS current
			DESCRIPTION
				"A table of plugs for devices."
			::= { sa1394Plugs 1 }

		
		-- 1.3.6.1.4.1.1429.9.1.13.2.2.1.1
		sa1394PlugEntry OBJECT-TYPE
			SYNTAX Sa1394PlugEntry
			MAX-ACCESS not-accessible
			STATUS current
			DESCRIPTION
				"A row in the table."
			INDEX { sa1394DeviceIndex, sa1394PlugIndex }
			::= { sa1394PlugTable 1 }

		
		Sa1394PlugEntry ::=
			SEQUENCE { 
				sa1394PlugIndex
					Integer32,
				sa1394PlugType
					INTEGER,
				sa1394PlugState
					INTEGER,
				sa1394PlugSpecificType
					AutonomousType
			 }

		-- 1.3.6.1.4.1.1429.9.1.13.2.2.1.1.1
		sa1394PlugIndex OBJECT-TYPE
			SYNTAX Integer32 (1..2147483647)
			MAX-ACCESS read-only
			STATUS current
			DESCRIPTION
				"A unique number for the plug within the context of the device."
			::= { sa1394PlugEntry 1 }

		
		-- 1.3.6.1.4.1.1429.9.1.13.2.2.1.1.2
		sa1394PlugType OBJECT-TYPE
			SYNTAX INTEGER
				{
				in(1),
				out(2)
				}
			MAX-ACCESS read-only
			STATUS current
			DESCRIPTION
				"The 'direction' of this plug as 'in' or 'out'."
			::= { sa1394PlugEntry 2 }

		
		-- 1.3.6.1.4.1.1429.9.1.13.2.2.1.1.3
		sa1394PlugState OBJECT-TYPE
			SYNTAX INTEGER
				{
				idle(1),
				ready(2),
				active(3),
				suspended(4)
				}
			MAX-ACCESS read-only
			STATUS current
			DESCRIPTION
				"The state of the plug."
			::= { sa1394PlugEntry 3 }

		
		-- 1.3.6.1.4.1.1429.9.1.13.2.2.1.1.4
		sa1394PlugSpecificType OBJECT-TYPE
			SYNTAX AutonomousType
			MAX-ACCESS read-only
			STATUS current
			DESCRIPTION
				"Either an OID value that provides a more specific type
				identification or an OID that points to the root of
				a MIB subtree for the plug type. If neither of these
				can be reported, then OID 0.0 is reported."
			::= { sa1394PlugEntry 4 }

		
		-- 1.3.6.1.4.1.1429.9.1.13.2.2.2
		sa1394VideoPlugTable OBJECT-TYPE
			SYNTAX SEQUENCE OF Sa1394VideoPlugEntry
			MAX-ACCESS not-accessible
			STATUS current
			DESCRIPTION
				"Video Out Plugs
				
				Each row in this table relates to one row in the sa1394PlugTable
				and provides more information for this specific kind of plug."
			::= { sa1394Plugs 2 }

		
		-- 1.3.6.1.4.1.1429.9.1.13.2.2.2.1
		sa1394VideoPlugEntry OBJECT-TYPE
			SYNTAX Sa1394VideoPlugEntry
			MAX-ACCESS not-accessible
			STATUS current
			DESCRIPTION
				"A row in the table."
			INDEX { sa1394DeviceIndex, sa1394PlugIndex }
			::= { sa1394VideoPlugTable 1 }

		
		Sa1394VideoPlugEntry ::=
			SEQUENCE { 
				sa1394VideoPlugContainsSpts
					TruthValue,
				sa1394VideoPlugPgmNum
					Unsigned32,
				sa1394VideoPlugVideoPID
					Unsigned32,
				sa1394VideoPlugAudioPID
					Unsigned32,
				sa1394VideoPlugPcrPid
					Integer32,
				sa1394VideoPlugEmi
					INTEGER,
				sa1394VideoPlugCci
					INTEGER
			 }

		-- 1.3.6.1.4.1.1429.9.1.13.2.2.2.1.1
		sa1394VideoPlugContainsSpts OBJECT-TYPE
			SYNTAX TruthValue
			MAX-ACCESS read-only
			STATUS current
			DESCRIPTION
				"Boolean stating whether a SPTS is being streamed"
			::= { sa1394VideoPlugEntry 1 }

		
		-- 1.3.6.1.4.1.1429.9.1.13.2.2.2.1.2
		sa1394VideoPlugPgmNum OBJECT-TYPE
			SYNTAX Unsigned32
			MAX-ACCESS read-only
			STATUS current
			DESCRIPTION
				"If streaming, this is the MPEG program number in the SPTS;
				otherwise this value is zero.
				"
			::= { sa1394VideoPlugEntry 2 }

		
		-- 1.3.6.1.4.1.1429.9.1.13.2.2.2.1.3
		sa1394VideoPlugVideoPID OBJECT-TYPE
			SYNTAX Unsigned32
			MAX-ACCESS read-only
			STATUS current
			DESCRIPTION
				"If streaming, this is the video PID in the SPTS;
				otherwise this value is zero."
			::= { sa1394VideoPlugEntry 3 }

		
		-- 1.3.6.1.4.1.1429.9.1.13.2.2.2.1.4
		sa1394VideoPlugAudioPID OBJECT-TYPE
			SYNTAX Unsigned32
			MAX-ACCESS read-only
			STATUS current
			DESCRIPTION
				"If streaming, this is the audio PID in the SPTS;
				otherwise this value is zero."
			::= { sa1394VideoPlugEntry 4 }

		
		-- 1.3.6.1.4.1.1429.9.1.13.2.2.2.1.5
		sa1394VideoPlugPcrPid OBJECT-TYPE
			SYNTAX Integer32
			MAX-ACCESS read-only
			STATUS current
			DESCRIPTION
				"If streaming, this is the PCR PID in the SPTS;
				otherwise this value is zero."
			::= { sa1394VideoPlugEntry 5 }

		
		-- 1.3.6.1.4.1.1429.9.1.13.2.2.2.1.6
		sa1394VideoPlugEmi OBJECT-TYPE
			SYNTAX INTEGER
				{
				undefined(0),
				copyNever(1),
				copyOneGeneration(2),
				copyNoMore(3),
				copyFree(4)
				}
			MAX-ACCESS read-only
			STATUS current
			DESCRIPTION
				"If streaming, contains the EMI value being encoded into the 1394 stream;
				otherwise the value is zero."
			::= { sa1394VideoPlugEntry 6 }

		
		-- 1.3.6.1.4.1.1429.9.1.13.2.2.2.1.7
		sa1394VideoPlugCci OBJECT-TYPE
			SYNTAX INTEGER
				{
				undefined(0),
				copyNever(1),
				copyOneGeneration(2),
				copyNoMore(3),
				copyFree(4)
				}
			MAX-ACCESS read-only
			STATUS current
			DESCRIPTION
				"If streaming, contains the CCI value being encoded into the PMT
				otherwise the value is zero."
			::= { sa1394VideoPlugEntry 7 }

		
		-- 1.3.6.1.4.1.1429.9.1.13.2.2.3
		sa1394AVSourceTable OBJECT-TYPE
			SYNTAX SEQUENCE OF Sa1394AVSourceEntry
			MAX-ACCESS not-accessible
			STATUS current
			DESCRIPTION
				"A table of information relating to the source of data on a plug.
				If no information is available for this plug, then the agent will
				not report a row for the plug when queried."
			::= { sa1394Plugs 3 }

		
		-- 1.3.6.1.4.1.1429.9.1.13.2.2.3.1
		sa1394AVSourceEntry OBJECT-TYPE
			SYNTAX Sa1394AVSourceEntry
			MAX-ACCESS not-accessible
			STATUS current
			DESCRIPTION
				"A row within the table"
			INDEX { sa1394DeviceIndex, sa1394PlugIndex }
			::= { sa1394AVSourceTable 1 }

		
		Sa1394AVSourceEntry ::=
			SEQUENCE { 
				sa1394AVSourceId
					Integer32
			 }

		-- 1.3.6.1.4.1.1429.9.1.13.2.2.3.1.1
		sa1394AVSourceId OBJECT-TYPE
			SYNTAX Integer32
			MAX-ACCESS read-only
			STATUS current
			DESCRIPTION
				"The ATSC/56 SourceID."
			::= { sa1394AVSourceEntry 1 }

		
		-- 1.3.6.1.4.1.1429.9.1.13.2.2.4
		sa1394VideoPlugAnalogSwitchingTable OBJECT-TYPE
			SYNTAX SEQUENCE OF Sa1394VideoPlugAnalogSwitchingEntry
			MAX-ACCESS not-accessible
			STATUS current
			DESCRIPTION
				"A table of information related to the analog switching capability of
				a video output plug.
				
				If no information is available for this plug, then the agent will
				not report a row for the plug when queried."
			::= { sa1394Plugs 4 }

		
		-- 1.3.6.1.4.1.1429.9.1.13.2.2.4.1
		sa1394VideoPlugAnalogSwitchingEntry OBJECT-TYPE
			SYNTAX Sa1394VideoPlugAnalogSwitchingEntry
			MAX-ACCESS not-accessible
			STATUS current
			DESCRIPTION
				"An entry in the table."
			INDEX { sa1394DeviceIndex, sa1394PlugIndex }
			::= { sa1394VideoPlugAnalogSwitchingTable 1 }

		
		Sa1394VideoPlugAnalogSwitchingEntry ::=
			SEQUENCE { 
				sa1394VideoPlugAnalogSwitchingSupported
					TruthValue
			 }

		-- 1.3.6.1.4.1.1429.9.1.13.2.2.4.1.1
		sa1394VideoPlugAnalogSwitchingSupported OBJECT-TYPE
			SYNTAX TruthValue
			MAX-ACCESS read-only
			STATUS current
			DESCRIPTION
				"Indicates if analog switching is supported for the video plug.
				
				If no information is available for this plug, then the agent will
				not report a row for the plug when queried."
			::= { sa1394VideoPlugAnalogSwitchingEntry 1 }

		
		-- 1.3.6.1.4.1.1429.9.1.13.3
		sa1394Events OBJECT-IDENTITY
			STATUS current
			DESCRIPTION 
				"Events associated with the SA-1394-MIB module"
			::= { sa1394Mib 3 }

		
		-- 1.3.6.1.4.1.1429.9.1.13.3.0
		sa1394EventsV2 OBJECT-IDENTITY
			STATUS current
			DESCRIPTION 
				"Dummy node needed for V1 compatability."
			::= { sa1394Events 0 }

		
	
	END

--
-- SA-1394-MIB.mib
--
