-- Electroline Global Registration mib
-- SNMPv2
--
-- FileName: ELECTROLINE-GLOBAL-REG.mib
-- RevDate: 09/02/2001
--
-- Frederick Plante
-- Nathaniel Mercure
-- Eric Desjardins
-- Carlene Gardner 2003-03-21

ELECTROLINE-GLOBAL-REG DEFINITIONS ::= BEGIN


IMPORTS
    MODULE-IDENTITY, OBJECT-IDENTITY,
    enterprises
        FROM SNMPv2-SMI;

--
-- Sub-tree definitions
--

-- 
-- Sub-tree for Electroline in enterprises
-- 1.3.6.1.4.1.5802
-- 
electrolineCoRoot       OBJECT-IDENTITY
    STATUS          current
    DESCRIPTION     "The root of the OID sub-tree assigned 
                to Electroline Equipment Inc. by the
                Internet Assigned Numbers Authority (IANA)."

    ::={enterprises 5802}

electrolineRoot         OBJECT-IDENTITY
    STATUS          current
    DESCRIPTION     "The root of Electroline oid tree."
    
::={electrolineCoRoot 1}

--
-- Sub-tree for Electroline Registrations 
--
electrolineReg          OBJECT-IDENTITY
    STATUS          current
    DESCRIPTION     "Sub-tree for registration"
    ::={electrolineRoot 1}
--
-- Sub-tree for Electroline Registrations of modules
--
electrolineModules      OBJECT-IDENTITY
    STATUS          current
    DESCRIPTION     "Sub-tree for modules registrations"

    ::={electrolineReg 1}

--
-- Sub-tree for enterprise wide objects and events.
--
electrolineGeneric      OBJECT-IDENTITY
    STATUS          current
    DESCRIPTION     "Sub-tree for common objects and events."
    ::={electrolineRoot 2}

-- 
-- Sub-tree for product-specific objects and events
--
electrolineProducts     OBJECT-IDENTITY
    STATUS          current
    DESCRIPTION     "Sub-tree for product-specific objects and 
                events."
    ::={electrolineRoot 3}

--
-- Sub-tree for hardware products
--
electrolineHardwareProducts     OBJECT-IDENTITY
    STATUS          current
    DESCRIPTION     "Sub-tree for hardware products."
    ::={electrolineProducts 1}
    
--
-- Sub-tre for software products.
-- 
electrolineSoftwareProducts     OBJECT-IDENTITY
    STATUS          current
    DESCRIPTION     "Sub-tree for software products."
    ::={electrolineProducts 2}

--
-- Sub-tree for agent capabilities (caps)
--
electrolineCaps         OBJECT-IDENTITY
    STATUS          current
    DESCRIPTION     "Sub-tree for agent profiles."
    ::={electrolineRoot 4}
--
-- Sub-tree for Requirement Specifications.
--
electrolineReqs         OBJECT-IDENTITY
    STATUS          current
    DESCRIPTION     "Sub-tree for management application 
                requirements."
    ::={electrolineRoot 5}

--
-- Sub-tree for Electroline Experiments
--
electrolineExpr         OBJECT-IDENTITY
    STATUS          current
    DESCRIPTION     "Sub-tree for experimental definitions."
    ::={electrolineRoot 6}

--
-- Global Registration Module Identity
--
electrolineGlobalRegModule  MODULE-IDENTITY
    LAST-UPDATED    "1902010000Z" 
    ORGANIZATION    "Electroline Equipment Inc."
    CONTACT-INFO    "fp@electroline.com"
    DESCRIPTION "Electroline Global Registration Module."
    REVISION    "1902010000Z"
    DESCRIPTION "The first draft."
    ::={ electrolineModules 1 }

--
-- Electroline Hardware Registration Module sub-tree
--
electrolineHardwareProductsReg  OBJECT-IDENTITY
    STATUS          current
    DESCRIPTION     "Sub-tree for registration of hardware
                products modules."
    ::={ electrolineModules 2}
    
--
-- Electroline Software Registration Module sub-tree
--
electrolineSoftwareProductsReg  OBJECT-IDENTITY
    STATUS          current
    DESCRIPTION     "Sub-tree for registration of software 
                product modules."
    ::={ electrolineModules 3}


END
