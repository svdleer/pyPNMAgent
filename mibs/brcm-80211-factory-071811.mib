--****************************************************************************
--
-- Copyright (c) 2002-2011 Broadcom Corporation
--
-- This program is the proprietary software of Broadcom Corporation and/or
-- its licensors, and may only be used, duplicated, modified or distributed
-- pursuant to the terms and conditions of a separate, written license
-- agreement executed between you and Broadcom (an "Authorized License").
-- Except as set forth in an Authorized License, Broadcom grants no license
-- (express or implied), right to use, or waiver of any kind with respect to
-- the Software, and Broadcom expressly reserves all rights in and to the
-- Software and all intellectual property rights therein.  IF YOU HAVE NO
-- AUTHORIZED LICENSE, THEN YOU HAVE NO RIGHT TO USE THIS SOFTWARE IN ANY WAY,
-- AND SHOULD IMMEDIATELY NOTIFY BROADCOM AND DISCONTINUE ALL USE OF THE
-- SOFTWARE.  
--
-- Except as expressly set forth in the Authorized License,
--
-- 1.     This program, including its structure, sequence and organization,
-- constitutes the valuable trade secrets of Broadcom, and you shall use all
-- reasonable efforts to protect the confidentiality thereof, and to use this
-- information only in connection with your use of Broadcom integrated circuit
-- products.
--
-- 2.     TO THE MAXIMUM EXTENT PERMITTED BY LAW, THE SOFTWARE IS PROVIDED
-- "AS IS" AND WITH ALL FAULTS AND BROADCOM MAKES NO PROMISES, REPRESENTATIONS
-- OR WARRANTIES, EITHER EXPRESS, IMPLIED, STATUTORY, OR OTHERWISE, WITH
-- RESPECT TO THE SOFTWARE.  BROADCOM SPECIFICALLY DISCLAIMS ANY AND ALL
-- IMPLIED WARRANTIES OF TITLE, MERCHANTABILITY, NONINFRINGEMENT, FITNESS FOR
-- A PARTICULAR PURPOSE, LACK OF VIRUSES, ACCURACY OR COMPLETENESS, QUIET
-- ENJOYMENT, QUIET POSSESSION OR CORRESPONDENCE TO DESCRIPTION. YOU ASSUME
-- THE ENTIRE RISK ARISING OUT OF USE OR PERFORMANCE OF THE SOFTWARE.
--
-- 3.     TO THE MAXIMUM EXTENT PERMITTED BY LAW, IN NO EVENT SHALL BROADCOM
-- OR ITS LICENSORS BE LIABLE FOR (i) CONSEQUENTIAL, INCIDENTAL, SPECIAL,
-- INDIRECT, OR EXEMPLARY DAMAGES WHATSOEVER ARISING OUT OF OR IN ANY WAY
-- RELATING TO YOUR USE OF OR INABILITY TO USE THE SOFTWARE EVEN IF BROADCOM
-- HAS BEEN ADVISED OF THE POSSIBILITY OF SUCH DAMAGES; OR (ii) ANY AMOUNT IN
-- EXCESS OF THE AMOUNT ACTUALLY PAID FOR THE SOFTWARE ITSELF OR U.S. $1,
-- WHICHEVER IS GREATER. THESE LIMITATIONS SHALL APPLY NOTWITHSTANDING ANY
-- FAILURE OF ESSENTIAL PURPOSE OF ANY LIMITED REMEDY.
--
--****************************************************************************
--    Filename: brcm-80211-factory.mib
--    Author:   Kevin O'Neal
--    Creation Date: 19-september-2002
--
--**************************************************************************
--    Description:
--
--		private MIB for cablemodem factory
--		
--**************************************************************************
--    Revision History:
--
--**************************************************************************

BRCM-80211-FACTORY-MIB DEFINITIONS ::= BEGIN

IMPORTS
    MODULE-IDENTITY,
    OBJECT-TYPE,
    Unsigned32
        FROM SNMPv2-SMI
    TruthValue,
    DisplayString
        FROM SNMPv2-TC
    SnmpAdminString
        FROM SNMP-FRAMEWORK-MIB
    cableDataFactory
        FROM BRCM-CABLEDATA-FACTORY-MIB;
                
ieee802dot11Factory MODULE-IDENTITY
    LAST-UPDATED "201107180000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
            "Broadcom proprietary MIB for factory management and configuration
             of objects related to the wi-fi network interface."
    REVISION      "201107180000Z"
    DESCRIPTION
            "Deprecated this MIB in favor of the BRCM-WIFI-FACTORY-MIB.  This 
             MIB is not capable of supporting designs with multiple wi-fi 
             interfaces.  When this MIB is supported, all scalar objects will 
             apply to the first wi-fi interface."
    REVISION      "201103230000Z"
    DESCRIPTION
            "dot11RegulatortRev and dot11RegOverride added."         
    REVISION      "200807010000Z"
    DESCRIPTION
            "dot11IsoCountry added and dot11Country deprecated."
    REVISION      "200702050000Z"
    DESCRIPTION
            "Module description was updated. 
             Compilability issues were cleaned up: 
             - Chronological order of revision history was corrected."
    REVISION      "200308220000Z"
    DESCRIPTION
            "Added dot11Country, dot11PAParameters, dot11IdleTSSI, and 
             dot11AntennaGain objects."     
    REVISION      "200304280000Z"
    DESCRIPTION
            "Added dot11DiagWlCmd object."     
    REVISION      "200209190000Z"
    DESCRIPTION
            "Initial version of this MIB module."
    ::= { cableDataFactory 5 }

-- dot11FactoryCfg: configure 802.11 setup objects
dot11FactoryCfg OBJECT IDENTIFIER ::= { ieee802dot11Factory 1 }

dot11RegDomain OBJECT-TYPE
    SYNTAX      INTEGER {
                fcc(16),
                doc(32),
                etsi(48),
                spain(49),
                france(50),
                mkk(64) -- Japan
    }
    MAX-ACCESS  read-write
    STATUS      deprecated
    DESCRIPTION
        "The 802.11 regulatory domain."
    ::= { dot11FactoryCfg 2 }
    
dot11BoardRev OBJECT-TYPE
    SYNTAX      Unsigned32
    MAX-ACCESS  read-write
    STATUS      deprecated    
    DESCRIPTION
    	"The revision of 802.11 hardware interface."
    ::= { dot11FactoryCfg 3 }

dot11MaxPower OBJECT-TYPE
    SYNTAX      Unsigned32
    MAX-ACCESS  read-write
    STATUS      deprecated
    DESCRIPTION        
        "Sets maximum TX power for power over temperature adjustment algorithm.  
         Used to prevent output overdrive."
    ::= { dot11FactoryCfg 4 }
    
dot11Country OBJECT-TYPE
    SYNTAX      INTEGER {
                worldWide(0),
                thailand(1),
                israel(2),
                jordan(3),
                china(4),
                japan(5),
                usa(6),
                europe(7),
                allChannels(8)
    }
    MAX-ACCESS  read-write
    STATUS      deprecated
    DESCRIPTION
        "Restricts the channel set based on country requirements."
    ::= { dot11FactoryCfg 5 }

dot11PAParameters OBJECT-TYPE
    SYNTAX      OCTET STRING (SIZE (6))
    MAX-ACCESS  read-write
    STATUS      deprecated
    DESCRIPTION
        "Sets PA parameters of the wireless hardware.  Used by output power 
         control algorithm."
    ::= { dot11FactoryCfg 6 }

dot11IdleTSSI OBJECT-TYPE
    SYNTAX      INTEGER (0..255)
    MAX-ACCESS  read-write
    STATUS      deprecated
    DESCRIPTION
        "Sets idle TSSI target of the wireless hardware.  Used by output power 
        control algorithm."
    ::= { dot11FactoryCfg 7 }
    
dot11AntennaGain OBJECT-TYPE
    SYNTAX      INTEGER (0..255)
    MAX-ACCESS  read-write
    STATUS      deprecated
    DESCRIPTION
        "Sets the antenna gain of the device.  Used by output power control 
         algorithm."
    ::= { dot11FactoryCfg 8 }

dot11SromWrite OBJECT-TYPE
    SYNTAX      OCTET STRING
    MAX-ACCESS  read-write
    STATUS      deprecated
    DESCRIPTION
        "Sets Srom parameter in Wifi Permanent Nonvol. Syntax is offset/value pairing
		 with the offset (into SROM) being a word (two bytes) and the value being a multiple of words.
		 Reading this object will always return a null string."
    ::= { dot11FactoryCfg 9 }

dot11SromRead OBJECT-TYPE
    SYNTAX      OCTET STRING
    MAX-ACCESS  read-write
    STATUS      deprecated
    DESCRIPTION
        "Read Srom parameters in Wifi Permanent Nonvol. Syntax on a write is offset/length pairing
		 with the offset (into the SROM) being a word (two bytes) and the length 
		 being a multiple of words. A read of this object will the Srom values that were specifed by
		 offset/lenght paring from the last write of this object."
    ::= { dot11FactoryCfg 10 }

dot11IsoCountry OBJECT-TYPE
    SYNTAX      OCTET STRING
    MAX-ACCESS  read-write
    STATUS      deprecated
    DESCRIPTION
        "Sets country code in ISO 3166 format."
    ::= { dot11FactoryCfg 11 }

dot11RegulatoryRev OBJECT-TYPE
    SYNTAX      INTEGER (0..99)
    MAX-ACCESS  read-write
    STATUS      deprecated
    DESCRIPTION
        "Sets 802.11 Regulatory Revision Number."
    ::= { dot11FactoryCfg 12 }

dot11RegOverrideEnable OBJECT-TYPE
    SYNTAX      TruthValue
    MAX-ACCESS  read-write
    STATUS      deprecated
    DESCRIPTION
        "Enable/Disable Regulatory Override Capability.When enabled, the country code and 
        regulatory revision number in the WiFi Card SROM will be overridden with 
        corresponding values in NonVol."
    ::= { dot11FactoryCfg 13 }

-- dot11FactoryDiagnostics: various objects for 802.11 diagnostics
dot11FactoryDiagnostics OBJECT IDENTIFIER ::= { ieee802dot11Factory 2 }

dot11DiagChannel OBJECT-TYPE
    SYNTAX      Unsigned32 (1..14)
    MAX-ACCESS  read-write
    STATUS      deprecated
    DESCRIPTION
        "Sets test channel number.  Obeys regulatory domain restrictions - step 
         through regulatory domains to cover all channels."
    ::= { dot11FactoryDiagnostics 1 }
    
dot11DiagAntennaDiversity OBJECT-TYPE
    SYNTAX      INTEGER {
                diversityDisabledAntenna0(0),
                diversityDisabledAntenna1(1),
                diversityEnabledAntenna1(2),
                diversityEnabledAntenna0(3)
    }
    MAX-ACCESS  read-write
    STATUS      deprecated
    DESCRIPTION
        "If diversity is disabled, then this value indicates the antenna used
         for transmission and reception.  If diversity is enabled, then this
         value controls the initial antenna used when written, and when read
         indicates the antenna on which the most recent packet was received."
    ::= { dot11FactoryDiagnostics 2 }
    
dot11DiagTxMode OBJECT-TYPE
    SYNTAX      INTEGER {
                cw(0),
                evm(1),
                normal(2)
    }
    MAX-ACCESS  read-write
    STATUS      deprecated
    DESCRIPTION
        "cw(0) is used for frequency accuracy test, evm(1) is used for error 
         vector test.  When set to normal(2), 802.11 STAs will once again be 
         able to associate with the DUT. "
    ::= { dot11FactoryDiagnostics 3 }
    
dot11DiagTxPowerLevel OBJECT-TYPE
    SYNTAX      INTEGER (1..1000)
    UNITS       "milliwatts"
    MAX-ACCESS  read-write
    STATUS      deprecated
    DESCRIPTION
        "Sets TX test power level as permitted by regulatory domain 
         restrictions."
    ::= { dot11FactoryDiagnostics 4 }
    
dot11DiagWirelessLanCmd OBJECT-TYPE
    SYNTAX      DisplayString
    MAX-ACCESS  read-write
    STATUS      deprecated
    DESCRIPTION
        "Sends commands to the 802.11 diagnostic and manufacturing utility.
         When read, reports the last command issued."
    ::= { dot11FactoryDiagnostics 5 }
    
dot11DiagWirelessLanOutput OBJECT-TYPE
    SYNTAX      OCTET STRING
    MAX-ACCESS  read-only
    STATUS      deprecated
    DESCRIPTION
        "Reports the console output (if any) generated by the last set of the 
         dot11DiagWirelessLanCmd object."
    ::= { dot11FactoryDiagnostics 6 }
   

-- dot11FactoryWPSSettings: various objects for 802.11 WPS Configurations Settings
dot11FactoryWPSSettings OBJECT IDENTIFIER ::= { ieee802dot11Factory 3 }

dot11WPSBoardNum OBJECT-TYPE
    SYNTAX      SnmpAdminString (SIZE(0..32))
    MAX-ACCESS  read-write
    STATUS      deprecated
    DESCRIPTION
        "Sets the WPS Board  Serial Number"
    ::= { dot11FactoryWPSSettings 1 }
 
dot11WPSDeviceName OBJECT-TYPE
    SYNTAX      SnmpAdminString (SIZE(0..32))
    MAX-ACCESS  read-write
    STATUS      deprecated
    DESCRIPTION
        "Sets the WPS Device Name"
    ::= { dot11FactoryWPSSettings 2 }

dot11WPSDevicePin OBJECT-TYPE
    SYNTAX      SnmpAdminString (SIZE(8))
    MAX-ACCESS  read-write
    STATUS      deprecated
    DESCRIPTION
        "Sets the WPS Device Pin, must be ascii numerical characters"
    ::= { dot11FactoryWPSSettings 3 }

dot11WPSMfgName OBJECT-TYPE
    SYNTAX      SnmpAdminString (SIZE(0..64))
    MAX-ACCESS  read-write
    STATUS      deprecated
    DESCRIPTION
        "Sets the WPS Manufacturer Name"
    ::= { dot11FactoryWPSSettings 4 }

dot11WPSModelName OBJECT-TYPE
    SYNTAX      SnmpAdminString (SIZE(0..32))
    MAX-ACCESS  read-write
    STATUS      deprecated
    DESCRIPTION
        "Sets the WPS Model Name"
    ::= { dot11FactoryWPSSettings 5 }

dot11WPSModelNum OBJECT-TYPE
    SYNTAX      SnmpAdminString (SIZE(0..32))
    MAX-ACCESS  read-write
    STATUS      deprecated
    DESCRIPTION
        "Sets the WPS Model Number"
    ::= { dot11FactoryWPSSettings 6 }

dot11WPSUUID OBJECT-TYPE
    SYNTAX      SnmpAdminString (SIZE(0..16))
    MAX-ACCESS  read-write
    STATUS      deprecated
    DESCRIPTION
        "Sets WPS Universal Unique Identifier"
    ::= { dot11FactoryWPSSettings 7 }



END
